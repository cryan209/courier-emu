--
--      usr-definitions.mib - Common definitions to be used in all USR MIBs.
--
--
-- Author:         Jim Halpin
--
-- $Id: usr_definitions.mib,v 1.49.2.21 1998/07/01 14:31:05 samara Exp $
--
-- +==========================================================================+
-- |                            3COM Corporation
-- |                         Copyright (c)  1995-97 
-- |
-- |    The information in this software is subject to change without  notice
-- |               and shall not be construed as a commitment by
-- |                            3COM Corporation.
-- |
-- | U.S. Robotics Access Corporation  assumes no responsibility for the  use
-- | or reliability  of its software  on equipment  which is  not supplied by
-- |                            3COM Corporation.
-- | 
-- | This software is  furnished under a license and may be copied only  with  
-- | the inclusion of the above copyright notice. This software, or any other
-- | copies thereof, may not be provided  or otherwise  made available to any
-- |       other person except to one who agrees to these license terms.
-- |
-- | Title to and  ownership of the  software shall at all  times remain with
-- |                            3COM Corporation.
-- +==========================================================================+


        USR-DEFINITIONS-MIB DEFINITIONS ::= BEGIN

        IMPORTS
                enterprises             FROM RFC1155-SMI
                Integer32               FROM SNMPv2-SMI
                TEXTUAL-CONVENTION      FROM SNMPv2-TC;



--      MIB-II (same prefix as MIB-I)
--      mib-2                    OBJECT IDENTIFIER ::= { mgmt 1 }
--      interfaces               OBJECT IDENTIFIER ::= { mib-2 2 }
--      transmission             OBJECT IDENTIFIER ::= { mib-2 10 }



--      DESCRIPTION OF THE enterprises.usRobotics BRANCH:
--     
--       + enterprises
--       |
--       + - - + usr (429)
--             |
--             + - - - +  usrSysOIDs  (2)
--             |       |
--             |       + - - - > chas17Slot          (1)
--             |       + - - - > chas7Slot           (2)
--             |       + - - - > wanHubAccessServer  (3)
--             |       + - - - > S/AloneAccessServer (4)
--             |       + - - - > netServer8-16       (5)
--             |       + - - - > modemPool16         (6)
--             |       + - - - > modemPool8          (7)
--             |       + - - - > chas17SlotHp        (8)
--             |       + - - - > chas17SlotClk       (9)
--             |       + - - - > netServerII8        (10)
--             |       + - - - > netServerII16       (11)
--             |       + - - - > lanLinkerBRI        (12)
--             |       + - - - > lanLinkerD56k       (13)
--             |       + - - - > netServerII8imdm    (14)
--             |       + - - - > netServerII16imdm   (15)
--             |       + - - - > pilgrimCore         (16)
--             |       + - - - > lanLinkerDSL        (17)
--             |       + - - - > lanLinkerDslCO      (18)
--             |       + - - - > usrHiPerArc         (19)
--             |       + - - - > positronRM          (20)  Access-Router 3000
--             |       + - - - > lanLinkerDualAnalog (21)
--             |       + - - - > DSLAMCoMux          (22)
--             |       + - - - > hiPerCableRouter    (23)
--             |       + - - - > dynatronRM          (24)  Access-Router 1000
--             |       + - - - > positronEM          (25)  EdgeServerPro 3000
--             |
--             |
--             + - - - +  usrExp      (3)
--             |
--             |
--             + - - - +  common      (4)
--             |       |
--             |       + - - - > usrConfig           (1)
--             |       + - - - > usruserMan          (2)
--             |       + - - - > roboExec            (3)
--             |       + - - - > usrIpx              (4)
--             |       + - - - > usrSnmp             (5)
--             |       + - - - > atcfgFwd            (6)
--             |       + - - - > atprivateFwd        (7)
--             |       + - - - > atcfgRtmp           (8)
--             |       + - - - > usrEventHandler     (9)
--             |       + - - - > usrCip              (10)
--             |       + - - - > usrPPP              (11)
--             |       + - - - > usrIp               (12)
--             |       + - - - > usrIpCfg            (13)
--             |       + - - - > usrBridge           (14)
--             |       + - - - > usrFR               (15)
--             |       + - - - > usrFilter           (16)
--             |       + - - - > usrDns              (17)
--             |       + - - - > usrTermProt         (18)
--             |       + - - - > usrIpRouting        (19)
--             |       + - - - > usrIpxCfg           (20)
--             |       + - - - > usrIsdnMib          (21)
--             |       + - - - > usrCli              (22)
--             |       + - - - > usrD56k             (23)
--             |       + - - - > usrTftp             (24)
--             |       + - - - > usrDialout          (25)
--             |       + - - - > usrAdsl             (26)
--             |       + - - - > usrDS1              (27)
--             |       + - - - > usrDS0              (28)
--             |       + - - - > usrStack            (29)  Stackables
--             |       + - - - > usrModem            (30)
--             |       + - - - > usrTopology         (31)  Stackables
--             |       + - - - > usrPN               (32)  Private Network
--             |       + - - - > usrPPTP             (33)
--             |       + - - - > usrNTP              (34)
--             |       + - - - > usrSLIP             (35)
--             |       + - - - > usrPing             (36)
--             |       + - - - > usrRemotePing       (37)
--             |       + - - - > usrGWCBSP           (38)
--             |       + - - - > usrRM               (39)  Positron-RM
--             |       + - - - > usrTraceRoute       (40)
--             |       + - - - > usrChassis          (41)
--             |       + - - - > usrCable            (42)
--             |       + - - - > usrDsx3             (43)  DS3/E3
--             |       + - - - > usrTraps            (44)  Stackables
--             |       + - - - > usrTcp              (45)
--             |       + - - - > usrIpoa             (46)
--             |       + - - - > usrAtm1483Pvc       (47)
--             |       + - - - > usrMdmTemplate      (48)
--             |       + - - - > usrAtmArp           (49)
--             |       + - - - > usrAtmCrossConnect  (50)
--             |       + - - - > usrAtm1577Pvc       (51)
--             |       + - - - > usrAtmCfg           (52)
--             |       + - - - > usrIgmp             (53)
--             |       + - - - > usrMPIP             (54)
--             |       + - - - > usrL2TP             (55)
--             |       + - - - > usrPptp             (56)
--             |       + - - - > usrTap              (57)
--             |       + - - - > usrGwcwan           (58)
--             |       + - - - > usrDhcp             (59)
--             |       + - - - > usrNat              (60)
--             |       + - - - > usrFcp              (61)
--             |       + - - - > usrNos              (62)
--             |       + - - - > usrOspf             (63)
--             |       + - - - > usrFRExt            (64)
--             |       + - - - > usrTundisp          (68)
--             |       + - - - > usrPm               (69)
--             |       + - - - > usrVTP              (70)
--             |       + - - - > usrGre              (72)
--             |       + - - - > usrInverseARP       (73)   Frame Relay PTMP IP Networks
--             |       + - - - > usrBetaSite         (76)
--             |       + - - - > usripNat            (78)
--             |       + - - - > usrPPPoE            (79)
--             |       
--             |
--             + - - - +  usrProducts (6)
--                     |
--                     + - - - + usrPositron  (1)
--                     |       |
--                     |       + - - - > adm  (1)
--                     |       + - - - > em   (2)
--                     |
--                     |
--                     + - - - + usrDynatron  (2)
--                     |       |
--                     |       + - - - > drm  (1)
--                     |       + - - - > pem  (2)
--                     |       + - - - > mms  (3)
--		       |       + - - - > dynabri (4)
--                     |       | 
--                     |       + - - - + usrDynatronCommon (9)
--                     |               |
--                     |               + - - - > TVsetup   (1)
--                     |               + - - - > SDL       (2)
--                     |               + - - - > PSU       (3)
--                     |               + - - - > OTS       (4)
--                     |               + - - - > BulkDL    (5)
--                     |
--
--

        usRobotics	                 OBJECT IDENTIFIER ::= { enterprises 429 }


        usrSysOIDs               OBJECT IDENTIFIER ::= { usRobotics 2 }

        usrExp                   OBJECT IDENTIFIER ::= { usRobotics 3 }

        common                   OBJECT IDENTIFIER ::= { usRobotics 4 }

        usrProducts              OBJECT IDENTIFIER ::= { usRobotics 6 }


        usrPositron              OBJECT IDENTIFIER ::= { usrProducts 1 }
        adm                      OBJECT IDENTIFIER ::= { usrPositron 1 }
        em                       OBJECT IDENTIFIER ::= { usrPositron 2 }

        usrDynatron              OBJECT IDENTIFIER ::= { usrProducts 2 }
        usrDrm                   OBJECT IDENTIFIER ::= { usrDynatron 1 }
        usrPem                   OBJECT IDENTIFIER ::= { usrDynatron 2 }
        usrMms                   OBJECT IDENTIFIER ::= { usrDynatron 3 }
        usrDynaBri               OBJECT IDENTIFIER ::= { usrDynatron 4 }


        usrDynatronCommon        OBJECT IDENTIFIER ::= { usrDynatron 9 }




   -- DEFINE ALL THE COMMON GROUPS HERE, TO PREVENT DUPLICATE NUMBER
   -- ASSIGNMENTS.

        usrConfig                OBJECT IDENTIFIER ::= { common 1 }   

        usrUserMan               OBJECT IDENTIFIER ::= { common 2 }
        roboExec                 OBJECT IDENTIFIER ::= { common 3 }

        usrIpx                   OBJECT IDENTIFIER ::= { common 4 }

        usrSnmp                  OBJECT IDENTIFIER ::= { common 5 }

   -- AppleTalk Configuration tables
        atcfgFwd                 OBJECT IDENTIFIER ::= { common 6 }
        atprivateFwd             OBJECT IDENTIFIER ::= { common 7 }
   --   atcfgRtmp                OBJECT IDENTIFIER ::= { common 8 }

        usrEventHandler          OBJECT IDENTIFIER ::= { common 9 }
   
        usrCip                   OBJECT IDENTIFIER ::= { common 10 }

        usrPPP                   OBJECT IDENTIFIER ::= { common 11 }

        usrIp                    OBJECT IDENTIFIER ::= { common 12 }

        usrIpCfg                 OBJECT IDENTIFIER ::= { common 13 }

        usrBridge                OBJECT IDENTIFIER ::= { common 14 }

        usrFR                    OBJECT IDENTIFIER ::= { common 15 }

        usrFilter                OBJECT IDENTIFIER ::= { common 16 }

        usrDns                   OBJECT IDENTIFIER ::= { common 17 }

        usrTermProt              OBJECT IDENTIFIER ::= { common 18 }

        usrIpRouting             OBJECT IDENTIFIER ::= { common 19 }

        usrIpxCfg                OBJECT IDENTIFIER ::= { common 20 }

        usrIsdnMib               OBJECT IDENTIFIER ::= { common 21 }

        usrCli                   OBJECT IDENTIFIER ::= { common 22 }

        usrD56k                  OBJECT IDENTIFIER ::= { common 23 }

        usrTftp                  OBJECT IDENTIFIER ::= { common 24 }

        usrDialout               OBJECT IDENTIFIER ::= { common 25 }

        usrAdsl                  OBJECT IDENTIFIER ::= { common 26 }

        usrDS1                   OBJECT IDENTIFIER ::= { common 27 }

        usrDS0                   OBJECT IDENTIFIER ::= { common 28 }

        usrStack                 OBJECT IDENTIFIER ::= { common 29 }

        usrModem                 OBJECT IDENTIFIER ::= { common 30 }

        usrTopology              OBJECT IDENTIFIER ::= { common 31 }

        usrPN                    OBJECT IDENTIFIER ::= { common 32 }

        usrPPTP                  OBJECT IDENTIFIER ::= { common 33 }

--      usrNTP                   OBJECT IDENTIFIER ::= { common 34 }

        usrSLIP                  OBJECT IDENTIFIER ::= { common 35 }

--      usrPing                  OBJECT IDENTIFIER ::= { common 36 }

        usrRemotePing            OBJECT IDENTIFIER ::= { common 37 }

        usrGWCBSP                OBJECT IDENTIFIER ::= { common 38 }

        usrRM                    OBJECT IDENTIFIER ::= { common 39 }

        usrTraceroute            OBJECT IDENTIFIER ::= { common 40 }

        usrChassis               OBJECT IDENTIFIER ::= { common 41 }

        usrCable                 OBJECT IDENTIFIER ::= { common 42 }

        usrDsx3  		         OBJECT IDENTIFIER ::= { common 43 }

        usrTraps                 OBJECT IDENTIFIER ::= { common 44 }

        usrTcp                   OBJECT IDENTIFIER ::= { common 45 }

        usrIpoa                  OBJECT IDENTIFIER ::= { common 46 }

        usrAtm1483Pvc            OBJECT IDENTIFIER ::= { common 47 }

        usrMdmTemplate           OBJECT IDENTIFIER ::= { common 48 }

        usrAtmArp                OBJECT IDENTIFIER ::= { common 49 }

        usrAtmCrossConnect       OBJECT IDENTIFIER ::= { common 50 }

        usrAtm1577Pvc            OBJECT IDENTIFIER ::= { common 51 }

        usrAtmCfg                OBJECT IDENTIFIER ::= { common 52 }

        usrIgmp                  OBJECT IDENTIFIER ::= { common 53 }

        usrMPIP                  OBJECT IDENTIFIER ::= { common 54 }

        usrL2TP                  OBJECT IDENTIFIER ::= { common 55 }

        usrPptp                  OBJECT IDENTIFIER ::= { common 56 }

        usrTap                   OBJECT IDENTIFIER ::= { common 57 } 

   	    usrGwcwan				 OBJECT IDENTIFIER ::= { common 58 }

   	    usrDhcp  	             OBJECT IDENTIFIER ::= { common 59 }

   	    usrNat                   OBJECT IDENTIFIER ::= { common 60 }

   	    usrFcp                   OBJECT IDENTIFIER ::= { common 61 }

   	    usrNos                   OBJECT IDENTIFIER ::= { common 62 }

        usrOspf                  OBJECT IDENTIFIER ::= { common 63 }

        usrFRExt                 OBJECT IDENTIFIER ::= { common 64 }

        usrTundisp               OBJECT IDENTIFIER ::= { common 68 }

        usrPm               	 OBJECT IDENTIFIER ::= { common 69 }

        usrVTP               	 OBJECT IDENTIFIER ::= { common 70 }

        usrGre               	 OBJECT IDENTIFIER ::= { common 72 }

        usrInverseARP            OBJECT IDENTIFIER ::= { common 73 }

	    usrRsh                   OBJECT IDENTIFIER ::= { common 74 }

	    usrBetaSite              OBJECT IDENTIFIER ::= { common 76 }

		usrSS7                   OBJECT IDENTIFIER ::= { common 77 }

        usripNat               	 OBJECT IDENTIFIER ::= { common 78 }

        usrPPPoE                 OBJECT IDENTIFIER ::= { common 79 }

		usrIpSec                 OBJECT IDENTIFIER ::= { common 80 }



--      DATA TYPES AND TEXTUAL CONVENTIONS.
--

        DisplayString   ::= OCTET STRING

        ProductID       ::=  OBJECT IDENTIFIER

        PhysAddress     ::= OCTET STRING

        InterfaceIndex  ::= TEXTUAL-CONVENTION
          DISPLAY-HINT "d"
          STATUS       current
          DESCRIPTION
            "A unique value, greater than zero, for each interface
             or interface sub-layer in the managed system.  It is
             recommended that values are assigned contiguously
             starting from 1.  The value for each interface sub-
             layer must remain constant at least from one re-
             initialization of the entity's network management
             system to the next re-initialization."
          SYNTAX       Integer32

	   InterfaceIndexOrZero ::= InterfaceIndex

        UsrConfigStatus ::= INTEGER {
                                   normal(1),
                                   save(2),
                                   saving(3),
                                   load(4),
                                   loading(5)
                                   }


--      NOT SURE WHAT THIS DATATYPE WILL BE. 
--      FOR NOW,  DEFINE IT AS AN INTEGER, 
--      ... BUT USE THE LEXICAL CONVENTION TO MAKE IT EASY TO CHANGE IN THE FUTURE.
                                
        UsrNetLogicalId ::= INTEGER(-2147483648..2147483647)
                                
        UsrUserName     ::= DisplayString(SIZE (1..64))
                                
        UsrFilterName   ::= DisplayString(SIZE (1..20))
 
	UsrPolicyfileName   ::= DisplayString(SIZE (1..20))

                                


--      DEFINE ALL PILGRIM BASED SYSOIDs HERE ....
                                
        chas17Slot               OBJECT IDENTIFIER ::= { usrSysOIDs 1 }
        chas7Slot                OBJECT IDENTIFIER ::= { usrSysOIDs 2 }
                                        
        wanHubAccessServer       OBJECT IDENTIFIER ::= { usrSysOIDs 3 }
                                        
        standAloneAccessServer   OBJECT IDENTIFIER ::= { usrSysOIDs 4 }
                                        
        netServer8-16            OBJECT IDENTIFIER ::= { usrSysOIDs 5 }
                                        
        modemPool16              OBJECT IDENTIFIER ::= { usrSysOIDs 6 }
        modemPool8               OBJECT IDENTIFIER ::= { usrSysOIDs 7 }
                                        
        chas17SlotHp             OBJECT IDENTIFIER ::= { usrSysOIDs 8 }
        chas17SlotClk            OBJECT IDENTIFIER ::= { usrSysOIDs 9 }
                                        
        netServerII8             OBJECT IDENTIFIER ::= { usrSysOIDs 10 }
        netServerII16            OBJECT IDENTIFIER ::= { usrSysOIDs 11 }
                                        
        lanLinkerBRI             OBJECT IDENTIFIER ::= { usrSysOIDs 12 }
        lanLinkerD56k            OBJECT IDENTIFIER ::= { usrSysOIDs 13 }
                                        
        netServerII8imdm         OBJECT IDENTIFIER ::= { usrSysOIDs 14 }
        netServerII16imdm        OBJECT IDENTIFIER ::= { usrSysOIDs 15 }
                                        
        pilgrimCore              OBJECT IDENTIFIER ::= { usrSysOIDs 16 }
                                        
        lanLinkerDSL             OBJECT IDENTIFIER ::= { usrSysOIDs 17 }
        lanLinkerDslCO           OBJECT IDENTIFIER ::= { usrSysOIDs 18 }
                                        
        usrHiPerArc              OBJECT IDENTIFIER ::= { usrSysOIDs 19 }
                                        
--      ACCESS-ROUTER  3000
        positronRM               OBJECT IDENTIFIER ::= { usrSysOIDs 20 }
                                        
        lanLinkerDualAnalogModem OBJECT IDENTIFIER ::= { usrSysOIDs 21 }
                                
        dSLAMCoMux               OBJECT IDENTIFIER ::= { usrSysOIDs 22 }
                                
        hiPerCableRouter         OBJECT IDENTIFIER ::= { usrSysOIDs 23 }
                                
--      ACCESS-ROUTER  1000
        dynatronRM               OBJECT IDENTIFIER ::= { usrSysOIDs 24 }
                                
--      EDGESERVER-PRO 3000
        positronEM               OBJECT IDENTIFIER ::= { usrSysOIDs 25 }
                                
END

                                
--
-- For the revision history to work correctly, after a new MIB file has been
-- added to the CVS repository the first time the CVS Admin person needs to
-- set the correct comment string delimter for the file.
--
-- $Log: usr_definitions.mib,v $
-- Revision 1.49.2.21  1998/07/01 14:31:05  samara
-- Added MIB variable for the Policy Manager.
--
-- Revision 1.49.2.20  1998/06/18 20:11:43  asingh
-- Added new object for tunnel switch.
--
-- Revision 1.49.2.19  1998/03/03 19:21:40  mharper
-- return usr to usRobotics
--
-- Revision 1.49.2.18  1998/03/03 16:35:31  psd
-- Changed UsrUserName size to 1..64. Again.
--
-- Revision 1.49.2.17  1998/03/03 16:25:39  edjean
-- Merge and resolve ambiguity problem between 2.0 and 3.0
--
-- Revision 1.49.2.15  1998/02/17 14:28:37  edjean
-- modify nodes Dhcp Nat... to include usr prefix
--
-- Revision 1.49.2.14  1998/02/17 07:28:32  mharper
-- fix previously added defs so they at least compile
--
-- Revision 1.49.2.13  1998/02/17 03:45:37  edjean
-- Add common nodes for DHCP, NAT, FCP, and NOS for Dynatron
--
-- Revision 1.49.2.12  1998/02/03 21:28:27  asingh
-- Changed usrNpptp to usrPptp
--
-- Revision 1.49.2.11  1998/01/29 06:03:25  hsingh
-- GWCWAN Driver integration
--
-- Revision 1.49.2.10  1998/01/12 15:11:39  senthil
-- Added usrTap OBJ ID
--
-- Revision 1.49.2.9  1998/01/06 22:56:02  asingh
-- Entry Added for usrNpptp mib
--
-- Revision 1.49.2.8  1998/01/06 22:07:36  edjean
-- Add node number for usrDynBri
--
-- Revision 1.49.2.7  1998/01/06 17:15:33  rverma
-- Added node for L2TP prop. mib
--
-- Revision 1.49.2.6  1997/12/22 21:01:05  mredden
-- Fix pilgrim20 merge
--
-- Revision 1.49.2.5  1997/12/19 13:20:24  psd
-- Another merge from 2.0
--
-- Revision 1.49.2.4  1997/09/17 19:06:27  psd
-- Merged 2.0 to 3.0
--
--Revision 1.57.2.5  1997/09/05  15:09:29  psd
--Changes to MIBs so that they compile using the SimpleTester.
--
--Revision 1.57.2.4  1997/09/04  14:06:29  pfc
--Merge from Positron
--
-- Revision 1.57.2.3  1997/08/29 02:47:51  mredden
-- Added usrAtmArp as { common 49 }
--
-- Revision 1.57.2.2  1997/08/18 16:41:04  edjean
-- Add node for usrMdmTemplate
--
-- Revision 1.57.2.1  1997/08/18 14:34:31  edjean
-- This file has been reorganized by Bob Sparling
--
-- Revision 1.50  1997/06/04 20:54:53  jhalpin
-- Add usrTcp branch
--
--Revision 1.49.2.3  1997/08/01  17:51:50  tamirisa
--Added MPIP branch
--
-- Revision 1.49.2.2  1997/07/29 23:35:39  hasmik
-- Added usrIgmp node ID.
--
-- Revision 1.49.2.1  1997/07/01 13:27:13  pfc
-- Merge in changes from mainline branch
--
-- Revision 1.49  1997/05/08 15:32:42  jhalpin
-- Add usrCable node
--
-- Revision 1.48  1997/05/02 17:56:29  jhalpin
-- Assign usrChassis value
--
-- Revision 1.47  1997/04/18 18:56:40  rsivan
-- Undid previous.
--
-- Revision 1.46  1997/04/18 18:52:10  rsivan
-- Uncomment definition for usrNTP
--
-- Revision 1.45  1997/04/18 14:19:41  jhalpin
-- Fix up traceroute stuff
--
-- Revision 1.44  1997/04/17 19:23:03  jhaag
-- Initial Check-In of Traceroute MIB
--
-- Revision 1.43  1997/03/25 18:23:00  pfc
-- Comment out ping and ntp so they can be v2 compliant
--
-- Revision 1.42  1997/03/20 03:43:14  mredden
-- Added usrExp and usrChassis
--
-- Revision 1.41  1997/03/13 01:01:23  sanil
-- Added BSP related command for Netserver4.X Risc
--
-- Revision 1.40  1997/03/12 19:32:23  rsivan
-- Added UsrRemotePing
--
-- Revision 1.39  1997/02/19 16:02:40  jhalpin
-- RECONFIGURE IP NETWORK support
--
-- Revision 1.38  1997/02/10 19:51:40  pfc
-- Add usr_ping mib and modify configurator mib to support busy out commands
--
-- Revision 1.37  1997/02/05 21:31:50  sanil
-- Added offloading configuration to PPP and SLIP modules for GWC and Positron
-- products
--
-- Revision 1.36  1997/01/29 17:32:21  jhalpin
-- Fixup the NTP related files
--
-- Revision 1.35  1997/01/28 18:51:33  jhalpin
-- Add nodes for new common mibs.
--
-- Revision 1.34  1997/01/23 16:58:24  jhalpin
-- Add new ADSL MIB module
--
-- Revision 1.33  1996/12/19 18:05:13  jhalpin
-- Add usrADSL mib branch definition
--
-- Revision 1.32.4.1  1997/02/03 19:48:19  jhalpin
-- Add New Network table MIB objects
--
-- Revision 1.32  1996/10/03 20:13:58  edjean
-- Add Mib support for SDL, EJB
--
-- Revision 1.31  1996/09/18 21:44:42  jhalpin
-- Merge in LANLinker branch changes <sawdust city here I come..>
--
-- Revision 1.30  1996/09/05 19:03:02  jhalpin
-- Xmit user name support
--
-- Revision 1.29  1996/07/09 18:45:15  psd
-- Added the Dial-out MIB.
--
-- Revision 1.28.2.7  1997/01/24 21:41:49  jhalpin
-- Add adsl stuff
--
-- Revision 1.28.2.6  1997/01/20 22:55:54  jhalpin
-- RECONFIGURE NETWORK support
--
-- Revision 1.28.2.5  1997/01/09 16:59:15  jhalpin
-- usr_definitions.mib
--
-- Revision 1.28.2.4  1996/09/12 21:16:46  jhalpin
-- Fix MIB files....
--
-- Revision 1.28.2.3  1996/09/12 18:32:06  jhalpin
-- Fix Filter protocol bits, build usr_cli.mib into usr_netserver.mib, remove unneeded definitions from usr_definitions.mib
--
-- Revision 1.28.2.2  1996/09/04 13:11:43  jhalpin
-- Fix UsrUserName size
--
-- Revision 1.28.2.1  1996/08/14 23:10:58  jhalpin
-- sysOID names
--
-- Revision 1.28  1996/06/03 13:50:29  jhalpin
-- Remove MIB-II dns definition, no longer need Object Identity macro imported.
--
-- Revision 1.27  1996/05/22 18:41:09  psd
-- Added usrTftp.
--
-- Revision 1.26  1996/05/21 00:07:24  joek
-- Added usr_d56k.mib.
--
-- Revision 1.25  1996/05/20 14:06:21  patton
-- added the CLI MIB
--
-- Revision 1.24  1996/05/01 17:16:34  jhalpin
-- Change pilgrim to netserver, use official OID assignment.
--
-- Revision 1.23  1996/05/01 14:40:30  dougo
-- added isdn mib
--
-- Revision 1.22  1996/04/17 22:56:26  freeve
-- Create and use usrFilteName type
--
-- Revision 1.21  1996/04/05 21:12:28  psd
-- Support for configuring IPX networks via the CFM.
--
-- Revision 1.20  1996/04/04 14:42:01  hanson
-- added usrIpRouting
--
-- Revision 1.19  1996/04/03 20:46:42  winter
-- Added new objid for Terminal Protocols (telnet & ClearTCP)
--
-- Revision 1.18  1996/03/26 20:08:15  pfc
-- Add usr_at.mib
--
-- Revision 1.17  1996/03/21 22:59:27  patton
-- DNS proprietary mib
--
-- Revision 1.16  1996/03/18 23:26:00  jhalpin
-- Update mib files
--
-- Revision 1.15  1996/03/18 21:03:35  freeve
-- Hook in filter MIB
--
-- Revision 1.14  1996/03/12 21:46:57  jhalpin
-- Change User Name data type to a DisplayString
--
-- Revision 1.13  1996/03/08 19:33:31  patton
-- DNS Mib Stuff
--
-- Revision 1.12  1996/02/29 17:55:31  jhalpin
-- Make UsrUserName a common data type
--
-- Revision 1.11  1996/02/16 22:04:16  jhalpin
-- Add IP mib symbol
--
-- Revision 1.10  1996/02/01 21:50:59  jhalpin
-- Fix up InterfaceIndex macro for interface related mib files, fix netStatus comment in usr_config.mib
--
-- Revision 1.9  1996/01/19 16:33:52  dougo
-- Added usrPPP defintion
--
-- Revision 1.8  1995/12/28  18:10:05  hasmik
-- Added usrCip.
--
-- Revision 1.7  1995/12/12 02:49:23  jhalpin
-- Add in event mib definition
--
-- Revision 1.6  1995/11/28 16:19:50  pfc
-- Add AppleTalk configuration
--
-- Revision 1.5  1995/10/24 21:27:20  jhalpin
-- Split out the IF MIB into a seaprate file
--
-- Revision 1.4  1995/09/25 20:57:25  jhalpin
-- Add in usrSnmp definitions
--
-- Revision 1.3  1995/09/19 16:21:25  hasmik
-- Added usrIpx
--
-- Revision 1.2  1995/09/18 20:27:15  pfc
-- 1) Put the RoboExec mib in the right place under Pilgrim.
-- 2) Add the logging level table into the RoboExec MIB
--
-- Revision 1.1  1995/09/15 20:12:30  jhalpin
-- Rename file to remove hyphens. Also split out UDP and TCP
--
-- Revision 1.4  1995/09/07 18:19:01  jhalpin
-- Fixed types in pilgrim group definitions
--
-- Revision 1.3  1995/09/07 14:36:42  jhalpin
-- Start defining Pilgrim Groups in this file.
--
-- Revision 1.2  1995/08/31 17:25:01  jhalpin
-- Added mgmt, mib-2, and transmission definitions
--
-- Revision 1.1  1995/08/31 14:43:51  jhalpin
-- Add template info and clean up.
--
--
-- Local Variables:
-- tab-width:5
-- tab-stop-list:( 5 10 15 20 25 30 35 40 45 50 55 60 65 70 75 80)
-- End:
--
USR-USER-MAN-MIB DEFINITIONS ::= BEGIN

	IMPORTS
		Counter, IpAddress
			FROM RFC1155-SMI
		OBJECT-TYPE
			FROM RFC-1212
		TRAP-TYPE
                        FROM RFC-1215
		TruthValue				FROM SNMPv2-TC
		usrUserMan, UsrUserName, DisplayString
			FROM USR-DEFINITIONS-MIB;

	usrUserManGroup	OBJECT IDENTIFIER ::= { usrUserMan 1 }
	usrUserManTraps OBJECT IDENTIFIER ::= { usrUserMan 2 }


-- Begin managed object definitions here...

	usrUserManRadiusIP	OBJECT-TYPE
	SYNTAX	IpAddress
	ACCESS	read-write
	STATUS	mandatory
	DESCRIPTION
		"The IP address of the RADIUS server"
	--CONFIGURABLE
	::= { usrUserManGroup 1 }

	usrUserManRadiusAltIP	OBJECT-TYPE
	SYNTAX	IpAddress
	ACCESS	read-write
	STATUS	mandatory
	DESCRIPTION
		"The alternate IP address of the RADIUS server"
	--CONFIGURABLE
	::= { usrUserManGroup 2 }

	usrUserManRadiusAcctIP	OBJECT-TYPE
	SYNTAX	IpAddress
	ACCESS	read-write
	STATUS	mandatory
	DESCRIPTION
		"The IP address of the RADIUS accounting server"
	--CONFIGURABLE
	::= { usrUserManGroup 3 }

	usrUserManRadiusAcctAltIP	OBJECT-TYPE
	SYNTAX	IpAddress
	ACCESS	read-write
	STATUS	mandatory
	DESCRIPTION
		"The IP address of the RADIUS alternate accounting
			server"
	--CONFIGURABLE
	::= { usrUserManGroup 4 }
	
	usrUserManLocalAuthSuccesses	OBJECT-TYPE
	SYNTAX	Counter
	ACCESS	read-only
	STATUS	mandatory
	DESCRIPTION
		"The number of local authentication successes"
	::= { usrUserManGroup 5 }

	usrUserManLocalAuthFails	OBJECT-TYPE
	SYNTAX	Counter
	ACCESS	read-only
	STATUS	mandatory
	DESCRIPTION
		"The number of local authentication failures"
	::= { usrUserManGroup 6 }

	usrUserManRadiusAuthSuccesses	OBJECT-TYPE
	SYNTAX	Counter
	ACCESS	read-only
	STATUS	mandatory
	DESCRIPTION
		"The number of radius authentication successes"
	::= { usrUserManGroup 7 }

	usrUserManRadiusAuthFails	OBJECT-TYPE
	SYNTAX	Counter
	ACCESS	read-only
	STATUS	mandatory
	DESCRIPTION
		"The number of radius authentication failures"
	::= { usrUserManGroup 8 }

	usrUserManLocalUsers	OBJECT-TYPE
	SYNTAX	Counter
	ACCESS	read-only
	STATUS	mandatory
	DESCRIPTION
		"The number of local users"
	::= { usrUserManGroup 9 }

	usrUserManActiveUsers	OBJECT-TYPE
	SYNTAX	Counter
	ACCESS	read-only
	STATUS	mandatory
	DESCRIPTION
		"The number of active users"
	::= { usrUserManGroup 10 }

	usrUserManRetransmissions	OBJECT-TYPE
	SYNTAX	Counter
	ACCESS	read-only
	STATUS	mandatory
	DESCRIPTION
		"The number of udp packet retransmissions"
	::= { usrUserManGroup 11 }

	usrUserManUdpReceives	OBJECT-TYPE
	SYNTAX	Counter
	ACCESS	read-only
	STATUS	mandatory
	DESCRIPTION
		"The number of udp packets received"
	::= { usrUserManGroup 12 }

	usrUserManRadiusRetrans	OBJECT-TYPE
	SYNTAX	INTEGER (0..100)
	ACCESS	read-write
	STATUS 	mandatory
	DESCRIPTION
		"The maximum number of times a timeout will occur when
			communicating with radius"	
	--CONFIGURABLE
	::= { usrUserManGroup 13 }

	usrUserManRadiusTimeout	OBJECT-TYPE
	SYNTAX	INTEGER (1..60)
	ACCESS	read-write
	STATUS	mandatory
	DESCRIPTION
		"The maximum amount of time in seconds we will wait
			for a RADIUS response before retransmitting"
	--CONFIGURABLE
	::= { usrUserManGroup 14 }

	usrUserManAcctRetrans	OBJECT-TYPE
	SYNTAX	INTEGER (0..2147483647)
	ACCESS	read-write
	STATUS 	mandatory
	DESCRIPTION
		"The maximum number of times a timeout will occur when
			communicating with radius accounting server"
	--CONFIGURABLE
	::= { usrUserManGroup 15 }

	usrUserManAcctTimeout	OBJECT-TYPE
	SYNTAX	INTEGER (1..60)
	ACCESS	read-write
	STATUS	mandatory
	DESCRIPTION
		"The maximum amount of time in seconds we will wait
			for a RADIUS accounting response before retransmitting"
	--CONFIGURABLE
	::= { usrUserManGroup 16 }

	usrUserManLocalAuth	OBJECT-TYPE
	SYNTAX	INTEGER {
			enabled(1),
			disabled(2)
		} 
	ACCESS	read-write
	STATUS	mandatory
	DESCRIPTION
		"Is local authentication on or off"
	--CONFIGURABLE
	::= { usrUserManGroup 17 }

	usrUserManAcct	OBJECT-TYPE
	SYNTAX	INTEGER {
			enabled(1),
			disabled(2)
		} 
	ACCESS	read-write
	STATUS	mandatory
	DESCRIPTION
		"Is accounting on or off"
	--CONFIGURABLE
	::= { usrUserManGroup 18 }

	usrUserManAcctServers	OBJECT-TYPE
	SYNTAX	INTEGER {
			one(1),
			both(2)
		} 
	ACCESS	read-write
	STATUS	mandatory
	DESCRIPTION
		"Do we want to consider both servers specified as primary"
	-- CONFIGURABLE
	::= { usrUserManGroup 19 }

	usrUserManRadiusAuth	OBJECT-TYPE
	SYNTAX	INTEGER {
			enabled(1),
			disabled(2)
		}
	ACCESS	read-write
	STATUS	mandatory
	DESCRIPTION
		"Is radius authentication on or off"
	--CONFIGURABLE
	::= { usrUserManGroup 20 }
	
	usrUserManStartAccountTime	OBJECT-TYPE
	SYNTAX	INTEGER	{
			connectionTime(1),
			authenticationTime(2)
			}
	ACCESS	read-write
	STATUS	mandatory
	DESCRIPTION
		"When do we want to account from"
	--CONFIGURABLE
	::= { usrUserManGroup 21 }

	usrUserManSnmpAccess	OBJECT-TYPE
	SYNTAX	INTEGER	{
			enable(1),
			disable(2)
			}
	ACCESS	read-write
	STATUS	mandatory
	DESCRIPTION
		"Do we allow snmp to set our user table"
	--CONFIGURABLE
	::= { usrUserManGroup 22 }

	usrUserManSaveUsers 	OBJECT-TYPE
	SYNTAX	INTEGER	{
			normal(0),
			save(2)
			}
	ACCESS	not-accessible
	STATUS	mandatory
	DESCRIPTION
		"If we hit the save flag the users will be saved to flash"
	::= { usrUserManGroup 23 }

	usrUserManRadiusSecret OBJECT-TYPE
	SYNTAX	OCTET STRING (SIZE (1..15))
	ACCESS	write-only
	STATUS	mandatory
	DESCRIPTION
		"The shared secret between the RADIUS server and pilgrim"
	--CONFIGURABLE
	::= { usrUserManGroup 24 }

-- User managers table definition

	usrUserManTable	OBJECT-TYPE
	SYNTAX SEQUENCE OF UumEntry
	ACCESS	not-accessible
	STATUS	mandatory
	DESCRIPTION
		""
	::= { usrUserManGroup 25 }
 
	uumEntry	OBJECT-TYPE
	SYNTAX	UumEntry
	ACCESS	not-accessible
	STATUS	mandatory
	DESCRIPTION
		""
	INDEX	{ uumUserName }
	::= { usrUserManTable 1 }

	UumEntry ::=
	SEQUENCE {
	uumUserName
		UsrUserName,
	uumStatus
		INTEGER,
	uumUserPassword
		OCTET STRING,
	uumServiceType
		INTEGER,
	uumFramedProtocol
		INTEGER,
	uumFramedIpAddress
		IpAddress,
	uumFramedIpNetmask
		IpAddress,
	uumFramedRouting
		INTEGER,
	uumFilterIdInput
		OCTET STRING,
	uumFramedMtu
		INTEGER,
	uumFramedCompression
		INTEGER,
	uumLoginIpHost
		IpAddress,
	uumLoginService
		INTEGER,
	uumLoginPort
		INTEGER,
	uumReplyMessage
		OCTET STRING,
	uumCallbackNumberOne
		OCTET STRING,
	uumExpiration
		OCTET STRING,
	uumFramedRoute
		OCTET STRING,
	uumFramedIpxNetwork
		OCTET STRING,
	uumSessionTimeout
		INTEGER,
	uumIdleTimeout
		INTEGER,
	uumBearerCapabilities
		INTEGER,
	uumSpeedOfConnection
		INTEGER,
	uumMaxChannels
		INTEGER,
	uumChannelExpansion
		INTEGER,
	uumChannelDecrement
		INTEGER,
	uumExpansionAlgorithm
		INTEGER,
	uumCompressionAlgorithm
		INTEGER,
	uumReceiveAccMap
		INTEGER,
	uumTransmitAccMap
		INTEGER,
	uumWhereCompression
		INTEGER,
	uumCompressionResetMode
		INTEGER,
	uumMinCompressionSize
		INTEGER,
	uumLocationType
		INTEGER,
	uumIp
		INTEGER,
	uumIpx
		INTEGER,
	uumFilterZones
		INTEGER,
	uumFilterIdOutput
		OCTET STRING,
	uumAppletalk
		INTEGER,
	uumBridging
		INTEGER,
	uumSpoofing
		INTEGER,
	uumHostType
		INTEGER,
	uumSendName
		OCTET STRING,
	uumSendPassword
		OCTET STRING,
	uumStartTime
		OCTET STRING,
	uumEndTime
		OCTET STRING,
	uumSendScript1
		OCTET STRING,
	uumReplyScript1
		OCTET STRING,
	uumSendScript2
		OCTET STRING,
	uumReplyScript2
		OCTET STRING,
	uumSendScript3
		OCTET STRING,
	uumReplyScript3
		OCTET STRING,
	uumSendScript4
		OCTET STRING,
	uumReplyScript4
		OCTET STRING,
	uumSendScript5
		OCTET STRING,
	uumReplyScript5
		OCTET STRING,
	uumSendScript6
		OCTET STRING,
	uumReplyScript6
		OCTET STRING,
	uumTerminalType
		OCTET STRING,
	uumAppletalkNetworkRange
		OCTET STRING,
	uumLocalIpAddress
		IpAddress,
	uumRoutingProtocol
		INTEGER,   -- deprecated
	uumCallbackNumberTwo
		OCTET STRING,
	uumModemGroup	
		OCTET STRING,
	uumIpxRouting
		INTEGER,
	uumIpxWan
		INTEGER,
	uumIpRipSendDefault
		INTEGER,
	uumIpRipSendRoutes
		INTEGER,
	uumIpRipSendSubnets
		INTEGER,
	uumIpRipAcceptDefault
		INTEGER,
	uumIpRipSplitHorizon
		INTEGER,
	uumIpRipPoisonReverse
		INTEGER,
	uumIpRipFlashUpdate
		INTEGER,
	uumIpRipSimpleAuth
		INTEGER,
	uumIpRipV1Send
		INTEGER,
	uumIpRipV1Receive
		INTEGER,
	uumIpRipV2Receive
		INTEGER,
	uumIpRipSilent
		INTEGER,
	uumSimpleAuthPassword
		OCTET STRING,
	uumIpDefaultRouteOption
		INTEGER,
	uumIpRoutingRipV1
		INTEGER,
	uumIpRoutingRipV2
		INTEGER,
	uumIpRoutingOspf
		INTEGER,
	uumOspfAddresslessIfIndex
		INTEGER,       
	uumLoginHostName
		OCTET STRING,
	uumIgmpInterfaceQueryInterval
		INTEGER,
	uumIgmpInterfaceQueryMaxResponseTime
		INTEGER,
	uumIgmpInterfaceVersion
		INTEGER,
	uumIgmpInterfaceRobustness
		INTEGER,
	uumIgmpInterfaceStatus
		INTEGER,
	uumIgmpInterfaceMcastFwdEnabled
		INTEGER,
	uumIpxRipUpdate
		INTEGER,
	uumIpxRipAgeMultiplier
		INTEGER,
	uumIpxSapUpdate
		INTEGER,
	uumIpxSapAgeMultiplier
		INTEGER,
	uumEncryptionAlgorithm
		INTEGER,
	uumTunnelType
		INTEGER,
	uumTunnelMediumType
		INTEGER,
	uumTunnelClientEndpoint
		OCTET STRING,
	uumTunnelServerEndpoint
		OCTET STRING,
	uumTunnelPassword
		OCTET STRING,
	uumTunnelPrivateGroupID
		OCTET STRING,
	uumTunnelSecurity
		INTEGER,
	uumPrimaryDNSServer
        IpAddress,
    uumSecondaryDNSServer
        IpAddress,
	uumUserTapStatus
		INTEGER,
	uumUserTapFormat
		INTEGER,
	uumUserTapOutput
		INTEGER,
	uumUserTapFacility
		INTEGER,
	uumUserTapLoglevel
		INTEGER,
	uumUserTapAddress
		IpAddress,
	uumMulticastProxy
		INTEGER,
	uumNasIpAddress
		IpAddress,
	uumNasPort
		INTEGER,
	uumFramedCallbackId
		INTEGER,
	uumState
	 	OCTET STRING,	
	uumClass
	 	OCTET STRING,	
	uumCalledStationId
	 	OCTET STRING,	
	uumCallingStationId
	 	OCTET STRING,	
	uumNasIdentifier
	 	OCTET STRING,
	uumCipIfName
	 	OCTET STRING,
	uumPPPLocalIpAddress
		IpAddress,
	uumPPPRemoteIpAddress
		IpAddress,
	uumSessionvars
		IpAddress,
	uumChatScriptName
	        OCTET STRING,
	uumPortLimit
		INTEGER,
        uumPppSourceIpFilter   
                INTEGER,
        uumCallbackType
                INTEGER,
        uumIsdnDataCallType
                INTEGER,
        uumDNISReAuth
                INTEGER,
        uumReChapTimeout
                INTEGER,
        uumNextHopGateway
                IpAddress,
        uumLocalTcpPort
		INTEGER,
	 uumConnectionvars
		IpAddress,
	uumShowConnVar
		INTEGER,
	uumSpecialXonXoff
		INTEGER,
	uumTelnetOptions
		INTEGER,
	uumMlPPPFragThreshold
		INTEGER,
	uumVPNName
		OCTET STRING,
	uumVPNID
		INTEGER,
	uumVPNGateway
		IpAddress,
        uumTrafficThreshold
		INTEGER,
	uumTunnelAssignmentId
		OCTET STRING,
	uumKeepAliveInterval
		INTEGER,
    uumTunnelClientAuthId
		OCTET STRING 
	}

	uumUserName	OBJECT-TYPE
	SYNTAX	UsrUserName
	ACCESS	not-accessible
	STATUS	mandatory
	DESCRIPTION
		"The users name"
	::= { uumEntry 1 }
		
	uumStatus	OBJECT-TYPE
	SYNTAX	INTEGER {
		delete(1),
		inactive(2),
		active(3),
		enabled(4),
		disabled(5),
		active-disabled(6)
		}
	ACCESS	read-write
	STATUS	mandatory
	DESCRIPTION
		"The status field for delete"
	--CONFIGURABLE
	::= { uumEntry 2 }

	uumUserPassword	OBJECT-TYPE
	SYNTAX	OCTET STRING (SIZE (1..15))
	ACCESS	write-only
	STATUS	mandatory
	DESCRIPTION
		"The users password"
	--CONFIGURABLE
	::= { uumEntry 3 }

	uumServiceType	OBJECT-TYPE
	SYNTAX	INTEGER 
	ACCESS	read-write
	STATUS	mandatory
	DESCRIPTION
		"The bitmap indicating one or more types of user:
	login 0x1, framed 0x2, callback 0x4, dial-out 0x8,
	administrative 0x10"
	--CONFIGURABLE
	::= { uumEntry 4 }

	uumFramedProtocol	OBJECT-TYPE
	SYNTAX	INTEGER {
		ppp(1),
		slip(2),
		arap(3),
		frame-relay(4)
		}
	ACCESS	read-write
	STATUS	mandatory
	DESCRIPTION
		"The framed users protocol"
	--CONFIGURABLE
	::= { uumEntry 5 }

	uumFramedIpAddress	OBJECT-TYPE
	SYNTAX	IpAddress
	ACCESS	read-write
	STATUS	mandatory
	DESCRIPTION
		"The IP destination for the framed user"
	--CONFIGURABLE
	::= { uumEntry 6 }

	uumFramedIpNetmask	OBJECT-TYPE
	SYNTAX	IpAddress
	ACCESS	read-write
	STATUS	mandatory
	DESCRIPTION
		"The destinations netmask"
	--CONFIGURABLE
	::= { uumEntry 7 }

	uumFramedRouting	OBJECT-TYPE
	SYNTAX	INTEGER {
		none(0),
		broadcastRoutingPackets(1),
		listenForRoutingPackets(2),
		broadcastAndListen(3)
		}
	ACCESS	read-write
	STATUS	mandatory
	DESCRIPTION
		"The routing defined for a framed user"
	--CONFIGURABLE
	::= { uumEntry 8 }

	uumFilterIdInput	OBJECT-TYPE
	SYNTAX	OCTET STRING (SIZE (0..240))
	ACCESS	read-write
	STATUS	mandatory
	DESCRIPTION
		"The input or output filter defined for the user"
	--CONFIGURABLE
	::= { uumEntry 9 }

	uumFramedMtu	OBJECT-TYPE
	SYNTAX	INTEGER (0..8192)
	ACCESS	read-write
	STATUS	mandatory
	DESCRIPTION
		"The framed maximum transmission unit"
	--CONFIGURABLE
	::= { uumEntry 10 }

	uumFramedCompression	OBJECT-TYPE
	SYNTAX	INTEGER {
		none(0),
		tcpIpCompression(1),
		ipxCompression(2) -- deprecated
		}
	ACCESS	read-write
	STATUS	mandatory
	DESCRIPTION
		"The compression being used for the framed user"
	--CONFIGURABLE
	::= { uumEntry 11 }

	uumLoginIpHost	OBJECT-TYPE
	SYNTAX	IpAddress
	ACCESS	read-write
	STATUS	mandatory
	DESCRIPTION
		"The IP destination for the login user"
	--CONFIGURABLE
	::= { uumEntry 12 }

	uumLoginService	OBJECT-TYPE
	SYNTAX	INTEGER {
		telnet(0),
		rlogin(1),
		tcp(2),
		lat(4),
		ping(1000)
		}
	ACCESS	read-write
	STATUS	mandatory
	DESCRIPTION
		"The login user's protocol"
	--CONFIGURABLE
	::= { uumEntry 13 }

	uumLoginPort	OBJECT-TYPE
	SYNTAX	INTEGER (0..65535)
	ACCESS	read-write
	STATUS	mandatory
	DESCRIPTION
		"The tcp port the user will use"
	--CONFIGURABLE
	::= { uumEntry 14 }

	uumReplyMessage	OBJECT-TYPE
	SYNTAX	OCTET STRING (SIZE (0..240))
	ACCESS	read-write
	STATUS	mandatory
	DESCRIPTION
		"The message to be displayed to the user"
	--CONFIGURABLE
	::= { uumEntry 15 }

	uumCallbackNumberOne	OBJECT-TYPE
	SYNTAX	OCTET STRING (SIZE (0..240))
	ACCESS	read-write
	STATUS 	mandatory
	DESCRIPTION
		"The first phone number configured for this user"
	--CONFIGURABLE
	::= { uumEntry 16 }

	uumExpiration	OBJECT-TYPE
	SYNTAX	OCTET STRING (SIZE (12))
	ACCESS	read-write
	STATUS	mandatory
	DESCRIPTION
		"The users expiration date"
	--CONFIGURABLE
	::= { uumEntry 17}

	uumFramedRoute	OBJECT-TYPE
	SYNTAX	OCTET STRING (SIZE (0..240))
	ACCESS	not-accessible
	STATUS	mandatory
	DESCRIPTION 
		"The framed route for the user"
	::= { uumEntry 18 }

	uumFramedIpxNetwork	OBJECT-TYPE
	SYNTAX	OCTET STRING (SIZE (4))
	ACCESS	read-write
	STATUS	mandatory
	DESCRIPTION
		"The ipx network defined for the user"
	--CONFIGURABLE
	::= { uumEntry 19 }

	uumSessionTimeout	OBJECT-TYPE
	SYNTAX	INTEGER (0..86400)
	ACCESS	read-write
	STATUS	mandatory
	DESCRIPTION
		"The amount of time in seconds before time out"
	--CONFIGURABLE
	::= { uumEntry 20 }

	uumIdleTimeout	OBJECT-TYPE
	SYNTAX	INTEGER (0..86400)
	ACCESS	read-write
	STATUS	mandatory
	DESCRIPTION
		"The amount of idle time in seconds before time out"
	--CONFIGURABLE
	::= { uumEntry 21 }

	uumBearerCapabilities	OBJECT-TYPE
	SYNTAX	INTEGER {
		digital(1),
		analog(2)
		}
	ACCESS	not-accessible
	STATUS	mandatory
	DESCRIPTION
		"The type of transmission"
	--CONFIGURABLE
	::= { uumEntry 22 }

	uumSpeedOfConnection	OBJECT-TYPE
	SYNTAX	INTEGER {
		auto(1),
		fifty-six-k(2),
		sixty-four-k(3),
		voice(4)
		}
	ACCESS	read-write
	STATUS	mandatory
	DESCRIPTION
		"The speed of the connection"
	--CONFIGURABLE
	::= { uumEntry 23 }		
		
	uumMaxChannels	OBJECT-TYPE
	SYNTAX	INTEGER (0..16)
	ACCESS	read-write
	STATUS	mandatory
	DESCRIPTION
		"The maximum number of channels that may be used"
	--CONFIGURABLE
	::= { uumEntry 24 }
 
	uumChannelExpansion	OBJECT-TYPE
	SYNTAX	INTEGER (0..100)
	ACCESS	read-write
	STATUS	mandatory
	DESCRIPTION
		"The percentage for channel expansion"
	--CONFIGURABLE
	::= { uumEntry 25 }

	uumChannelDecrement	OBJECT-TYPE
	SYNTAX	INTEGER (0..100)
	ACCESS	read-write
	STATUS	mandatory
	DESCRIPTION
		"The percentage for channel decrement"
	--CONFIGURABLE
	::= { uumEntry 26 }

	uumExpansionAlgorithm	OBJECT-TYPE
	SYNTAX	INTEGER {
		constant(1),
		linear(2)
		}
	ACCESS	read-write
	STATUS	mandatory
	DESCRIPTION
		"The expansion algorithm being used"
	--CONFIGURABLE
	::= { uumEntry 27 }	
		
	uumCompressionAlgorithm	OBJECT-TYPE
	SYNTAX	INTEGER {
		none(0),
		stac(1),
		ascend(2),
		microsoft(3),
		auto(4), 
		deflate(5)
		}
	ACCESS	read-write
	STATUS	mandatory
	DESCRIPTION
		"The compression algorithm to be used"
	--CONFIGURABLE
	::= { uumEntry 28 }

	uumReceiveAccMap	OBJECT-TYPE
	SYNTAX	INTEGER
	ACCESS	read-write
	STATUS	mandatory
	DESCRIPTION
		"The receive acc mapping"
	--CONFIGURABLE
	::= { uumEntry 29 }

	uumTransmitAccMap	OBJECT-TYPE
	SYNTAX	INTEGER
	ACCESS	read-write
	STATUS	mandatory
	DESCRIPTION
		"The transmit acc mapping"
	--CONFIGURABLE
	::= { uumEntry 30 }
	
	uumWhereCompression	OBJECT-TYPE
	SYNTAX	INTEGER {
		link(1),
		bundle(2)
		}	
	ACCESS	not-accessible
	STATUS	obsolete
	DESCRIPTION
		"The area where compression should be done"
	-- CONFIGURABLE
	::= { uumEntry 31 }

	uumCompressionResetMode	OBJECT-TYPE
	SYNTAX	INTEGER {
		auto(1),
		resetEveryPacket(2),
		resetEveryError(3)
		}
	ACCESS	read-write
	STATUS	mandatory
	DESCRIPTION
		"The mode that the compression should be reset in"
	--CONFIGURABLE
	::= { uumEntry 32 }

	uumMinCompressionSize	OBJECT-TYPE
	SYNTAX	INTEGER (0..2048) 
	ACCESS	read-write
	STATUS	mandatory
	DESCRIPTION
		"The minimum size for compression"
	--CONFIGURABLE
	::= { uumEntry 33 }

	uumLocationType	OBJECT-TYPE
	SYNTAX	INTEGER {
		continuous(1),
		onDemand(2),
		manual(3),
		timed(4)
		}
	ACCESS	read-write
	STATUS	mandatory
	DESCRIPTION
		"The type of location user"
	--CONFIGURABLE
	::= { uumEntry 34 }

	uumIp	OBJECT-TYPE
	SYNTAX	INTEGER {
		enabled(1),
		disabled(2)
		}
	ACCESS	read-write
	STATUS	mandatory
	DESCRIPTION
		"Ip enabled or disabled"
	--CONFIGURABLE
	::= { uumEntry 35 }

	uumIpx	OBJECT-TYPE
	SYNTAX	INTEGER {
		enabled(1),
		disabled(2)
		}
	ACCESS	read-write
	STATUS	mandatory
	DESCRIPTION
		"Ipx enabled or disabled"
	--CONFIGURABLE
	::= { uumEntry 36 }

	uumFilterZones	OBJECT-TYPE
	SYNTAX	INTEGER {
		enabled(1),
		disabled(2)
		}
	ACCESS	read-write
	STATUS	mandatory
	DESCRIPTION
		"Arap needed to define filter zones"
	--CONFIGURABLE
	::= { uumEntry 37 }	

	uumFilterIdOutput	OBJECT-TYPE
	SYNTAX	OCTET STRING (SIZE (0..240))
	ACCESS	read-write
	STATUS	mandatory
	DESCRIPTION
		"The output filter defined for the user"
	--CONFIGURABLE
	::= { uumEntry 38 }

	uumAppletalk	OBJECT-TYPE
	SYNTAX	INTEGER {
		enabled(1),
		disabled(2)
		}
	ACCESS	read-write
	STATUS	mandatory
	DESCRIPTION
		"Appletalk enabled or disabled"
	--CONFIGURABLE
	::= { uumEntry 39 }

	uumBridging	OBJECT-TYPE
	SYNTAX	INTEGER {
		enabled(1),
		disabled(2)
		}
	ACCESS	read-write
	STATUS	mandatory
	DESCRIPTION
		"Bridging enabled or disabled"
	--CONFIGURABLE
	::= { uumEntry 40 }

	uumSpoofing	OBJECT-TYPE
	SYNTAX	INTEGER {
		enabled(1),
		disabled(2)
		}
	ACCESS	read-write
	STATUS	mandatory
	DESCRIPTION
		"Ipx spoofing enabled or disabled"
	--CONFIGURABLE
	::= { uumEntry 41 }

	uumHostType	OBJECT-TYPE
	SYNTAX	INTEGER {
		prompt(1),
		default(2),
		specified(3)
		}
	ACCESS	not-accessible
	STATUS	obsolete
	DESCRIPTION
		"The means for specifying a host for this user"
	-- CONFIGURABLE
	::= { uumEntry 42 }

	uumSendName	OBJECT-TYPE
	SYNTAX	OCTET STRING (SIZE (1..240))
	ACCESS	not-accessible
	STATUS	mandatory
	DESCRIPTION
		"Name we use when challenged for authentication"
	--CONFIGURABLE
	::= { uumEntry 43 }

	uumSendPassword	OBJECT-TYPE
	SYNTAX	OCTET STRING (SIZE (1..240))
	ACCESS	write-only
	STATUS	mandatory
	DESCRIPTION
		"Password we use when challenged for authentication"
	--CONFIGURABLE
	::= { uumEntry 44 }
				
	uumStartTime	OBJECT-TYPE
	SYNTAX	OCTET STRING (SIZE (12))
	ACCESS	read-write
	STATUS	mandatory
	DESCRIPTION
		"Daily time we start timed location"
	--CONFIGURABLE
	::= { uumEntry 45 }

	uumEndTime	OBJECT-TYPE
	SYNTAX	OCTET STRING (SIZE (12))
	ACCESS	read-write
	STATUS	mandatory
	DESCRIPTION
		"Daily time we stop timed location"
	--CONFIGURABLE
	::= { uumEntry 46 }

	uumSendScript1	OBJECT-TYPE
	SYNTAX	OCTET STRING (SIZE (0..240))
	ACCESS	read-write
	STATUS	mandatory
	DESCRIPTION
		"The first send script for this dial-out user"
	--CONFIGURABLE
	::= { uumEntry 47 }

	uumReplyScript1	OBJECT-TYPE
	SYNTAX	OCTET STRING (SIZE (0..240))
	ACCESS	read-write
	STATUS	mandatory
	DESCRIPTION
		"The first reply script for this dial-out user"
	--CONFIGURABLE
	::= { uumEntry 48 }

	uumSendScript2	OBJECT-TYPE
	SYNTAX	OCTET STRING (SIZE (0..240))
	ACCESS	read-write
	STATUS	mandatory
	DESCRIPTION
		"The second send script for this dial-out user"
	--CONFIGURABLE
	::= { uumEntry 49 }

	uumReplyScript2	OBJECT-TYPE
	SYNTAX	OCTET STRING (SIZE (0..240))
	ACCESS	read-write
	STATUS	mandatory
	DESCRIPTION
		"The second reply script for this dial-out user"
	--CONFIGURABLE
	::= { uumEntry 50 }

	uumSendScript3	OBJECT-TYPE
	SYNTAX	OCTET STRING (SIZE (0..240))
	ACCESS	read-write
	STATUS	mandatory
	DESCRIPTION
		"The third send script for this dial-out user"
	--CONFIGURABLE
	::= { uumEntry 51 }

	uumReplyScript3	OBJECT-TYPE
	SYNTAX	OCTET STRING (SIZE (0..240))
	ACCESS	read-write
	STATUS	mandatory
	DESCRIPTION
		"The third reply script for this dial-out user"
	--CONFIGURABLE
	::= { uumEntry 52 }

	uumSendScript4	OBJECT-TYPE
	SYNTAX	OCTET STRING (SIZE (0..240))
	ACCESS	read-write
	STATUS	mandatory
	DESCRIPTION
		"The fourth send script for this dial-out user"
	--CONFIGURABLE
	::= { uumEntry 53 }

	uumReplyScript4	OBJECT-TYPE
	SYNTAX	OCTET STRING (SIZE (0..240))
	ACCESS	read-write
	STATUS	mandatory
	DESCRIPTION
		"The fourth reply script for this dial-out user"
	--CONFIGURABLE
	::= { uumEntry 54 }

	uumSendScript5	OBJECT-TYPE
	SYNTAX	OCTET STRING (SIZE (0..240))
	ACCESS	read-write
	STATUS	mandatory
	DESCRIPTION
		"The fifth send script for this dial-out user"
	--CONFIGURABLE
	::= { uumEntry 55 }

	uumReplyScript5	OBJECT-TYPE
	SYNTAX	OCTET STRING (SIZE (0..240))
	ACCESS	read-write
	STATUS	mandatory
	DESCRIPTION
		"The fifth reply script for this dial-out user"
	--CONFIGURABLE
	::= { uumEntry 56 }

	uumSendScript6	OBJECT-TYPE
	SYNTAX	OCTET STRING (SIZE (0..240))
	ACCESS	read-write
	STATUS	mandatory
	DESCRIPTION
		"The sixth send script for this dial-out user"
	--CONFIGURABLE
	::= { uumEntry 57 }

	uumReplyScript6	OBJECT-TYPE
	SYNTAX	OCTET STRING (SIZE (0..240))
	ACCESS	read-write
	STATUS	mandatory
	DESCRIPTION
		"The sixth reply script for this dial-out user"
	--CONFIGURABLE
	::= { uumEntry 58 }

	uumTerminalType	OBJECT-TYPE
	SYNTAX	OCTET STRING (SIZE (0..240))
	ACCESS	read-write
	STATUS	mandatory
	DESCRIPTION
		"The terminal type for the user"
	--CONFIGURABLE
	::= { uumEntry 59 }

	uumAppletalkNetworkRange	OBJECT-TYPE
	SYNTAX	OCTET STRING (SIZE (4))
	ACCESS	read-write
	STATUS	mandatory
	DESCRIPTION
		"The appletalk network range for the user"
	--CONFIGURABLE
	::= { uumEntry 60 }

	uumLocalIpAddress	OBJECT-TYPE
	SYNTAX	IpAddress
	ACCESS	read-write
	STATUS	mandatory
	DESCRIPTION
		"The local ip address configured for a dial-out user"
	--CONFIGURABLE
	::= { uumEntry 61 }

	uumRoutingProtocol	OBJECT-TYPE
	SYNTAX	INTEGER {
		rip1(1),
		rip2(2)
		}
	ACCESS	read-write
	STATUS	deprecated
	DESCRIPTION
		"The routing protocol configured for a user"
	-- CONFIGURABLE
	::= { uumEntry 62 }
	
        uumCallbackNumberTwo	OBJECT-TYPE
	SYNTAX	OCTET STRING (SIZE (0..240))
	ACCESS	read-write
	STATUS 	mandatory
	DESCRIPTION
		"The second phone number configured for this user"
	--CONFIGURABLE
	::= { uumEntry 63 }
	
	uumModemGroup	OBJECT-TYPE
	SYNTAX	OCTET STRING (SIZE (0..240))
	ACCESS	read-write
	STATUS	mandatory
	DESCRIPTION
		"The modem group string for the user"
	--CONFIGURABLE
	::= { uumEntry 64 }

	uumIpxRouting	OBJECT-TYPE
	SYNTAX	INTEGER {
		none(0),
		send(1),
		listen(2),
		respond(3),
		all(4)
		}
	ACCESS	read-write
	STATUS	mandatory
	DESCRIPTION
		"The ipx routing defined for a framed user"
	--CONFIGURABLE
	::= { uumEntry 65 }

	uumIpxWan	OBJECT-TYPE
	SYNTAX	INTEGER {
		enable(1),
		disable(2)
		}
	ACCESS	read-write
	STATUS	mandatory
	DESCRIPTION
		"Is ipx wan enabled or disabled for the user"
	--CONFIGURABLE
	::= { uumEntry 66 }

	uumIpRipSendDefault	OBJECT-TYPE
	SYNTAX	INTEGER {
		enable(1),
		disable(2)
		}
	ACCESS	read-write
	STATUS	mandatory
	DESCRIPTION
		"IP RIP flag"
	--CONFIGURABLE
	::= { uumEntry 67 }

	uumIpRipSendRoutes	OBJECT-TYPE
	SYNTAX	INTEGER {
		enable(1),
		disable(2)
		}
	ACCESS	read-write
	STATUS	mandatory
	DESCRIPTION
		"IP RIP flag"
	--CONFIGURABLE
	::= { uumEntry 68 }

	uumIpRipSendSubnets	OBJECT-TYPE
	SYNTAX	INTEGER {
		enable(1),
		disable(2)
		}
	ACCESS	read-write
	STATUS	mandatory
	DESCRIPTION
		"IP RIP flag"
	--CONFIGURABLE
	::= { uumEntry 69 }

	uumIpRipAcceptDefault	OBJECT-TYPE
	SYNTAX	INTEGER {
		enable(1),
		disable(2)
		}
	ACCESS	read-write
	STATUS	mandatory
	DESCRIPTION
		"IP RIP flag"
	--CONFIGURABLE
	::= { uumEntry 70 }

	uumIpRipSplitHorizon	OBJECT-TYPE
	SYNTAX	INTEGER {
		enable(1),
		disable(2)
		}
	ACCESS	read-write
	STATUS	mandatory
	DESCRIPTION
		"IP RIP flag"
	--CONFIGURABLE
	::= { uumEntry 71 }
	
	uumIpRipPoisonReverse	OBJECT-TYPE
	SYNTAX	INTEGER {
		enable(1),
		disable(2)
		}
	ACCESS	read-write
	STATUS	mandatory
	DESCRIPTION
		"IP RIP flag"
	--CONFIGURABLE
	::= { uumEntry 72 }

	uumIpRipFlashUpdate	OBJECT-TYPE
	SYNTAX	INTEGER {
		enable(1),
		disable(2)
		}
	ACCESS	read-write
	STATUS	mandatory
	DESCRIPTION
		"IP RIP flag"
	--CONFIGURABLE
	::= { uumEntry 73 }

	uumIpRipSimpleAuth	OBJECT-TYPE
	SYNTAX	INTEGER {
		enable(1),
		disable(2)
		}
	ACCESS	read-only
	STATUS	mandatory
	DESCRIPTION
		"IP RIP flag"
	::= { uumEntry 74 }

	uumIpRipV1Send	OBJECT-TYPE
	SYNTAX	INTEGER {
		enable(1),
		disable(2)
		}
	ACCESS	read-write
	STATUS	mandatory
	DESCRIPTION
		"IP RIP flag"
	--CONFIGURABLE
	::= { uumEntry 75 }

	uumIpRipV1Receive	OBJECT-TYPE
	SYNTAX	INTEGER {
		enable(1),
		disable(2)
		}
	ACCESS	read-write
	STATUS	mandatory
	DESCRIPTION
		"IP RIP flag"
	--CONFIGURABLE
	::= { uumEntry 76 }

	uumIpRipV2Receive	OBJECT-TYPE
	SYNTAX	INTEGER {
		enable(1),
		disable(2)
		}
	ACCESS	read-write
	STATUS	mandatory
	DESCRIPTION
		"IP RIP flag"
	--CONFIGURABLE
	::= { uumEntry 77 }

	uumIpRipSilent	OBJECT-TYPE
	SYNTAX	INTEGER {
		enable(1),
		disable(2)
		}
	ACCESS	read-write
	STATUS	mandatory
	DESCRIPTION
		"IP RIP flag"
	--CONFIGURABLE
	::= { uumEntry 78 }

	uumSimpleAuthPassword	OBJECT-TYPE
	SYNTAX	OCTET STRING (SIZE (0..64))
	ACCESS	read-write
	STATUS	mandatory
	DESCRIPTION
		"The IP RIP simple authentication password"
	--CONFIGURABLE
	::= { uumEntry 79 }

	uumIpDefaultRouteOption	OBJECT-TYPE
	SYNTAX	INTEGER {
		enable(1),
		disable(2)
		}
	ACCESS	read-write
	STATUS	mandatory
	DESCRIPTION
		"If enable (1) a default route will be created using
                 the remote users IP address.  If disable (2) no such
                 route is created."
	--CONFIGURABLE
	::= { uumEntry 80 }


	uumLoginHostName	OBJECT-TYPE
	SYNTAX	OCTET STRING
	ACCESS	read-write
	STATUS	mandatory
	DESCRIPTION
		"The destination host name for the login user"
	--CONFIGURABLE
	::= { uumEntry 81 }

	uumIgmpInterfaceQueryInterval OBJECT-TYPE
	SYNTAX     INTEGER (1..65535)
	ACCESS read-write
	STATUS     mandatory
	DESCRIPTION
		"The frequency at which IGMP Host-Query packets are
		transmitted on this interface."
	DEFVAL     { 125 }
	--CONFIGURABLE
	::= { uumEntry 82 }
	
	uumIgmpInterfaceQueryMaxResponseTime OBJECT-TYPE
	SYNTAX     INTEGER (1..10)
	ACCESS read-write
	STATUS     mandatory
	DESCRIPTION
		"The maximum query response time advertised in IGMPv2
		queries on this interface.  Smaller values allow a router to
		prune groups faster."
	DEFVAL     { 10 }
	--CONFIGURABLE                                                    
	::= { uumEntry 83 }
	
	uumIgmpInterfaceRobustness OBJECT-TYPE
	SYNTAX     INTEGER (1..5)
	ACCESS read-write
	STATUS     mandatory
	DESCRIPTION
		"The Robustness Variable allows tuning for the expected
		packet loss on a subnet.  If a subnet is expected to be
		lousy, the Robustness Variable may be increased.  IGMP is
		robust to (Robustness Variable-1) packet losses."
	DEFVAL     { 2 }
	--CONFIGURABLE                                                    
	::= { uumEntry 84 }

	uumIgmpInterfaceVersion OBJECT-TYPE
	SYNTAX     INTEGER (1..2)
	ACCESS read-write
	STATUS     mandatory
	DESCRIPTION
		"The maximum query response time advertised in IGMPv2
		queries on this interface.  Smaller values allow a router to
		prune groups faster."
	DEFVAL     { 2 }
	--CONFIGURABLE                                                    
	::= { uumEntry 85 }

	uumIgmpInterfaceStatus OBJECT-TYPE
	SYNTAX	INTEGER {
		enabled(1),
		disabled(2)
		}
	ACCESS read-write
	STATUS     mandatory
	DESCRIPTION
		"If enabled, Multicast packets will be routed on this
		user's interface."
	DEFVAL	{ enabled }
	--CONFIGURABLE
	::= { uumEntry 86 }

	uumIgmpInterfaceMcastFwdEnabled OBJECT-TYPE
	SYNTAX	INTEGER {
		enabled(1),
		disabled(2)
		}
	ACCESS read-write                                                 
	STATUS     mandatory                                                 
	DESCRIPTION
		"If enabled Multicast packets will be forwarded on this
		user's interface."   
	DEFVAL    { enabled }
	--CONFIGURABLE                                                        
	::= { uumEntry 87 }                                        

	uumIpxRipUpdate	  OBJECT-TYPE
	SYNTAX  INTEGER (30..86400)
	ACCESS	read-write
	STATUS	mandatory
	DESCRIPTION
		"The IPX RIP update interval in seconds"
	DEFVAL	{ 60 }
	--CONFIGURABLE
	::= { uumEntry 88 }

	uumIpxRipAgeMultiplier	  OBJECT-TYPE
	SYNTAX  INTEGER(1..1080) 
	ACCESS	read-write
	STATUS	mandatory
	DESCRIPTION
		"The IPX RIP multiplier for information received in
		 periodic updates"
	DEFVAL	{ 4 }
	--CONFIGURABLE
	::= { uumEntry 89 }

	uumIpxSapUpdate	  OBJECT-TYPE
	SYNTAX  INTEGER(30..86400) 
	ACCESS	read-write
	STATUS	mandatory
	DESCRIPTION
		"The IPX SAP update interval in seconds"
	DEFVAL	{ 60 }
	--CONFIGURABLE
	::= { uumEntry 90 }

	uumIpxSapAgeMultiplier	  OBJECT-TYPE
	SYNTAX  INTEGER(1..1080) 
	ACCESS	read-write
	STATUS	mandatory
	DESCRIPTION
		"The IPX SAP multiplier for information received in
		 periodic updates"
	DEFVAL	{ 4 }
	--CONFIGURABLE
	::= { uumEntry 91 }
	
	uumEncryptionAlgorithm	OBJECT-TYPE
	SYNTAX	INTEGER {
		none(0),
		auto(1),
		microsoft40bit(2),
		microsoft128bit(3),
		required(4),
		microsoft56bit(5),
                bit40ornone(6),
                bit128ornone(7),
                bit56ornone(8),
                bit128orbit56(9),
                bit128orbit56ornone(10),
                bit128orbit40(11),
                bit128orbit40ornone(12),
                bit56orbit40(13),
                bit56orbit40ornone(14)
                }
	ACCESS	read-write
	STATUS	mandatory
	DESCRIPTION
		"The encryption algorithm to be used"
	--CONFIGURABLE
	::= { uumEntry 92 }

	uumTunnelType	  OBJECT-TYPE
	SYNTAX  INTEGER {
			none(0),
			pptp(1),
			l2f(2),
			l2tp(3),
			atmp(4),
			vtp(5),
			ah(6),
			ip-ip(7),
			min-ip-ip(8),
			esp(9),
			gre(10),
			dvs(11),
			ip-in-ip(12)
			}
	ACCESS	read-write
	STATUS	mandatory
	DESCRIPTION
		"The tunneling protocol to be used for this user"
	DEFVAL { pptp }
	--CONFIGURABLE
	::= { uumEntry 93 }
	
	uumTunnelMediumType	  OBJECT-TYPE
	SYNTAX  INTEGER {
			ipv4(1),
			ipv6(2),
			nsap(3),
			hdlc(4),
			bbn1822(5),
			e802(6),
			e163(7),
			e164(8),
			f69(9),
			x121(10),
			ipx(11),
			appletalk(12),
			decnetIV(13),
			banyanVines(14),
			e164NSAP(15)
			}
	ACCESS	read-write
	STATUS	mandatory
	DESCRIPTION
		"This object indicates which transport medium to use
		 when creating a tunnel for those protocols (such as
		 L2TP) that can operate over multiple transports."
	DEFVAL	{ ipv4 }
	--CONFIGURABLE
	::= { uumEntry 94 }
	
	uumTunnelClientEndpoint	  OBJECT-TYPE
	SYNTAX  OCTET STRING
	ACCESS	read-write
	STATUS	mandatory
	DESCRIPTION
		"The address of the initiator end of the tunnel."
	--CONFIGURABLE
	::= { uumEntry 95 }
	
	uumTunnelServerEndpoint	  OBJECT-TYPE
	SYNTAX  OCTET STRING
	ACCESS	read-write
	STATUS	mandatory
	DESCRIPTION
		"The address of the server end of the tunnel."
	--CONFIGURABLE
	::= { uumEntry 96 }
	
	uumTunnelPassword	  OBJECT-TYPE
	SYNTAX  OCTET STRING
	ACCESS	write-only
	STATUS	mandatory
	DESCRIPTION
		"The password of the tunnel."
	--CONFIGURABLE
	::= { uumEntry 97 }
	
	uumTunnelPrivateGroupID	  OBJECT-TYPE
	SYNTAX  OCTET STRING
	ACCESS	read-write
	STATUS	mandatory
	DESCRIPTION
		"The group ID for the tunneled session."
	--CONFIGURABLE
	::= { uumEntry 98 }
	
	uumTunnelSecurity	  OBJECT-TYPE
	SYNTAX  INTEGER {
			none(0),
			control-Only(1),
			data-Only(2),
			both-Data-And-Control(3)
			}
	ACCESS	read-write
	STATUS	mandatory
	DESCRIPTION
		"The security level of the tunnel."
	DEFVAL { none }
	--CONFIGURABLE
	::= { uumEntry 99 }

	uumPrimaryDNSServer OBJECT-TYPE
    SYNTAX  IpAddress
    ACCESS  read-write
    STATUS  mandatory
    DESCRIPTION
        "The primary dns server for the user"
    DEFVAL { 0  }
    --CONFIGURABLE
    ::= { uumEntry 100 }
 
    uumSecondaryDNSServer OBJECT-TYPE
    SYNTAX  IpAddress
    ACCESS  read-write
    STATUS  mandatory
    DESCRIPTION
        "The secondary DNS server for the user"
    DEFVAL { 0  }
    --CONFIGURABLE
    ::= { uumEntry 101 }
	
	uumUserTapStatus	OBJECT-TYPE
	SYNTAX	INTEGER {
		disabled(0),
		enabled(1)
		}
	ACCESS	read-write
	STATUS	mandatory
	DESCRIPTION
		"Is this user to be tapped"
	--CONFIGURABLE
	::= { uumEntry 102 }

	uumUserTapFormat	OBJECT-TYPE
	SYNTAX	INTEGER {
		ascii(0),
		hex(1),
		clear(2)
		}
	ACCESS	read-write
	STATUS	mandatory
	DESCRIPTION
		"The tap format if tap is enabled"
	--CONFIGURABLE
	::= { uumEntry 103 }

	uumUserTapOutput	OBJECT-TYPE
	SYNTAX	INTEGER {
		syslog(0)
		}
	ACCESS	read-write
	STATUS	mandatory
	DESCRIPTION
		"Send the tapped output to syslog"
	--CONFIGURABLE
	::= { uumEntry 104 }

	uumUserTapFacility	OBJECT-TYPE
	SYNTAX	INTEGER {
		auth(1),
		level0(2),
		level1(3),
		level2(4),
		level3(5),
		level4(6),
		level5(7),
		level6(8),
		level7(9)
		}
	ACCESS	read-write
	STATUS	mandatory
	DESCRIPTION
		"The syslog facility to send the output to."
	--CONFIGURABLE
	::= { uumEntry 105 }

	uumUserTapLoglevel	OBJECT-TYPE
	SYNTAX	INTEGER {
		critical(0),
		unusual(1),
		common(2),
		verbose(3)
		}
	ACCESS	read-write
	STATUS	mandatory
	DESCRIPTION
		"The syslog level to send the output to."
	--CONFIGURABLE
	::= { uumEntry 106 }

	uumUserTapAddress	OBJECT-TYPE
	SYNTAX	IpAddress
	ACCESS	read-write
	STATUS	mandatory
	DESCRIPTION
		"The syslogd address"
	--CONFIGURABLE
	::= { uumEntry 107 }

	uumMulticastProxy OBJECT-TYPE
	SYNTAX	INTEGER {
		enabled(1),
		disabled(2)
		}
	ACCESS read-write                                                 
	STATUS mandatory                                                 
	DESCRIPTION
		"If Multicast will be proxied"   
	DEFVAL    { disabled }
	--CONFIGURABLE                                                        
	::= { uumEntry 108 }            

	uumNasIpAddress	OBJECT-TYPE
	SYNTAX	IpAddress
	ACCESS	read-write
	STATUS	mandatory
	DESCRIPTION
		"The NAS IP address"
	--CONFIGURABLE
	::= { uumEntry 113 }

	uumNasPort	OBJECT-TYPE
	SYNTAX	INTEGER
	ACCESS	read-write
	STATUS	mandatory
	DESCRIPTION
		"The NAS Port Attribute"
	--CONFIGURABLE
	::= { uumEntry 114 }
	
	uumFramedCallbackId	OBJECT-TYPE
	SYNTAX	INTEGER
	ACCESS	read-write
	STATUS	mandatory
	DESCRIPTION
		"Framed Callback Identifier  attribute"
	--CONFIGURABLE
	::= { uumEntry 115 }

	uumState	OBJECT-TYPE
	SYNTAX OCTET STRING	
	ACCESS	read-write
	STATUS	mandatory
	DESCRIPTION
		"State attribute"
	--CONFIGURABLE
	::= { uumEntry 116 }
	
	uumClass	OBJECT-TYPE
	SYNTAX OCTET STRING	
	ACCESS	read-write
	STATUS	mandatory
	DESCRIPTION
		"Class attribute"
	--CONFIGURABLE
	::= { uumEntry 117 }

	uumCalledStationId	OBJECT-TYPE
	SYNTAX OCTET STRING	
	ACCESS	read-write
	STATUS	mandatory
	DESCRIPTION
		"Called Station Id"
	--CONFIGURABLE
	::= { uumEntry 118 }

	uumCallingStationId	OBJECT-TYPE
	SYNTAX OCTET STRING	
	ACCESS	read-write
	STATUS	mandatory
	DESCRIPTION
		"Calling Station Id"
	--CONFIGURABLE
	::= { uumEntry 119 }

	uumNasIdentifier	OBJECT-TYPE
	SYNTAX OCTET STRING	
	ACCESS	read-write
	STATUS	mandatory
	DESCRIPTION
		"NAS ID"
	--CONFIGURABLE
	::= { uumEntry 120 }
	
	uumCipIfName	OBJECT-TYPE
	SYNTAX OCTET STRING	(SIZE (0..32))
	ACCESS	read-write
	STATUS	mandatory
	DESCRIPTION
		"CIP Interface Name"
	--CONFIGURABLE
	::= { uumEntry 121 }
	
	uumPPPLocalIpAddress	OBJECT-TYPE
	SYNTAX IpAddress
	ACCESS	read-only
	STATUS	mandatory
	DESCRIPTION
		"PPP Local IP Address"
	--CONFIGURABLE
	::= { uumEntry 122 }
	
	uumPPPRemoteIpAddress	OBJECT-TYPE
	SYNTAX IpAddress
	ACCESS	read-only
	STATUS	mandatory
	DESCRIPTION
		"PPP Remote IP Address"
	--CONFIGURABLE
	::= { uumEntry 123 }
	
	uumSessionvars	OBJECT-TYPE
	SYNTAX	IpAddress 
	ACCESS	read-only
	STATUS	mandatory
	DESCRIPTION
		""
	::= { uumEntry 126 }

	uumChatScriptName   OBJECT-TYPE
    SYNTAX OCTET STRING
    ACCESS  read-write
    STATUS  mandatory
    DESCRIPTION 
        "The chat script name configured for the user"
    --CONFIGURABLE
    ::= { uumEntry 127 }
    
	
	uumPortLimit	OBJECT-TYPE
	SYNTAX	INTEGER 
	ACCESS	read-write
	STATUS	mandatory
	DESCRIPTION
		""
	--CONFIGURABLE
	::= { uumEntry 128 }

    uumPppSourceIpFilter    OBJECT-TYPE
        SYNTAX  INTEGER  
        ACCESS  read-write
        STATUS  mandatory
        DESCRIPTION     
                "PPP Source Address Ip Filer "
        --CONFIGURABLE
        ::= { uumEntry 129 }

        uumCallbackType OBJECT-TYPE
        SYNTAX INTEGER { 
               normal(1),
               ani(2),   
               static(3), 
               dynamic(4)
               }
        ACCESS read-write   
        STATUS mandatory
        DESCRIPTION
               "The Callback Type.  Normal to dial callback users
               using the existing phone number field.  ANI to dial
               callback users using the number supplied with the
               caller ID.  Static to dial callback users using the
               numbers provided in the DialGroup specified for this
               user.  Dynamic to dial callback users using the numbers
               provided during LCP negotiations."
        --CONFIGURABLE    
        ::= { uumEntry 131}  
        
        uumIsdnDataCallType OBJECT-TYPE
        SYNTAX INTEGER {
               notConfigured(0),
               cleared(1),
               dataovervoice(2),
               restricted56k(3),
               v11056k(4),
               unrestricted64k(5),
               asynctosyncppp(6)
               } 
        ACCESS read-write
        STATUS mandatory
        DESCRIPTION
               "The ISDN customized CallType. The values represent a series
                of AT commands that users of the profile can generate.  For
                'cleared' no AT command will be generated.

               dataovervoice        *V2=3    S67.1=0
               restricted56k        *V2=4    S67.1=1     S67.2=0
               v11056k              *V2=2    S67.1=1     S67.2=0
               unrestricted64k      *V2=4    S67.1=1     S67.2=1
               asynctosyncppp       *V2=5    S67.1=0

               where *V2=2 -> V.110 Rate Adaption only
                        =3 -> Modem/Fax Emulation only
                        =4 -> Clear Channel only
                        =5 -> Async to sync PPP

                   S67.1=0 -> Rate not fixed
                        =1 -> Rate fixed

                   S67.2=0 -> Connect at 56k
                        =1 -> Connect at 64k  "
        DEFVAL  { 1 }
        --CONFIGURABLE
        ::= { uumEntry 132}

    uumDNISReAuth    OBJECT-TYPE
        SYNTAX  INTEGER {
            none(0),
            any(1),
            chap(2),
            eap(3),
            mschap(4),
            pap(5),
            proxyEap(6)
        } 
        ACCESS  read-write
        STATUS  mandatory
        DESCRIPTION     
                "DNIS Re-Authentication flag "
        --CONFIGURABLE
        ::= { uumEntry 139 }
    
    uumReChapTimeout    OBJECT-TYPE
    SYNTAX  INTEGER 
    ACCESS  read-write
    STATUS  mandatory
    DESCRIPTION
        "Re Chap timeout for PPP"
    --CONFIGURABLE
    ::= { uumEntry 140 }

    uumNextHopGateway    OBJECT-TYPE
        SYNTAX  IpAddress
        ACCESS  read-write
        STATUS  mandatory
        DESCRIPTION
                "The VPN-neighbour. "
        --CONFIGURABLE
     ::= { uumEntry 130 }

    uumLocalTcpPort OBJECT-TYPE
    SYNTAX  INTEGER     
    ACCESS  read-only 
    STATUS  mandatory
    DESCRIPTION 
        "Local TCP port of telnet/CTCP login user"
    ::= { uumEntry 141 } 

    uumConnectionvars   OBJECT-TYPE
    SYNTAX  IpAddress
    ACCESS  read-only 
    STATUS  mandatory
    DESCRIPTION  
        ""      
    ::= { uumEntry 144 } 
        
    uumShowConnVar   OBJECT-TYPE
    SYNTAX  INTEGER 
    ACCESS  read-only 
    STATUS  mandatory
    DESCRIPTION  
        "For the CLI command show connection <interface-name>"      
    ::= { uumEntry 145 } 


    uumSpecialXonXoff  OBJECT-TYPE
    SYNTAX  INTEGER {
        disabled(0),
        enabled(1)
    } 
    ACCESS  read-write
    STATUS  mandatory
    DESCRIPTION     
            "Special Xon Xoff flow control \n"
    --CONFIGURABLE
    ::= { uumEntry 160 }

    uumTelnetOptions  OBJECT-TYPE
    SYNTAX  INTEGER
    ACCESS  read-write
    STATUS  mandatory
    DESCRIPTION     
            "User specific Telnet Options \n"
    --CONFIGURABLE
    ::= { uumEntry 161 }

	uumMlPPPFragThreshold OBJECT-TYPE
	SYNTAX	INTEGER(64..4096)
	ACCESS	read-write
	STATUS	mandatory
	DESCRIPTION
			"Multilink fragmentation threshold"
	--CONFIGURABLE
	::= { uumEntry 165 }

    uumTunnelClientAuthId    OBJECT-TYPE
        SYNTAX  OCTET STRING
        ACCESS  read-write
        STATUS  mandatory
        DESCRIPTION
                "Replaces the System Transmit Auth Name." 
        --CONFIGURABLE       
     ::= { uumEntry 174 } 

	uumTunnelChallengeOutgoing	OBJECT-TYPE
	SYNTAX	INTEGER {
		none(0),
		enable(1),
		disable(2)
		}
	ACCESS	read-write
	STATUS	mandatory
	DESCRIPTION
		"Enables or disables the tunnel challenge when a tunnel is initiated
		 by the LAC, overriding the global L2TP setting; if set to None, 
		 global setting takes effect."
	--CONFIGURABLE
	::= { uumEntry 173 }

	uumIpRoutingRipV1	OBJECT-TYPE
	SYNTAX	INTEGER {
		enable(1),
		disable(2)
		}
	ACCESS	read-write
	STATUS	mandatory
	DESCRIPTION
		"Enables or disables the IP RIPv1 routing protocol
                 for this User"
	--CONFIGURABLE
	::= { uumEntry 133 }

	uumIpRoutingRipV2	OBJECT-TYPE
	SYNTAX	INTEGER {
		enable(1),
		disable(2)
		}
	ACCESS	read-write
	STATUS	mandatory
	DESCRIPTION
		"Enables or disables the IP RIPv2 routing protocol
                 for this User"
	--CONFIGURABLE
	::= { uumEntry 134 }

	uumIpRoutingOspf 	OBJECT-TYPE
	SYNTAX	INTEGER {
		enable(1),
		disable(2)
		}
	ACCESS	read-write
	STATUS	mandatory
	DESCRIPTION
		"Enables or disables the IP OSPF routing protocol
                 for this User"
	--CONFIGURABLE
	::= { uumEntry 135 }

	uumOspfAddresslessIfIndex	OBJECT-TYPE
	SYNTAX	INTEGER 
	ACCESS	read-write
	STATUS	mandatory
	DESCRIPTION
		"An arbitary 32-bit integer value defined by the user 
		 to be used with Addressless interfaces. This 
                 addresslessIfIndex will bind with the configured OSPF
		 INTF addresslessIfIndex, if one was configured."
	::= { uumEntry 136 }

	uumIpSecPolicyFile	OBJECT-TYPE
	SYNTAX	DisplayString (SIZE (0..40))
	ACCESS	read-write
	STATUS 	mandatory
	DESCRIPTION
		"The name of IP Security Policy filename associated with that user. -Note: This feature is available from Hiper ARC 5.0 release onwards."
	--CONFIGURABLE
	::= { uumEntry 155 }

	uumIpSecPolicyAccess	OBJECT-TYPE
	SYNTAX	INTEGER {
		enabled(1),
		disabled(0)
		}
	ACCESS	read-write
	STATUS	mandatory
	DESCRIPTION
		"This flag defines whether the IP Security policy access is enabled or disabled. Note: This feature is available from Hiper ARC 5.0 release onwards."
        DEFVAL  { disabled }
	::= { uumEntry 156 }

	uumIpSecPolicyType	OBJECT-TYPE
	SYNTAX	INTEGER {
		domain-based(0),
		user-based(1)
		}
	ACCESS	read-write
	STATUS	mandatory
	DESCRIPTION
		"This flag defines whether the IP Security policy type is user-based or domain-based. Note: This feature is available from Hiper ARC 5.0 release onwards"
        DEFVAL  { domain-based }
	::= { uumEntry 157 }

	uumIpSecPolicyConfiguration	OBJECT-TYPE
	SYNTAX	INTEGER {
		static(0),
		dynamic(1)
		}
	ACCESS	read-write
	STATUS	mandatory
	DESCRIPTION
		"This flag specifies whether IP Security Policy is applied in statically or dynamically. Note: This feature is available only from Hiper ARC 5.0 onwards."
        DEFVAL  { static }
	::= { uumEntry 158 }

    uumVPNGateway    OBJECT-TYPE
        SYNTAX  IpAddress
        ACCESS  read-only
        STATUS  mandatory
        DESCRIPTION
                "The VPN-Gateway. "
     ::= { uumEntry 162 }

    uumVPNID    OBJECT-TYPE
        SYNTAX  INTEGER 
        ACCESS  read-only
        STATUS  mandatory
        DESCRIPTION
                "The VPN-ID. "
     ::= { uumEntry 163 }
    
	uumVPNName    OBJECT-TYPE
        SYNTAX  OCTET STRING 
        ACCESS  read-only
        STATUS  mandatory
        DESCRIPTION
                "The VPN-Name. "
     ::= { uumEntry 164 }
        
        uumTrafficThreshold OBJECT-TYPE
        SYNTAX  INTEGER
        ACCESS  read-write
        STATUS  mandatory
        DESCRIPTION
                        "traffic threshold based idle timeout"
        --CONFIGURABLE
        ::= { uumEntry 167 }

	uumTunnelAssignmentId    OBJECT-TYPE
        SYNTAX  OCTET STRING 
        ACCESS  read-write
        STATUS  mandatory
        DESCRIPTION
                "The name of the L2TP/PPTP tunnel that may be created for the user."
		--CONFIGURABLE
     ::= { uumEntry 168 }

	uumKeepAliveInterval	  OBJECT-TYPE
	SYNTAX  INTEGER (0..65535)
	ACCESS	read-write
	STATUS	mandatory
	DESCRIPTION
		"The TCP Keep Alive Interval in seconds"
	DEFVAL	{ 0 }
	--CONFIGURABLE
	::= { uumEntry 169 }

	usrUserManCfmFileName	OBJECT-TYPE
	SYNTAX	DisplayString (SIZE (1..32))
	ACCESS	read-only
	STATUS 	mandatory
	DESCRIPTION
		"The name of the configuration file"
	::= { usrUserManGroup 26 }

	usrUserManCfmSaveFlag	OBJECT-TYPE
	SYNTAX	INTEGER	{
			normal(1),
			save(2),
			saving(3), 
			load(4),
			loading(5)
			}
	ACCESS	read-write
	STATUS	mandatory
	DESCRIPTION
		"The Configuration File Manager Flag for saving user management scalars"
	::= { usrUserManGroup 27 }

	usrUserManRadiusPort	OBJECT-TYPE
	SYNTAX	INTEGER	(0..65535)
	ACCESS	read-write
	STATUS	mandatory
	DESCRIPTION
		"The udp port the primary radius server listens at"
	--CONFIGURABLE
	::= { usrUserManGroup 28 }

	usrUserManRadiusAltPort	OBJECT-TYPE
	SYNTAX	INTEGER	(0..65535)
	ACCESS	read-write
	STATUS	mandatory
	DESCRIPTION
		"The udp port the alternate radius server listens at"
	--CONFIGURABLE
	::= { usrUserManGroup 29 }

	usrUserManRadiusAltSecret	OBJECT-TYPE
	SYNTAX	OCTET STRING	(SIZE (1..15))
	ACCESS	write-only
	STATUS	mandatory
	DESCRIPTION
		"The shared secret between the alternate RADIUS server and pilgrim"
	--CONFIGURABLE
	::= { usrUserManGroup 30 }

-- User managers framed route table definition

	usrUserManFramedRouteTable	OBJECT-TYPE
	SYNTAX	SEQUENCE OF UumFramedRouteEntry
	ACCESS	not-accessible
	STATUS	mandatory
	DESCRIPTION
		""
	--CONFIGURABLE
	::= { usrUserManGroup 31 }

	uumFramedRouteEntry	OBJECT-TYPE
	SYNTAX	UumFramedRouteEntry
	ACCESS	not-accessible
	STATUS	mandatory
	DESCRIPTION
		""
	INDEX	{ uumFramedRouteUserName, uumFramedRouteIpAddress }
	--CONFIGURABLE
	::= { usrUserManFramedRouteTable 1 }

	UumFramedRouteEntry ::= 
	SEQUENCE {
	uumFramedRouteUserName
		UsrUserName,
	uumFramedRouteIpAddress
		IpAddress,
	uumFramedRouteStatus
		INTEGER,
	uumFramedRouteIpMask
		IpAddress,
	uumFramedRouteIpGateway
		IpAddress,
	uumFramedRouteIpMetric
		INTEGER
	}

	uumFramedRouteUserName	OBJECT-TYPE
	SYNTAX	UsrUserName
	ACCESS	not-accessible
	STATUS	mandatory
	DESCRIPTION
		"The users name"
	--CONFIGURABLE
	::= { uumFramedRouteEntry 1 }

	uumFramedRouteIpAddress	OBJECT-TYPE
	SYNTAX	IpAddress
	ACCESS	not-accessible
	STATUS	mandatory
	DESCRIPTION
		"The framed routing ip address for the user"
	--CONFIGURABLE
	::= { uumFramedRouteEntry 2 }
	
	uumFramedRouteStatus	OBJECT-TYPE
	SYNTAX	INTEGER {
		delete(1),
		add(2)
		}
	ACCESS	write-only
	STATUS	mandatory
	DESCRIPTION	
		"The status field for the framed route"
	::= { uumFramedRouteEntry 3 }

	uumFramedRouteIpMask	OBJECT-TYPE
	SYNTAX	IpAddress
	ACCESS	read-write
	STATUS	mandatory
	DESCRIPTION
		"The framed routing ip mask for the user"
	--CONFIGURABLE
	::= { uumFramedRouteEntry 4 }	
		
	uumFramedRouteIpGateway	OBJECT-TYPE
	SYNTAX	IpAddress
	ACCESS	read-write
	STATUS	mandatory
	DESCRIPTION
		"The framed routing ip gateway for the user"
	--CONFIGURABLE
	::= { uumFramedRouteEntry 5 }

	uumFramedRouteIpMetric	OBJECT-TYPE
	SYNTAX	INTEGER (1..16)
	ACCESS	read-write
	STATUS	mandatory
	DESCRIPTION	
		"The framed routing ip metric for the user"
	--CONFIGURABLE
	::= { uumFramedRouteEntry 6 }

	usrUserManRadiusAcctSecret	OBJECT-TYPE
	SYNTAX	OCTET STRING	(SIZE (1..15))
	ACCESS	write-only
	STATUS	mandatory
	DESCRIPTION
		"The radius secret for the primary accounting server"
	--CONFIGURABLE
	::= { usrUserManGroup 32 }
	
	usrUserManRadiusAcctAltSecret	OBJECT-TYPE
	SYNTAX	OCTET STRING	(SIZE (1..15))
	ACCESS	write-only
	STATUS	mandatory
	DESCRIPTION
		"The radius secret for the secondary accounting server"
	--CONFIGURABLE
	::= { usrUserManGroup 33 }

	usrUserManRadiusAcctPort	OBJECT-TYPE
	SYNTAX	INTEGER (0..65535)
	ACCESS	read-write
	STATUS	mandatory
	DESCRIPTION
		"The radius port for the primary accounting server"
	--CONFIGURABLE
	::= { usrUserManGroup 34 }

	usrUserManRadiusAcctAltPort	OBJECT-TYPE
	SYNTAX	INTEGER (0..65535)
	ACCESS	read-write
	STATUS	mandatory
	DESCRIPTION
		"The radius port for the secondary accounting server"
	--CONFIGURABLE
	::= { usrUserManGroup 35 }

	usrRadiusBusyOutEnabled	OBJECT-TYPE
	SYNTAX	TruthValue
	ACCESS	read-write
	STATUS	mandatory
	DESCRIPTION
		"Is the Radius client regularly checking the contact time
		 of the servers so that it can cause the modems to be busied
		 out when the servers are unreachbale."
	DEFVAL	{ 1 }
	--CONFIGURABLE
	::= { usrUserManGroup 36 }

	usrRadiusHelloFrequency	OBJECT-TYPE
	SYNTAX	INTEGER(1..6000)
	ACCESS	read-write
	STATUS	mandatory
	DESCRIPTION
		"The number of seconds the system can go between messages
		 from the RADIUS servers before it sends a Status-Server
		 request to that server."
	DEFVAL	{ 60 }
	--CONFIGURABLE
	::= { usrUserManGroup 37 }

	usrRadiusAuthState	OBJECT-TYPE
	SYNTAX	INTEGER {
			start(1), up(2), losingContact(3), down(4), gainingContact(5)
			}
	ACCESS	read-only
	STATUS	mandatory
	DESCRIPTION
		"If the system is tracking RADIUS servers for service
		 loss busy-out, the state of those server."
	DEFVAL	{ 1 }
	::= { usrUserManGroup 38 }


-- User managers assigned address pool table definition

	usrUserManAddrPoolTable	OBJECT-TYPE
	SYNTAX	SEQUENCE OF UumAddrPoolEntry
	ACCESS	not-accessible
	STATUS	mandatory
	DESCRIPTION
		"Table of address pools a user is configured for."
	--CONFIGURABLE
	::= { usrUserManGroup 39 }

	uumAddrPoolEntry	OBJECT-TYPE
	SYNTAX	UumAddrPoolEntry
	ACCESS	not-accessible
	STATUS	mandatory
	DESCRIPTION
		"An entry of an address pool that a user is configured for."
	INDEX	{ uumAddrPoolUserName, uumAddrPoolName}
	--CONFIGURABLE
	::= { usrUserManAddrPoolTable 1 }

	UumAddrPoolEntry ::= SEQUENCE {
	     uumAddrPoolUserName    UsrUserName,
	     uumAddrPoolName        DisplayString,
             uumAddrPoolStatus      INTEGER
	     }

	uumAddrPoolUserName	OBJECT-TYPE
	SYNTAX	UsrUserName
	ACCESS	not-accessible
	STATUS	mandatory
	DESCRIPTION
		"The users name"
	--CONFIGURABLE
	::= { uumAddrPoolEntry 1 }

	uumAddrPoolName	OBJECT-TYPE
	SYNTAX	DisplayString (SIZE(1..16))
	ACCESS	not-accessible
	STATUS	mandatory
	DESCRIPTION
		"The name of the address pool this user is configured for"
	--CONFIGURABLE
	::= { uumAddrPoolEntry 2 }
	
	uumAddrPoolStatus	OBJECT-TYPE
	SYNTAX	INTEGER {
		delete(1),
		add(2)
		}
	ACCESS	read-write
	STATUS	mandatory
	DESCRIPTION	
		"If set to active(2) user is configured to use this pool. If
                 set to delet(1) this pool should be deleted from user's
                 address pool list"
     	--CONFIGURABLE
	::= { uumAddrPoolEntry 3 }

	usrRadiusAcctState	OBJECT-TYPE
	SYNTAX	INTEGER {
			start(1), up(2), losingContact(3), down(4), gainingContact(5)
			}
	ACCESS	read-only
	STATUS	mandatory
	DESCRIPTION
		"A debug value for debugging the service loss subsystem."
	::= { usrUserManGroup 40 }

	usrRadiusAuthSecsMessage	OBJECT-TYPE
	SYNTAX	INTEGER
	ACCESS	read-only
	STATUS	mandatory
	DESCRIPTION
		"A debug value for debugging the service loss subsystem."
	::= { usrUserManGroup 41 }

	usrRadiusAcctSecsMessage	OBJECT-TYPE
	SYNTAX	INTEGER
	ACCESS	read-only
	STATUS	mandatory
	DESCRIPTION
		"A debug value for debugging the service loss subsystem."
	::= { usrUserManGroup 42 }

	usrRadiusAuthSecsState	OBJECT-TYPE
	SYNTAX	INTEGER
	ACCESS	read-only
	STATUS	mandatory
	DESCRIPTION
		"A debug value for debugging the service loss subsystem."
	::= { usrUserManGroup 43 }

	usrRadiusAcctSecsState	OBJECT-TYPE
	SYNTAX	INTEGER
	ACCESS	read-only
	STATUS	mandatory
	DESCRIPTION
		"A debug value for debugging the service loss subsystem."
	::= { usrUserManGroup 44 }

	usrUserManRadiusAuthNoResponse	OBJECT-TYPE
	SYNTAX	Counter
	ACCESS	read-only
	STATUS	mandatory
	DESCRIPTION
		"The number of times radius fails to answer an 
		 authentication request"
	::= { usrUserManGroup 45 }

	usrUserManActiveSessionTable	OBJECT-TYPE
	SYNTAX	SEQUENCE OF UumActiveSessionEntry
	ACCESS	not-accessible
	STATUS	mandatory
	DESCRIPTION
		""
	::= { usrUserManGroup 46 }

	uumActiveSessionEntry	OBJECT-TYPE
	SYNTAX	UumActiveSessionEntry
	ACCESS	not-accessible
	STATUS	mandatory
	DESCRIPTION
		""
	INDEX	{ uumActiveSessionUserName, uumActiveSessionSessionId }
	::= { usrUserManActiveSessionTable 1 }
		
	UumActiveSessionEntry ::= 
	SEQUENCE {
	uumActiveSessionUserName
		UsrUserName,
	uumActiveSessionSessionId
		INTEGER,
	uumActiveSessionConnectionType
		INTEGER,
	uumActiveSessionProtocolType
		INTEGER,
	uumActiveSessionAction
		INTEGER,
	uumActiveSessionIfName
		OCTET STRING,
	uumActiveSessionIpAddress
		IpAddress,
	uumActiveSessionConnTime
		INTEGER,
	uumActiveSessionIdleTime
		INTEGER,
    uumActiveSessionId
        INTEGER,
    uumSessionUserName    
        UsrUserName,  
	uumActiveSessionInBytes
		INTEGER,
	uumActiveSessionOutBytes
		INTEGER,
    uumActiveSessionIpAddress
        IpAddress,
	uumActiveSessionCallId
		OCTET STRING
	}

	uumActiveSessionUserName	OBJECT-TYPE
	SYNTAX	UsrUserName
	ACCESS	not-accessible
	STATUS	mandatory
	DESCRIPTION
		"The users name"
	::= { uumActiveSessionEntry 1 }

	uumActiveSessionSessionId	OBJECT-TYPE
	SYNTAX	INTEGER 
	ACCESS	not-accessible
	STATUS	mandatory
	DESCRIPTION
		"The unique id for the active session"
	::= { uumActiveSessionEntry 2 }

	uumActiveSessionConnectionType	OBJECT-TYPE
	SYNTAX	INTEGER {
		unknown(1),
		wan(2),
		lan(3)
		}
	ACCESS	read-only
	STATUS	mandatory
	DESCRIPTION
		"The connection type for the active session"
	::= { uumActiveSessionEntry 3 }
		
	uumActiveSessionProtocolType	OBJECT-TYPE
	SYNTAX	INTEGER {
		unknown(1),
		ppp(2),
		slip(3),
		arap(4),
		telnet(5),
		rlogin(6),
		cleartcp(7)
		}
	ACCESS	read-only
	STATUS	mandatory
	DESCRIPTION
		"The protocol type for the active session"
	::= { uumActiveSessionEntry 4 }

	uumActiveSessionAction	OBJECT-TYPE
	SYNTAX	INTEGER {
		disconnect(6)
		}
	ACCESS	write-only
	STATUS	mandatory
	DESCRIPTION
		"We need to be able to disconnect all users with a
		 particular user name"
	::= { uumActiveSessionEntry 5 }

	uumActiveSessionIfName	OBJECT-TYPE
	SYNTAX OCTET STRING	
	ACCESS	read-only
	STATUS	mandatory
	DESCRIPTION
		"Interface Name"
	::= { uumActiveSessionEntry 6 }

	uumActiveSessionIpAddress	OBJECT-TYPE
	SYNTAX IpAddress	
	ACCESS	read-only
	STATUS	mandatory
	DESCRIPTION
		"IP Address of the session. This can be Remote PPP IP address
		 in the case of a framed user or the login host ip address if
		 the user type is login."
	::= { uumActiveSessionEntry 7 }

	uumActiveSessionConnTime	OBJECT-TYPE
	SYNTAX  INTEGER	
	ACCESS	read-only
	STATUS	mandatory
	DESCRIPTION
		"Session Connect Time"
	::= { uumActiveSessionEntry 8 }

	uumActiveSessionIdleTime	OBJECT-TYPE
	SYNTAX  INTEGER	
	ACCESS	read-only
	STATUS	mandatory
	DESCRIPTION
		"Session Idle Time"
	::= { uumActiveSessionEntry 9 }

    uumActiveSessionId  OBJECT-TYPE
    SYNTAX  INTEGER
    ACCESS  read-write
    STATUS  mandatory
    DESCRIPTION
        "We need to display the sessionId"
    ::= { uumActiveSessionEntry 10 }
    
    uumSessionUserName  OBJECT-TYPE
    SYNTAX  UsrUserName
    ACCESS  read-write
    STATUS  mandatory
    DESCRIPTION
        "We need to display the username"
    ::= { uumActiveSessionEntry 11 }

	uumActiveSessionInBytes	OBJECT-TYPE
	SYNTAX  INTEGER	
	ACCESS	read-only
	STATUS	mandatory
	DESCRIPTION
		"Session Bytes Count - Input Bytes"
	::= { uumActiveSessionEntry 12 }
	
	uumActiveSessionOutBytes	OBJECT-TYPE
	SYNTAX  INTEGER	
	ACCESS	read-only
	STATUS	mandatory
	DESCRIPTION
		"Session Bytes Count - Output Bytes"
	::= { uumActiveSessionEntry 13 }
	
	uumActiveSessionCallId	OBJECT-TYPE
	SYNTAX  OCTET STRING
	ACCESS	read-only
	STATUS	mandatory
	DESCRIPTION
		"Session Call ID"
	::= { uumActiveSessionEntry 14 }

	usrUserManSlotSpanChanOffset	OBJECT-TYPE
	SYNTAX	INTEGER (0..1)
	ACCESS	read-write
	STATUS	mandatory
	DESCRIPTION
		"Offset to add to modem's reported slot/span/channel
		when reporting this information.
		Default value is 1 for all platforms except
		Positron which uses a default of 0."
     	--CONFIGURABLE
	::= { usrUserManGroup 47 }

	usrUserManHintAssigned	OBJECT-TYPE
	SYNTAX	INTEGER {
			enabled(1),
			disabled(2)
		}
	ACCESS	read-write
	STATUS	mandatory
	DESCRIPTION
		"Is the hint assigned feature enabled?"
	--CONFIGURABLE
	::= { usrUserManGroup 48 }

    usrUserManAuthorEna    OBJECT-TYPE
    SYNTAX  INTEGER {
            enabled(1),
            disabled(2)
        }
    ACCESS  read-write
    STATUS  mandatory
    DESCRIPTION
        "Is remote authorization on or off"
    --CONFIGURABLE
    ::= { usrUserManGroup 49 }

    usrUserManTcpPacketsRx   OBJECT-TYPE
    SYNTAX  Counter
    ACCESS  read-only
    STATUS  mandatory
    DESCRIPTION
        "The number of TCP packets received"
    ::= { usrUserManGroup 50 }

    usrUserManTcpPacketsTx   OBJECT-TYPE
    SYNTAX  Counter
    ACCESS  read-only
    STATUS  mandatory
    DESCRIPTION
        "The number of TCP packets transmitted"
    ::= { usrUserManGroup 51 }
 
-- AAA server table definition.  A Direct-Request host name entry refers
-- to one of the AAA servers in this table.
  
    usrUserManAAAServersTable OBJECT-TYPE
    SYNTAX SEQUENCE OF UumAAAServersEntry
    ACCESS  not-accessible
    STATUS  mandatory
    DESCRIPTION
        ""
    ::= { usrUserManGroup 52 }


    uumAAAServersEntry    OBJECT-TYPE
    SYNTAX  UumAAAServersEntry
    ACCESS  not-accessible
    STATUS  mandatory
    DESCRIPTION
        ""
    INDEX   { uumAAAServersName, uumAAAServersPref }
    ::= { usrUserManAAAServersTable 1 }

    UumAAAServersEntry ::=
    SEQUENCE {
    uumAAAServersName 
        UsrUserName,
    uumAAAServersPref
        INTEGER,
    uumAAAServerIpAddress
        IpAddress,
    uumAAAServersSecret
        OCTET STRING,
    uumAAAServersPort
        INTEGER,
    uumAAAServersEncryption 
        INTEGER,
    uumAAAServersState
        INTEGER,
    uumAAAServersHostName
        OCTET STRING,
    uumAAAServersPassThru
        INTEGER, 
    uumAAAServersSourcePort
	INTEGER,
    uumAAAServersStatus
        INTEGER,
        uumAAAServersMirrorGroup         INTEGER,
        uumAAAServersSelectionMask       OCTET STRING,  
        uumAAAServersAAAType             INTEGER,
        uumAAAServersProtocol            INTEGER,
        uumAAAServersTimeout             INTEGER,
        uumAAAServersRetransmit          INTEGER,
        uumAAAServersSuccessCount        Counter,
        uumAAAServersFailureCount        Counter,
        uumAAAServersNoResponseCount     Counter,
        uumAAAServersContactInterval     INTEGER,
        uumAAAServersOperationalStatus   INTEGER

    }

    uumAAAServersName  OBJECT-TYPE
    SYNTAX  UsrUserName
    ACCESS  not-accessible      
    STATUS  mandatory
    DESCRIPTION
        "Server name"
    --CONFIGURABLE
    ::= { uumAAAServersEntry 1 }

    uumAAAServersPref  OBJECT-TYPE
    SYNTAX  INTEGER 
    ACCESS  not-accessible      
    STATUS  mandatory
    DESCRIPTION
        "Server preference"
    --CONFIGURABLE
    ::= { uumAAAServersEntry 2 }
    
    uumAAAServerIpAddress OBJECT-TYPE
    SYNTAX  IpAddress
    ACCESS  read-write
    STATUS  mandatory
    DESCRIPTION
        "The IP address for the server"
    --CONFIGURABLE
    ::= { uumAAAServersEntry 3 }

    uumAAAServersSecret OBJECT-TYPE
    SYNTAX  OCTET STRING (SIZE (1..15))
    ACCESS  write-only
    STATUS  mandatory
    DESCRIPTION 
        "The shared secret between the AAA server and client"
    --CONFIGURABLE
    ::= { uumAAAServersEntry 4 }

    uumAAAServersPort    OBJECT-TYPE
    SYNTAX  INTEGER (1..65535)
    ACCESS  read-write
    STATUS  mandatory
    DESCRIPTION
        "The port the AAA server listens at"
    --CONFIGURABLE
    ::= { uumAAAServersEntry 5 }

-- Reversed the definition and change to on/off instead of enable/disable
-- which is consistent with similar difinition on other encryption setting  WSFU 9/23/97
    uumAAAServersEncryption   OBJECT-TYPE
    SYNTAX  INTEGER {
                on(1),
                off(2) 
            }
    ACCESS  read-write
    STATUS  mandatory 
    DESCRIPTION
        "Packet body encryption enabled or disabled.  Disabling encryption
         works for TACACS+ clients only.  The entire body will be sent as 
         clear text. Obvious security concern."
    --CONFIGURABLE
    ::= { uumAAAServersEntry 6 }

    uumAAAServersState OBJECT-TYPE
    SYNTAX  INTEGER {
            enabled(1),
            disabled(2)
        }
    ACCESS  read-write
    STATUS  mandatory 
    DESCRIPTION
        "Is the AAA server enable or disabled"
    --CONFIGURABLE
    ::= { uumAAAServersEntry 7 }

    uumAAAServersHostName OBJECT-TYPE
    SYNTAX  OCTET STRING (SIZE (0..240))
    ACCESS  read-write
    STATUS  mandatory
    DESCRIPTION
        "The name of the AAA host to be resolved by DNS"
    --CONFIGURABLE
    ::= { uumAAAServersEntry 8 }

    uumAAAServersPassThru OBJECT-TYPE
    SYNTAX  INTEGER {
            enabled(1),
            disabled(2)
        }
    ACCESS  read-write
    STATUS  mandatory
    DESCRIPTION
        "When enabled will allow users access to a domain even if they authentication fails.
         This object is used primarily with the direct request feature."
    --CONFIGURABLE
    ::= { uumAAAServersEntry 9 }

    uumAAAServersSourcePort    OBJECT-TYPE
    SYNTAX  INTEGER (0..65535)
    ACCESS  read-write
    STATUS  mandatory
    DESCRIPTION
        "The source port the AAA server listens at"
    --CONFIGURABLE
    ::= { uumAAAServersEntry 10 }

    uumAAAServersStatus   OBJECT-TYPE
    SYNTAX  INTEGER {
        delete(1), 
        inactive(2),
        active(3)
        }
    ACCESS  read-write
    STATUS  mandatory 
    DESCRIPTION
        "The status field for delete -- LEAVE THIS AS LAST OBJECT IN TABLE"
    --CONFIGURABLE
    ::= { uumAAAServersEntry 11 }

    uumAAAServersMirrorGroup  OBJECT-TYPE
    SYNTAX  INTEGER  (0..65535)
    ACCESS  read-write
    STATUS  mandatory
    DESCRIPTION
        "Mirror Group for this server"
    --CONFIGURABLE
    ::= { uumAAAServersEntry 12 }
    
    uumAAAServersSelectionMask OBJECT-TYPE
    SYNTAX  OCTET STRING (SIZE (1..20))
    ACCESS  read-write
    STATUS  mandatory
    DESCRIPTION
    "The Selection mask for Server selection"
    --CONFIGURABLE
    ::= { uumAAAServersEntry 13 }
        
    uumAAAServersAAAType OBJECT-TYPE
        SYNTAX  INTEGER {
                auth(1),
                acco(2) 
            }           
    ACCESS  read-write
    STATUS  mandatory
    DESCRIPTION
        "AAA Server type. Can be Authentication/Accounting"
    --CONFIGURABLE
    ::= { uumAAAServersEntry 14 } 

    uumAAAServersProtocol OBJECT-TYPE
        SYNTAX  INTEGER {
                tacacsplus(1),
                radius(2)
            }
    ACCESS  read-write
    STATUS  mandatory
    DESCRIPTION
        "AAA Server Protocol. For now can be TACACS+ or RADIUS"
    --CONFIGURABLE
    ::= { uumAAAServersEntry 15 }

    uumAAAServersTimeout    OBJECT-TYPE
    SYNTAX  INTEGER (0..65535)
        ACCESS  read-write
        STATUS  mandatory
        DESCRIPTION
                "Timeout value for trying this server.
                Exceeding the time setting will lead to trying for the
                next server in the table "
        --CONFIGURABLE
        ::= { uumAAAServersEntry 16 }

        uumAAAServersRetransmit    OBJECT-TYPE
        SYNTAX  INTEGER (0..65535)
        ACCESS  read-write
        STATUS  mandatory
        DESCRIPTION
                " The retry count or retransmission count for this server
                in the table "
        --CONFIGURABLE
        ::= { uumAAAServersEntry 17 }

        uumAAAServersSuccessCount OBJECT-TYPE
        SYNTAX  Counter
        ACCESS  read-only
        STATUS  mandatory
        DESCRIPTION
        "The number of times radius fails to answer an
                        authentication request"
        ::= { uumAAAServersEntry 18 }

        uumAAAServersFailureCount  OBJECT-TYPE
        SYNTAX  Counter
        ACCESS  read-only
        STATUS  mandatory
        DESCRIPTION
        "The number of times radius fails to answer an
                        authentication request"
        ::= { uumAAAServersEntry 19 }

        uumAAAServersNoResponseCount  OBJECT-TYPE
        SYNTAX  Counter
        ACCESS  read-only
        STATUS  mandatory
        DESCRIPTION
        "The number of times there was a no response from the server
                        for a AAA request "
        ::= { uumAAAServersEntry 20 }

        uumAAAServersContactInterval      OBJECT-TYPE
            SYNTAX  INTEGER
            ACCESS  read-only
            STATUS  mandatory
            DESCRIPTION
           "Number of seconds since the authentication server was last contacted."
                DEFVAL { -1 }
          ::= { uumAAAServersEntry 21 }

        uumAAAServersOperationalStatus      OBJECT-TYPE
            SYNTAX  INTEGER {
                        up(1),
                        down(2)
                }
            ACCESS  read-only
            STATUS  mandatory
            DESCRIPTION
                " Operational Status of Server during AUTH/ACCO "
                DEFVAL { 1 }
          ::= { uumAAAServersEntry 22 }

	usrUserManDirectRequestStatus	OBJECT-TYPE
	SYNTAX	INTEGER {
			enabled(1),
			disabled(2)
		} 
	ACCESS	read-write
	STATUS	mandatory
	DESCRIPTION
		"Is direct request on or off"
	--CONFIGURABLE
	::= { usrUserManGroup 53 }

    usrUserManDirectRequestDelimiter  OBJECT-TYPE
    SYNTAX  OCTET STRING    (SIZE (1..20))
    ACCESS  read-write
    STATUS  mandatory
    DESCRIPTION
        "The delimiter string for the direct request service"
    --CONFIGURABLE
    ::= { usrUserManGroup 54 }

    usrUserManDirectRequestTimeout  OBJECT-TYPE
    SYNTAX  INTEGER (0..30)
    ACCESS  read-write
    STATUS  mandatory
    DESCRIPTION
        "Timeout feature for the direct request service"
    --CONFIGURABLE
    ::= { usrUserManGroup 55 }


        usrUserManRadiusVSA     OBJECT-TYPE
        SYNTAX  INTEGER {
                        enabled(1),
                        disabled(2)
                        }
        ACCESS  read-write
        STATUS  mandatory
        DESCRIPTION
                "Vendor Specific Attribute for the compatibility of Sprint CISCO Server" 
        --CONFIGURABLE
        ::= { usrUserManGroup 56 }
         
        usrUserManRadiusAcctVSA OBJECT-TYPE
        SYNTAX  INTEGER { 
                        enabled(1),
                        disabled(2)
                        }
        ACCESS  read-write
        STATUS  mandatory
        DESCRIPTION
                "Vendor Specific Attribute for the compatibility of Sprint CISCO Server"         
        --CONFIGURABLE
        ::= { usrUserManGroup 57 }

--###===========AAA Domain Table===========
-- AAA Domain table definition.
--      
    usrUserManAAADomainTable OBJECT-TYPE
    SYNTAX SEQUENCE OF UumAAADomainEntry
    ACCESS  not-accessible
    STATUS  mandatory
    DESCRIPTION 
        ""
    ::= { usrUserManGroup 67 }
        
 uumAAADomainEntry    OBJECT-TYPE 
    SYNTAX  UumAAADomainEntry
    ACCESS  not-accessible
    STATUS  mandatory
    DESCRIPTION
        ""  
    INDEX   { uumAAADomainName, uumAAADomainAAAType }
    ::= { usrUserManAAADomainTable 1 }
    
    
 UumAAADomainEntry ::=
    SEQUENCE {
    uumAAADomainName            UsrUserName,
    uumAAADomainAAAType         INTEGER,
    uumAAADomainServersUnavail     OCTET STRING,
    uumAAADomainSearchAlg       INTEGER,
    uumAAADomainDNSIpRotation   INTEGER,
    uumAAADomainInterimAccountingInterval INTEGER,
    uumAAADomainMirroring       INTEGER,
    uumAAADomainState            INTEGER,
    uumAAADomainStatus          INTEGER
    }   
        
                        
        uumAAADomainName        OBJECT-TYPE
                SYNTAX UsrUserName
        ACCESS  not-accessible
        STATUS  mandatory
        DESCRIPTION 
                        "The name of the AAA domain "
                --CONFIGURABLE
                ::= { uumAAADomainEntry 1 }
          
        uumAAADomainAAAType  OBJECT-TYPE
                SYNTAX  INTEGER  (1..3)
            ACCESS  not-accessible 
        STATUS  mandatory
            DESCRIPTION  
            "AAA Server type. Can be Authorizing/Accounting/AAA"
                --CONFIGURABLE
                ::= { uumAAADomainEntry 2 }
                
        uumAAADomainServersUnavail      OBJECT-TYPE
                SYNTAX  OCTET STRING (SIZE (0..240))
                ACCESS  read-write
                STATUS  mandatory
                DESCRIPTION
                "Behaviour if servers are unavailable"
                --CONFIGURABLE
                ::= { uumAAADomainEntry 3 }



        uumAAADomainSearchAlg    OBJECT-TYPE
        SYNTAX  INTEGER {
                fall-Through(1),
                round-Robin(2),
                active-server(3),
                preferred(4),
                load-balancing(5)
                }
                ACCESS  read-write
                STATUS  mandatory
                DESCRIPTION
                "Domain Server Search Algorithm"
                --CONFIGURABLE
                ::= { uumAAADomainEntry 4 }

        uumAAADomainDNSIpRotation    OBJECT-TYPE
        SYNTAX  INTEGER {
                yes(1),
                no(2)
                }
                ACCESS  read-write
                STATUS  mandatory
                DESCRIPTION
                "Should this domain be looked up using DNS ? "
                --CONFIGURABLE
                ::= { uumAAADomainEntry 5 }

        uumAAADomainInterimAccountingInterval    OBJECT-TYPE
                SYNTAX  INTEGER (0..65535)
                ACCESS  read-write
                STATUS  mandatory
                DESCRIPTION
                "Checkpoint Interval for looking up this domain.
                Exceeding the time setting will lead to trying for the
                next domain in the table "
                --CONFIGURABLE
                ::= { uumAAADomainEntry 6 }

        uumAAADomainMirroring    OBJECT-TYPE
        SYNTAX  INTEGER {
                yes(1),
                no(2)
                }
                ACCESS  read-write
                STATUS  mandatory
                DESCRIPTION
                "Should this Domain info. be mirrored ? "
                --CONFIGURABLE
            ::= { uumAAADomainEntry 7 }


        uumAAADomainState    OBJECT-TYPE
        SYNTAX  INTEGER {
                enable(1),
                disable(2)
                }
                ACCESS  read-write
                STATUS  mandatory
                DESCRIPTION
                "Is this domain enabled to be used ? "
                --CONFIGURABLE
            ::= { uumAAADomainEntry 8 }

        uumAAADomainStatus    OBJECT-TYPE
                SYNTAX  INTEGER {
                                delete(1),
                                inactive(2),
                                active(3)
                                }
                ACCESS  read-write
                STATUS  mandatory
                DESCRIPTION
                "Is this domain  added or deleted. Leave this last in the table"
                --CONFIGURABLE
            ::= { uumAAADomainEntry 9 }



-- Global default parameters for Domain Information. Also includes
-- DIRECT_REQUEST Settings



        uumAAAGlobalSelectionMask  OBJECT-TYPE
        SYNTAX  OCTET STRING (SIZE (1..64))
        ACCESS  read-write
        STATUS  mandatory
        DESCRIPTION
        "The Selection mask for Server selection"
        --CONFIGURABLE
         ::= { usrUserManGroup 68 }

        uumAAAGlobalServersUnavail OBJECT-TYPE
        SYNTAX  OCTET STRING  (SIZE (0..240))
                ACCESS  read-write
                STATUS  mandatory
                DESCRIPTION
                "Behaviour if servers are unavailable. Action can be
                                DENY, PERMIT or <domain name> "
                --CONFIGURABLE
         ::= { usrUserManGroup 69 }

        uumAAAGlobalSearchAlg     OBJECT-TYPE
        SYNTAX  INTEGER {
                fall-Through(1),
                round-Robin(2),
				active-server(3),
				prefered(4),
				load-Balancing(5)
                }
        ACCESS  read-write
        STATUS  mandatory
        DESCRIPTION
        "Domain Server Search Algorithm"
        --CONFIGURABLE
         ::= { usrUserManGroup 70 }

        uumAAAGlobalDNSIpRotation       OBJECT-TYPE
        SYNTAX  INTEGER {
                enabled(1),
                disabled(2)
                }
                ACCESS  read-write
                STATUS  mandatory
                DESCRIPTION
                "Should this domain be looked up using DNS ? "
                --CONFIGURABLE
         ::= { usrUserManGroup 71 }


        uumAAAGlobalMirroring     OBJECT-TYPE
        SYNTAX  INTEGER {
                enabled(1),
                disabled(2)
                }
        ACCESS  read-write
        STATUS  mandatory
        DESCRIPTION
        "Should this Domain info. be mirrored ? "
        --CONFIGURABLE
         ::= { usrUserManGroup 73 }
         

        uumAAAGlobalRealmPassword  OBJECT-TYPE
        SYNTAX  OCTET STRING (SIZE (1..15))
        ACCESS  write-only
        STATUS  mandatory
        DESCRIPTION
        "The password for the user send to RADIUS realm directed req case"
        --CONFIGURABLE
         ::= { usrUserManGroup 229 }


-- Pilgrim20 has elements defined in the range through 57 and 
-- 90 through 91.  

	usrUserManReportedPortDensity	OBJECT-TYPE
	SYNTAX	INTEGER (1..256)
	ACCESS	read-write
	STATUS	mandatory
	DESCRIPTION
		"Used as slot multiplier for modem slot
	         when reporting RADIUS NAS-PORT attribute.
	         The reported NAS-PORT attribute for a call is
		 computed as: <slot#> * usrUserManReportedPortDensity +
		              <channel#> + usrUserManSlotSpanChanOffset
	         This can be used to achieve a dense NAS-PORT # mapping for a
		 chassis with uniform modem port density.  Note that it is possible
		 to configure this attribute such that eroneous aliasing of NAS-PORT #s
		 are generated if the ReportPortDensity is set < the systems true port density.
		 Default value is 256."
     	--CONFIGURABLE
	::= { usrUserManGroup 90 }

    usrUserManFillNullAttributes  OBJECT-TYPE
    SYNTAX  INTEGER {
             disabled(0),
             enabled(1)
         }
     ACCESS  read-write
     STATUS  mandatory
     DESCRIPTION
         "This is the switch to enable/disable Filling of Null Attributes
          in Radius Accounting records"
     --CONFIGURABLE
     ::= { usrUserManGroup 91 }

-- Radius enhancements for UUNET follow
 
-- The source port for the authentication servers
 
        usrUserManRadiusSrcPort OBJECT-TYPE
        SYNTAX  INTEGER (1..65535)
        ACCESS  read-write
        STATUS  mandatory
        DESCRIPTION
                "The source udp port the primary radius server binds to"
        --CONFIGURABLE
        ::= { usrUserManGroup 92 }
-- The source port for the accounting servers
 
        usrUserManRadiusAcctSrcPort     OBJECT-TYPE
        SYNTAX  INTEGER (1..65535)
        ACCESS  read-write
        STATUS  mandatory
        DESCRIPTION
                "The source radius port for the primary accounting server"
        --CONFIGURABLE
        ::= { usrUserManGroup 93 }
 
-- The tertiary authentication server details
 
        usrUserManRadiusTertiaryIP      OBJECT-TYPE
        SYNTAX  IpAddress
        ACCESS  read-write
        STATUS  mandatory
        DESCRIPTION
                "The tertiary IP address of the RADIUS server"
        --CONFIGURABLE
        ::= { usrUserManGroup 94 }
 
        usrUserManRadiusTertiarySecret  OBJECT-TYPE
        SYNTAX  OCTET STRING    (SIZE (1..15))
        ACCESS  write-only
        STATUS  mandatory
        DESCRIPTION
                "The radius secret for the tertiary server"
        --CONFIGURABLE
        ::= { usrUserManGroup 95 }

        usrUserManRadiusTertiaryPort    OBJECT-TYPE
        SYNTAX  INTEGER (0..65535)
        ACCESS  read-write
        STATUS  mandatory
        DESCRIPTION
                "The udp port the tertiary radius server listens at"
        --CONFIGURABLE
        ::= { usrUserManGroup 96 }
 
-- The algorithm for authentication
 

        usrRadiusAuthAlgorithm  OBJECT-TYPE
        SYNTAX  INTEGER {
                fallthrough(1),
                roundrobin(2),
				activeserver(3),
				prefered(4)
                }
        ACCESS  read-write
        STATUS  mandatory
        DESCRIPTION
                "Takes either the Fall-through or Round-robin algorithm
                 for re-tries"
        --CONFIGURABLE
        ::= { usrUserManGroup 97 }
 
-- The USR or UUNET style for attribute values
 
        usrRadiusAttributeStyle OBJECT-TYPE
        SYNTAX  INTEGER {
                standard(1),
                ascend(2),
                mci(4)
                }
        ACCESS  read-write
        STATUS  mandatory
        DESCRIPTION
				"Takes STANDARD or ASCEND style for attribute values"
        --CONFIGURABLE
        ::= { usrUserManGroup 98 }
 
-- The Interim accounting interval for checkpoint accounting
 
        usrRadiusInterimAccountingIntervalEnabled       OBJECT-TYPE
        SYNTAX  TruthValue
        ACCESS  read-write
        STATUS  mandatory
        DESCRIPTION
                "Whether checkpoint accounting is enabled"
        DEFVAL  { 1 }
        --CONFIGURABLE
        ::= { usrUserManGroup 99 }
 
        usrRadiusInterimAccountingInterval      OBJECT-TYPE
        SYNTAX  INTEGER (5..3600)
        ACCESS  read-write
        STATUS  mandatory
        DESCRIPTION
                "The time intervals when acct. info is sent to the servers"
        --CONFIGURABLE
        ::= { usrUserManGroup 100 }
 
-- Primary server accounting status
 
        usrUserManPrimAcctStatus        OBJECT-TYPE
        SYNTAX  INTEGER {
                        enabled(1),
                        disabled(2)
                }
        ACCESS  read-write
        STATUS  mandatory
        DESCRIPTION
                "Is priamary accounting on or off"
        --CONFIGURABLE
        ::= { usrUserManGroup 101 }
 
-- Secondary server accounting status
 
        usrUserManSecAcctStatus OBJECT-TYPE
        SYNTAX  INTEGER {
                        enabled(1),
                        disabled(2)
                }
        ACCESS  read-write
        STATUS  mandatory
        DESCRIPTION
                "Is secondary accounting on or off"
        --CONFIGURABLE
        ::= { usrUserManGroup 102 }
 
        usrUserManRadiusAcctFirstBackupIP       OBJECT-TYPE
        SYNTAX  IpAddress
        ACCESS  read-write
        STATUS  mandatory
        DESCRIPTION
                "The IP address of the Primary RADIUS First backup accounting server"
        --CONFIGURABLE
        ::= { usrUserManGroup 103 }
 
        usrUserManRadiusAcctSecondBackupIP      OBJECT-TYPE
        SYNTAX  IpAddress
        ACCESS  read-write
        STATUS  mandatory
        DESCRIPTION
                "The IP address of the Primary RADIUS Second backup accounting server"
        --CONFIGURABLE
        ::= { usrUserManGroup 104 }
 
        usrUserManRadiusAcctAltFirstBackupIP    OBJECT-TYPE
        SYNTAX  IpAddress
        ACCESS  read-write
        STATUS  mandatory
        DESCRIPTION
                "The IP address of the Secondary RADIUS First backup accounting server"
        --CONFIGURABLE
        ::= { usrUserManGroup 105 }

        usrUserManRadiusAcctAltSecondBackupIP   OBJECT-TYPE
        SYNTAX  IpAddress
        ACCESS  read-write
        STATUS  mandatory
        DESCRIPTION
                "The IP address of the Secondary RADIUS Second backup accounting
 server"
        --CONFIGURABLE
        ::= { usrUserManGroup 106 }
 
        usrUserManRadiusAcctFirstBackupSecret   OBJECT-TYPE
        SYNTAX  OCTET STRING    (SIZE (1..15))
        ACCESS  write-only
        STATUS  mandatory
        DESCRIPTION
                "The radius secret for the primary first backup accounting server"
        --CONFIGURABLE
        ::= { usrUserManGroup 107 }
 
        usrUserManRadiusAcctSecondBackupSecret  OBJECT-TYPE
        SYNTAX  OCTET STRING    (SIZE (1..15))
        ACCESS  write-only
        STATUS  mandatory
        DESCRIPTION
                "The radius secret for the primary second backup accounting server"
        --CONFIGURABLE
        ::= { usrUserManGroup 108 }
 
        usrUserManRadiusAcctAltFirstBackupSecret        OBJECT-TYPE
        SYNTAX  OCTET STRING    (SIZE (1..15))
        ACCESS  write-only
        STATUS  mandatory
        DESCRIPTION
                "The radius secret for the secondary first backup accounting server"
        --CONFIGURABLE
        ::= { usrUserManGroup 109 }
 
        usrUserManRadiusAcctAltSecondBackupSecret       OBJECT-TYPE
        SYNTAX  OCTET STRING    (SIZE (1..15))
        ACCESS  write-only
        STATUS  mandatory
        DESCRIPTION
                "The radius secret for the secondary second backup accounting server"
        --CONFIGURABLE
        ::= { usrUserManGroup 110 }
 
        usrUserManRadiusAcctFirstBackupPort     OBJECT-TYPE
        SYNTAX  INTEGER (0..65535)
        ACCESS  read-write
        STATUS  mandatory
        DESCRIPTION
                "The radius port for the primary first backup accounting server"
        --CONFIGURABLE
        ::= { usrUserManGroup 111 }
 
        usrUserManRadiusAcctSecondBackupPort    OBJECT-TYPE
        SYNTAX  INTEGER (0..65535)
        ACCESS  read-write
        STATUS  mandatory
        DESCRIPTION
                "The radius port for the primary second backup accounting server"
        --CONFIGURABLE
        ::= { usrUserManGroup 112 }
 
        usrUserManRadiusAcctAltFirstBackupPort  OBJECT-TYPE
        SYNTAX  INTEGER (0..65535)
        ACCESS  read-write
        STATUS  mandatory
        DESCRIPTION
                "The radius port for the secondary first backup accounting server"
        --CONFIGURABLE
        ::= { usrUserManGroup 113 }
 
        usrUserManRadiusAcctAltSecondBackupPort OBJECT-TYPE
        SYNTAX  INTEGER (0..65535)
        ACCESS  read-write
        STATUS  mandatory
        DESCRIPTION
                "The radius port for the secondary second backup accounting server"
        --CONFIGURABLE
        ::= { usrUserManGroup 114 }
 
        usrUserManRadiusAcctRoundRobinCount     OBJECT-TYPE
        SYNTAX  INTEGER (0..65535)
        ACCESS  read-only
        STATUS  mandatory
        DESCRIPTION
                "The number of times the servers are switched in the primary server group"
        ::= { usrUserManGroup 115 }
 
        usrUserManRadiusAcctAltRoundRobinCount  OBJECT-TYPE
        SYNTAX  INTEGER (0..65535)
        ACCESS  read-only
        STATUS  mandatory
        DESCRIPTION
                "The number of times the servers are switched in the secondary server group"
        ::= { usrUserManGroup 116 }
 
        usrUserManRadiusAcctPacketDiscardCount  OBJECT-TYPE
        SYNTAX  INTEGER (0..65535)
        ACCESS  read-only
        STATUS  mandatory
        DESCRIPTION
                "The number of packets discarded in the primary server group"
        ::= { usrUserManGroup 117 }
 
        usrUserManRadiusAcctAltPacketDiscardCount       OBJECT-TYPE
        SYNTAX  INTEGER (0..65535)
        ACCESS  read-only
        STATUS  mandatory
        DESCRIPTION
                "The number of packets discarded in the secondary server group"
        ::= { usrUserManGroup 118 }

        usrUserManRadiusAcctQueuePercentFull    OBJECT-TYPE
        SYNTAX  INTEGER (0..100)
        ACCESS  read-only
        STATUS  mandatory
        DESCRIPTION
                "Percentage of the queue filled in the primary server group"
        ::= { usrUserManGroup 119 }
 
        usrUserManRadiusAcctAltQueuePercentFull OBJECT-TYPE
        SYNTAX  INTEGER (0..100)
        ACCESS  read-only
        STATUS  mandatory
        DESCRIPTION
                "Percentage of the queue filled in the secondary server group"
        ::= { usrUserManGroup 120 }
 
        usrUserManRadiusAcctOutstandingPacketCount      OBJECT-TYPE
        SYNTAX  INTEGER (0..65535)
        ACCESS  read-only
        STATUS  mandatory
        DESCRIPTION
                "The number of packets outstanding in the primary server group"
        ::= { usrUserManGroup 121 }
 
        usrUserManRadiusAcctAltOutstandingPacketCount   OBJECT-TYPE
        SYNTAX  INTEGER (0..65535)
        ACCESS  read-only
        STATUS  mandatory
        DESCRIPTION
                "The number of packets outstanding in the primary server group"
        ::= { usrUserManGroup 122 }
 
    usrTacacsAcctAttrList OBJECT-TYPE 
    SYNTAX  INTEGER {                                                      
                all(1),                                                 
                simple(2),
                sprint(3)
            }
    ACCESS      read-write
    STATUS      mandatory
    DESCRIPTION
        "Specifies the tacacs+ accounting attribute lists requested from
         different customer like SPRINT ...."
    DEFVAL  { 2 }
    --CONFIGURABLE
    ::= { usrUserManGroup 123 }

	usrUserManAcctAltRetrans    OBJECT-TYPE
    SYNTAX  INTEGER (0..2147483647)
    ACCESS  read-write
    STATUS  mandatory
    DESCRIPTION
        "The maximum number of times a timeout will occur for a secondary server when
            communicating with radius accounting server"
    --CONFIGURABLE
    ::= { usrUserManGroup 124 }
   
	usrUserManLogUnauthenticatedCalls    OBJECT-TYPE
    SYNTAX  TruthValue
    ACCESS  read-write
    STATUS  mandatory
    DESCRIPTION
        "If set to true(1), all unauthenticated calls will generate
         a Stop Accounting-Request. If set to false(2), no Stop
         Accounting-Requests will be sent."
    DEFVAL { true }
    --CONFIGURABLE
    ::= { usrUserManGroup 125 }



	usrUserManRadiusActiveAuthIP	OBJECT-TYPE
	SYNTAX	IpAddress
	ACCESS	read-write
	STATUS	mandatory
	DESCRIPTION
		"The IP address of the Active RADIUS Authentication Server"
	--CONFIGURABLE
	::= { usrUserManGroup 126 }

	usrUserManRadiusActiveAcctIPFirst	OBJECT-TYPE
	SYNTAX	IpAddress
	ACCESS	read-write
	STATUS	mandatory
	DESCRIPTION
		"The IP address of the Active RADIUS Accounting  Server of First Group"
	--CONFIGURABLE
	::= { usrUserManGroup 127 }

	usrUserManRadiusActiveAcctIPSecond	OBJECT-TYPE
	SYNTAX	IpAddress
	ACCESS	read-write
	STATUS	mandatory
	DESCRIPTION
		"The IP address of the Active RADIUS Accounting  Server of Second Group"
	--CONFIGURABLE
	::= { usrUserManGroup 128 }

    usrUserManRadiusFirstBackupAuthSuccesses    OBJECT-TYPE
    SYNTAX  Counter
    ACCESS  read-only
    STATUS  mandatory
    DESCRIPTION
        "The number of first backup radius server authentication successes"
    ::= { usrUserManGroup 129 }

    usrUserManRadiusFirstBackupAuthFails	OBJECT-TYPE
    SYNTAX	Counter
    ACCESS	read-only
    STATUS	mandatory
    DESCRIPTION
    	"The number of first backup radius server authentication failures"
    ::= { usrUserManGroup 130 }

    usrUserManRadiusSecondBackupAuthSuccesses	OBJECT-TYPE
    SYNTAX	Counter
    ACCESS	read-only
    STATUS	mandatory
    DESCRIPTION
    	"The number of secondary backup radius server authentication successes"
    ::= { usrUserManGroup 131 }

    usrUserManRadiusSecondBackupAuthFails	OBJECT-TYPE
    SYNTAX	Counter
    ACCESS	read-only
    STATUS	mandatory
    DESCRIPTION
    	"The number of secondary backup radius server authentication failures"
    ::= { usrUserManGroup 132 }

    usrUserManRadiusFirstBackupAuthNoResponse	OBJECT-TYPE
    SYNTAX	Counter
    ACCESS	read-only
    STATUS	mandatory
    DESCRIPTION
    	"The number of times first backup radius server fails to answer an 
    	 authentication request"
    ::= { usrUserManGroup 133 }

    usrUserManRadiusSecondBackupAuthNoResponse	OBJECT-TYPE
    SYNTAX	Counter
    ACCESS	read-only
    STATUS	mandatory
    DESCRIPTION
    	"The number of times secondary backup radius server fails to answer an 
    	 authentication request"
    ::= { usrUserManGroup 134 }

    usrUserManRadiusCounterResetTime	OBJECT-TYPE
    SYNTAX	OCTET STRING (SIZE (12))
    ACCESS	read-only
    STATUS	mandatory
    DESCRIPTION
    	"Daily time we reset all the authentication counter contains to value zero"
    --CONFIGURABLE
    ::= { usrUserManGroup 135 }

    usrUserManRadiusResetAuthCountersToZero	OBJECT-TYPE
    SYNTAX	INTEGER
    ACCESS	write-only
    STATUS	mandatory
    DESCRIPTION
    	"An user action to reset all the authentication counter contains to value zero"
    --CONFIGURABLE
    ::= { usrUserManGroup 136 }

    usrUserManRadiusAcctCounterResetTime	OBJECT-TYPE
    SYNTAX	OCTET STRING (SIZE (12))
    ACCESS	read-only
    STATUS	mandatory
    DESCRIPTION
    	"Daily time we reset all the accounting counter contains to value zero"
    --CONFIGURABLE
    ::= { usrUserManGroup 137 }

    usrUserManRadiusResetAcctCountersToZero	OBJECT-TYPE
    SYNTAX	INTEGER
    ACCESS	write-only
    STATUS	mandatory
    DESCRIPTION
    	"An user action to reset all the accounting counter contains to value zero"
    --CONFIGURABLE
    ::= { usrUserManGroup 138 }

-- The usrUserManVTSTermTable is used to terminate a session using
-- the unique index key made up of usrUserManVTSTermUserName,
-- usrUserManVTSTermSessionId, usrUserManVTSTermDynamicIpAddress,
-- and usrUserManVTSTermSessionKey.

 	usrUserManVTSTermTable	OBJECT-TYPE
	SYNTAX	SEQUENCE OF UsrUserManVTSTermEntry
	ACCESS	not-accessible
	STATUS	mandatory
	DESCRIPTION
		""
	::= { usrUserManGroup 139 }

	usrUserManVTSTermEntry	OBJECT-TYPE
	SYNTAX	UsrUserManVTSTermEntry
	ACCESS	not-accessible
	STATUS	mandatory
	DESCRIPTION
		""
	INDEX	{ usrUserManVTSTermUserName, usrUserManVTSTermSessionId,
			  usrUserManVTSTermDynamicIpAddress, usrUserManVTSTermSessionKey }
	::= { usrUserManVTSTermTable 1 }
		
	UsrUserManVTSTermEntry ::= 
	SEQUENCE {
	usrUserManVTSTermUserName
		UsrUserName,
	usrUserManVTSTermSessionId
		OCTET STRING,
	usrUserManVTSTermDynamicIpAddress
		IpAddress,
	usrUserManVTSTermSessionKey
		OCTET STRING,
	usrUserManVTSTermAction
		INTEGER
	}

	usrUserManVTSTermUserName	OBJECT-TYPE
	SYNTAX	UsrUserName
	ACCESS	not-accessible
	STATUS	mandatory
	DESCRIPTION
		"The users name"
	::= { usrUserManVTSTermEntry 1 }

	usrUserManVTSTermSessionId	OBJECT-TYPE
	SYNTAX	OCTET STRING 
	ACCESS	not-accessible
	STATUS	mandatory
	DESCRIPTION
		"The unique id for the active session"
	::= { usrUserManVTSTermEntry 2 }

	usrUserManVTSTermDynamicIpAddress	OBJECT-TYPE
	SYNTAX	IpAddress
	ACCESS	not-accessible
	STATUS	mandatory
	DESCRIPTION
		"The dynamic IP address for the active session"
	::= { usrUserManVTSTermEntry 3 }
		
	usrUserManVTSTermSessionKey	OBJECT-TYPE
	SYNTAX	OCTET STRING (SIZE(16))
	ACCESS	not-accessible
	STATUS	mandatory
	DESCRIPTION
		"A unique key to identify the active session"
	::= { usrUserManVTSTermEntry 4 }

	usrUserManVTSTermAction	OBJECT-TYPE
	SYNTAX	INTEGER {
		disconnectSession(1)
		}
	ACCESS	write-only
	STATUS	mandatory
	DESCRIPTION
		"The action to perform on the active session."
	::= { usrUserManVTSTermEntry 5 }

-- The usrUserManVTSVerifyTable is used to determin if a session
-- is still active.

 	usrUserManVTSVerifyTable	OBJECT-TYPE
	SYNTAX	SEQUENCE OF UsrUserManVTSVerifyEntry
	ACCESS	not-accessible
	STATUS	mandatory
	DESCRIPTION
		""
	::= { usrUserManGroup 140 }

	usrUserManVTSVerifyEntry	OBJECT-TYPE
	SYNTAX	UsrUserManVTSVerifyEntry
	ACCESS	not-accessible
	STATUS	mandatory
	DESCRIPTION
		""
	INDEX	{ usrUserManVTSVerifySessionId }
	::= { usrUserManVTSVerifyTable 1 }
		
	UsrUserManVTSVerifyEntry ::= 
	SEQUENCE {
	usrUserManVTSVerifySessionId
		OCTET STRING,
	usrUserManVTSVerifyUserName
		UsrUserName
	}

	usrUserManVTSVerifySessionId	OBJECT-TYPE
	SYNTAX	OCTET STRING 
	ACCESS	not-accessible
	STATUS	mandatory
	DESCRIPTION
		"The unique id for the active session"
	::= { usrUserManVTSVerifyEntry 1 }

	usrUserManVTSVerifyUserName	OBJECT-TYPE
	SYNTAX	UsrUserName
	ACCESS	read-only
	STATUS	mandatory
	DESCRIPTION
		"The users name"
	::= { usrUserManVTSVerifyEntry 2 }
	
        usrUserManMaxLocalUsers      OBJECT-TYPE
        SYNTAX  INTEGER
        ACCESS  read-write
        STATUS  mandatory
        DESCRIPTION
                "Maximum Local users that may be supported on the card"
                DEFVAL { 450 }
        --CONFIGURABLE
        ::= { usrUserManGroup 141 }

-- Following MIB Objects are added for Resource Management Feature.
        
  usrUserManRadiusSrcPortAuth  OBJECT-TYPE
    SYNTAX  TruthValue
    ACCESS  read-write
    STATUS  mandatory
    DESCRIPTION
        "This flag state whether to use check the response radius
         source port same at that configured in the system. The
         default value is TRUE"
    --CONFIGURABLE
    ::= { usrUserManGroup 142 }
 
    usrUserManRadiusUseRadUsername  OBJECT-TYPE
    SYNTAX  TruthValue
    ACCESS  read-write
    STATUS  mandatory
    DESCRIPTION
        "This flag states whether to use the radius supplied username in the
         access-accept packet to override the username in the request packet.
         The default value is FALSE."
    --CONFIGURABLE
    ::= { usrUserManGroup 143 }
 

        usrResourceMgmtState      OBJECT-TYPE
    	SYNTAX  INTEGER {
            enabled(1),
            disabled(2)
        }
        ACCESS  read-write
        STATUS  mandatory
        DESCRIPTION
                "Whether the Resource Management is enabled or disabled."
                DEFVAL { disabled }
        --CONFIGURABLE
        ::= { usrUserManGroup 144 }

        usrResourceMgmtQueriesReceivedPrimary      OBJECT-TYPE
    	SYNTAX  INTEGER 
        ACCESS  read-only
        STATUS  mandatory
        DESCRIPTION
                "Number of Resource Management Queries received from the Primary server."
                DEFVAL { 0 }
        ::= { usrUserManGroup 145 }

        usrResourceMgmtQueryResponsesPrimary      OBJECT-TYPE
    	SYNTAX  INTEGER 
        ACCESS  read-only
        STATUS  mandatory
        DESCRIPTION
                "Number of Resource Management Query Responses sent to the Primary server."
                DEFVAL { 0 }
        ::= { usrUserManGroup 146 }

        usrResourceMgmtReclaimsReceivedPrimary      OBJECT-TYPE
    	SYNTAX  INTEGER 
        ACCESS  read-only
        STATUS  mandatory
        DESCRIPTION
                "Number of Resource Management Reclaims received from the Primary server."
                DEFVAL { 0 }
        ::= { usrUserManGroup 147 }

        usrResourceMgmtFreeSendPrimary      OBJECT-TYPE
    	SYNTAX  INTEGER 
        ACCESS  read-only
        STATUS  mandatory
        DESCRIPTION
                "Number of successful Resource Management Frees sent to the Primary server."
                DEFVAL { 0 }
        ::= { usrUserManGroup 148 }

        usrResourceMgmtFreeRexmitPrimary      OBJECT-TYPE
    	SYNTAX  INTEGER 
        ACCESS  read-only
        STATUS  mandatory
        DESCRIPTION
                "Number of Resource Management Frees retransmitted to the Primary server."
                DEFVAL { 0 }
        ::= { usrUserManGroup 149 }

        usrResourceMgmtQueriesReceivedSecondary      OBJECT-TYPE
    	SYNTAX  INTEGER 
        ACCESS  read-only
        STATUS  mandatory
        DESCRIPTION
                "Number of Resource Management Queries received from the Secondary server."
                DEFVAL { 0 }
        ::= { usrUserManGroup 150 }

        usrResourceMgmtQueryResponsesSecondary      OBJECT-TYPE
    	SYNTAX  INTEGER 
        ACCESS  read-only
        STATUS  mandatory
        DESCRIPTION
                "Number of Resource Management Query Responses sent to the Secondary server."
                DEFVAL { 0 }
        ::= { usrUserManGroup 151 }

        usrResourceMgmtReclaimsReceivedSecondary      OBJECT-TYPE
    	SYNTAX  INTEGER 
        ACCESS  read-only
        STATUS  mandatory
        DESCRIPTION
                "Number of Resource Management Reclaims received from the Secondary server."
                DEFVAL { 0 }
        ::= { usrUserManGroup 152 }

        usrResourceMgmtFreeSendSecondary      OBJECT-TYPE
    	SYNTAX  INTEGER 
        ACCESS  read-only
        STATUS  mandatory
        DESCRIPTION
                "Number of successful Resource Management Frees sent to the Secondary server."
                DEFVAL { 0 }
        ::= { usrUserManGroup 153 }

        usrResourceMgmtFreeRexmitSecondary      OBJECT-TYPE
    	SYNTAX  INTEGER 
        ACCESS  read-only
        STATUS  mandatory
        DESCRIPTION
                "Number of Resource Management Frees retransmitted to the Secondary server."
                DEFVAL { 0 }
        ::= { usrUserManGroup 154 }

        usrResourceMgmtQueriesReceivedTertiary      OBJECT-TYPE
    	SYNTAX  INTEGER 
        ACCESS  read-only
        STATUS  mandatory
        DESCRIPTION
                "Number of Resource Management Queries received from the Tertiary server."
                DEFVAL { 0 }
        ::= { usrUserManGroup 155 }

        usrResourceMgmtQueryResponsesTertiary      OBJECT-TYPE
    	SYNTAX  INTEGER 
        ACCESS  read-only
        STATUS  mandatory
        DESCRIPTION
                "Number of Resource Management Query Responses sent to the Tertiary server."
                DEFVAL { 0 }
        ::= { usrUserManGroup 156 }

        usrResourceMgmtReclaimsReceivedTertiary      OBJECT-TYPE
    	SYNTAX  INTEGER 
        ACCESS  read-only
        STATUS  mandatory
        DESCRIPTION
                "Number of Resource Management Reclaims received from the Tertiary server."
                DEFVAL { 0 }
        ::= { usrUserManGroup 157 }

        usrResourceMgmtFreeSendTertiary      OBJECT-TYPE
    	SYNTAX  INTEGER 
        ACCESS  read-only
        STATUS  mandatory
        DESCRIPTION
                "Number of successful Resource Management Frees sent to the Tertiary server."
                DEFVAL { 0 }
        ::= { usrUserManGroup 158 }

        usrResourceMgmtFreeRexmitTertiary      OBJECT-TYPE
    	SYNTAX  INTEGER 
        ACCESS  read-only
        STATUS  mandatory
        DESCRIPTION
                "Number of Resource Management Frees retransmitted to the Tertiary server."
                DEFVAL { 0 }
        ::= { usrUserManGroup 159 }

    usrResetResourceMgmtCountersToZero		OBJECT-TYPE
    SYNTAX	INTEGER
    ACCESS	write-only
    STATUS	mandatory
    DESCRIPTION
    	"An user action to reset all the resource management counters to zero"
    ::= { usrUserManGroup 161 }

    usrResetResourceMgmtCountersResetTime	OBJECT-TYPE
    SYNTAX	OCTET STRING (SIZE (12))
    ACCESS	read-only
    STATUS	mandatory
    DESCRIPTION
    	"Time the resource management counters were last reset to value zero."
    ::= { usrUserManGroup 162 }
    usrRadiusAccountingAttributeStyle OBJECT-TYPE
    SYNTAX  INTEGER {
            standard(1),
            netserver(3)
            }
    ACCESS  read-write
    STATUS  mandatory
    DESCRIPTION
    "Takes STANDARD or Netserver style for accounting attribute values"
    --CONFIGURABLE
    ::= { usrUserManGroup 160 }

    usrRadiusSendAcctUnauthRecord      OBJECT-TYPE
    SYNTAX  TruthValue
    ACCESS  read-write
    STATUS  mandatory
    DESCRIPTION
           "Whether the Sending unauthenticated STOP records is enabled or disabled."
    --CONFIGURABLE
    ::= { usrUserManGroup 165 }

-- Accounting Counters for UUNET

	usrUserManRadiusAcctPrimaryServerGroupCounterResetTime    OBJECT-TYPE
			SYNTAX  OCTET STRING (SIZE (12))
			ACCESS  read-write
			STATUS  mandatory
			DESCRIPTION
				"Daily time we reset all the accounting counters 
				 for primary group  to value zero"
			--CONFIGURABLE
			::= { usrUserManGroup  163 }

	usrUserManRadiusAcctSecondaryServerGroupCounterResetTime    OBJECT-TYPE
			SYNTAX  OCTET STRING (SIZE (12))
			ACCESS  read-write
			STATUS  mandatory
			DESCRIPTION
				"Daily time we reset all the accounting counters
				 for secondary group to value zero"
			--CONFIGURABLE
			::= { usrUserManGroup  164 }

        usrUserManRadiusDefaultUserAcct OBJECT-TYPE
                        SYNTAX  TruthValue
                        ACCESS  read-write
                        STATUS  mandatory
                        DESCRIPTION
                                "Whether to send accounting records for default users"
                        --CONFIGURABLE
                        ::= { usrUserManGroup 166 }

        usrUserManTunnelAuthenName   OBJECT-TYPE
        SYNTAX  INTEGER {
                        enabled(1),
                        disabled(2)
                }
        ACCESS  read-write
        STATUS  mandatory
        DESCRIPTION
                "This option is used for l2tp tunnel authentication.
                 Default/Disabled -- System Transmit Authentication Name
                 Enabled -- Used domain name or tunnel name "
        --CONFIGURABLE
        ::= { usrUserManGroup 167 }
         
        usrPrimaryAuthContactInterval      OBJECT-TYPE
        SYNTAX  INTEGER 
        ACCESS  read-only
        STATUS  mandatory
        DESCRIPTION
                "Number of seconds since the Primary Radius authentication server was last contacted."
                DEFVAL { -1 }
        ::= { usrUserManGroup 168 }

        usrSecondaryAuthContactInterval      OBJECT-TYPE
        SYNTAX  INTEGER 
        ACCESS  read-only
        STATUS  mandatory
        DESCRIPTION
                "Number of seconds since the Secondary Radius authentication server was last contacted."
                DEFVAL { -1 }
        ::= { usrUserManGroup 169 }

        usrTertiaryAuthContactInterval      OBJECT-TYPE
        SYNTAX  INTEGER 
        ACCESS  read-only
        STATUS  mandatory
        DESCRIPTION
                "Number of seconds since the Tertiary Radius authentication server was last contacted."
                DEFVAL { -1 }
        ::= { usrUserManGroup 170 }

        usrAcctGrp1PriContactInterval      OBJECT-TYPE
        SYNTAX  INTEGER 
        ACCESS  read-only
        STATUS  mandatory
        DESCRIPTION
                "Number of seconds since the Group 1 Primary Accounting server was last contacted."
                DEFVAL { -1 }
        ::= { usrUserManGroup 171 }

        usrAcctGrp1FrstBkpContactInterval      OBJECT-TYPE
        SYNTAX  INTEGER 
        ACCESS  read-only
        STATUS  mandatory
        DESCRIPTION
                "Number of seconds since the Group 1 First backup accounting server was last contacted."
                DEFVAL { -1 }
        ::= { usrUserManGroup 172 }

        usrAcctGrp1SecBkpContactInterval      OBJECT-TYPE
        SYNTAX  INTEGER 
        ACCESS  read-only
        STATUS  mandatory
        DESCRIPTION
                "Number of seconds since the Group 1 Second Backup Accounting server was last contacted."
                DEFVAL { -1 }
        ::= { usrUserManGroup 173 }

        usrAcctGrp2PriContactInterval      OBJECT-TYPE
        SYNTAX  INTEGER 
        ACCESS  read-only
        STATUS  mandatory
        DESCRIPTION
                "Number of seconds since the Group 2 Primary Accounting server was last contacted."
                DEFVAL { -1 }
        ::= { usrUserManGroup 174 }

        usrAcctGrp2FrstBkpContactInterval      OBJECT-TYPE
        SYNTAX  INTEGER 
        ACCESS  read-only
        STATUS  mandatory
        DESCRIPTION
                "Number of seconds since the Group 2 First backup accounting server was last contacted."
                DEFVAL { -1 }
        ::= { usrUserManGroup 175 }

        usrAcctGrp2SecBkpContactInterval      OBJECT-TYPE
        SYNTAX  INTEGER 
        ACCESS  read-only
        STATUS  mandatory
        DESCRIPTION
                "Number of seconds since the Group 2 Second backup accounting server was last contacted."
                DEFVAL { -1 }
        ::= { usrUserManGroup 176 }
 
    usrUserManSyslogFormat  OBJECT-TYPE
    SYNTAX  INTEGER
    ACCESS  read-write
    STATUS  mandatory
    DESCRIPTION
        "Syslog message Format. Specifies which syslog style
        format is in effect out of the possible range of
        selections."
    --CONFIGURABLE
    ::= { usrUserManGroup 177 }

    usrUserManIPOnlyForPrimaryLink    OBJECT-TYPE      
        SYNTAX  INTEGER {
             disabled(0),    
             enabled(1)
         }
         ACCESS  read-write
         STATUS  mandatory
         DESCRIPTION 
             "This is the switch to enable/disable sending 0.0.0.0 ip address
              for any non primary link in the accounting records. "
         --CONFIGURABLE
         ::= { usrUserManGroup 178 }

    usrRadiusAccountingPrioritiseFirstServer    OBJECT-TYPE
        SYNTAX  INTEGER {
            enabled(1),
            disabled(2)
         }
         ACCESS  read-write
         STATUS  mandatory
         DESCRIPTION
             "This switch is to enable/disable prioritisation of the first server
              in each server group"
         --CONFIGURABLE
         ::= { usrUserManGroup 179 }

	usrUserManOnlySTOPforFailedService    OBJECT-TYPE      
        SYNTAX  INTEGER {
             disabled(0),    
             enabled(1)
         }
         ACCESS  read-write
         STATUS  mandatory
         DESCRIPTION 
             "After successful authentication, if the required service
			  start for the user fails, just send acct STOP"
         --CONFIGURABLE
         ::= { usrUserManGroup 180 }

    usrRadiusSendAcctAuthServiceType      OBJECT-TYPE
    SYNTAX  TruthValue
    ACCESS  read-write
    STATUS  mandatory
    DESCRIPTION
           "Whether the Sending of service type in auth-request enabled or disabled."
    --CONFIGURABLE
    ::= { usrUserManGroup 181 }

    usrRadiusAuthStatusPollInitInterval      OBJECT-TYPE
    SYNTAX  INTEGER
    ACCESS  read-write
    STATUS  mandatory
    DESCRIPTION
           "The Initial Interval for Auth Status Polling"
    --CONFIGURABLE
    ::= { usrUserManGroup 182 }

    usrRadiusAuthStatusPollMaxInterval      OBJECT-TYPE
    SYNTAX  INTEGER
    ACCESS  read-write
    STATUS  mandatory
    DESCRIPTION
           "The Maximum Interval for Auth Status Polling"
    --CONFIGURABLE
    ::= { usrUserManGroup 183 }

    usrRadiusAuthStatusPollIncInterval      OBJECT-TYPE
    SYNTAX  INTEGER
    ACCESS  read-write
    STATUS  mandatory
    DESCRIPTION
           "The interval increment for Auth Status Polling"
    --CONFIGURABLE
    ::= { usrUserManGroup 184 }

    usrRadiusAuthStatusServerUpRetry      OBJECT-TYPE
    SYNTAX  INTEGER
    ACCESS  read-write
    STATUS  mandatory
    DESCRIPTION
           "The number of status server tries before making the server from down to up"
    --CONFIGURABLE
    ::= { usrUserManGroup 185 }

    usrRadiusAuthStatusServerDownRetry      OBJECT-TYPE
    SYNTAX  INTEGER
    ACCESS  read-write
    STATUS  mandatory
    DESCRIPTION
           "The number of status server retries before making the server from up to down"
    --CONFIGURABLE
    ::= { usrUserManGroup 186 }

    usrRadiusAuthStatusPrimServer      OBJECT-TYPE
    SYNTAX  INTEGER
    ACCESS  read-only
    STATUS  mandatory
    DESCRIPTION
           "The status of the primary server "
    ::= { usrUserManGroup 187 }

    usrRadiusAuthStatusSecServer      OBJECT-TYPE
    SYNTAX  INTEGER
    ACCESS  read-only
    STATUS  mandatory
    DESCRIPTION
           "The status of the secondary server "
    ::= { usrUserManGroup 188 }

    usrRadiusAuthStatusTerServer      OBJECT-TYPE
    SYNTAX  INTEGER
    ACCESS  read-only
    STATUS  mandatory
    DESCRIPTION
           "The status of the tertiary server "
    ::= { usrUserManGroup 189 }


    usrRadiusDNISAuthServiceType      OBJECT-TYPE
    SYNTAX  INTEGER
    ACCESS  read-write
    STATUS  mandatory
    DESCRIPTION
           "The service type set fot DNIS authenticaton request.
			Default is 10"
    --CONFIGURABLE
    ::= { usrUserManGroup 190 }
    
	usrRadiusVTPAccountingFlag     OBJECT-TYPE
    SYNTAX  INTEGER
    ACCESS  read-write
    STATUS  mandatory
    DESCRIPTION
			"Flag which decides whether to send acct records
			 for VTP tunnel users or not"
    --CONFIGURABLE
    ::= { usrUserManGroup 194 }

    uumAAAGlobalOpStatusRenewIntvl    OBJECT-TYPE
        SYNTAX  INTEGER (0..65536)
        ACCESS  read-write
        STATUS  mandatory
        DESCRIPTION
        " Time to reenable operationally down servers"
        --CONFIGURABLE
         ::= { usrUserManGroup 199 }

 uumAAAGlobalTotalRetransmit     OBJECT-TYPE
        SYNTAX  INTEGER  (0..60)
        ACCESS  read-write
        STATUS  mandatory
        DESCRIPTION
        "Total Retransmit, same as RadiusOthers.radius_retrans"
        --CONFIGURABLE
         ::= { usrUserManGroup 200 }


	usrPortIdStyle  OBJECT-TYPE
        SYNTAX  INTEGER {
			contiguous(1),
			density-based(2)
		} 
        ACCESS  read-write
        STATUS  mandatory
        DESCRIPTION
        "Port Id generation style. The value of 1 means that the port id will
         be computed based on the density of ports. The value 2 means the
         lowest port id will be given from a contiguous space"
        DEFVAL { 1 }      
        --CONFIGURABLE   
        ::= { usrUserManGroup 201 }

	usrResourceReclaimStyle  OBJECT-TYPE
        SYNTAX  INTEGER  {
			draft-style(1),
			mci-style(2)
		} 
        ACCESS  read-write
        STATUS  mandatory
        DESCRIPTION
        "Whether resource reclaim is done in MCI style or the IETF draft style. 		Default is DRAFT style"
        DEFVAL { 1 }      
        --CONFIGURABLE   
        ::= { usrUserManGroup 202 }

	usrAuthSyslogState  OBJECT-TYPE
	SYNTAX	INTEGER {
			enabled(1),
			disabled(2)
		} 
        ACCESS  read-write
        STATUS  mandatory
        DESCRIPTION
        "This value states whether the Authentication information is sent in 
	the syslogs."
        DEFVAL { 2 }      
        --CONFIGURABLE   
        ::= { usrUserManGroup 203 }

	usrAcctSyslogState  OBJECT-TYPE
	SYNTAX	INTEGER {
			enabled(1),
			disabled(2)
		} 
        ACCESS  read-write
        STATUS  mandatory
        DESCRIPTION
        "This value states whether the Accounting information is sent in 
	the syslogs."
        DEFVAL { 2 }      
        --CONFIGURABLE   
        ::= { usrUserManGroup 204 }

	usrAuthSyslogReset  OBJECT-TYPE
	SYNTAX	INTEGER {
			enabled(1),
			disabled(2)
		} 
        ACCESS  read-write
        STATUS  mandatory
        DESCRIPTION
        "This value states whether or not the authentication counters will be 
	reset at a configured interval."
        DEFVAL { 2 }      
        --CONFIGURABLE   
        ::= { usrUserManGroup 205 }

	usrAcctSyslogReset  OBJECT-TYPE
	SYNTAX	INTEGER {
			enabled(1),
			disabled(2)
		} 
        ACCESS  read-write
        STATUS  mandatory
        DESCRIPTION
        "This value states whether or not the accounting counters will be 
	reset at a configured interval."
        DEFVAL { 2 }      
        --CONFIGURABLE   
        ::= { usrUserManGroup 206 }

	usrAuthSyslogFrequency  OBJECT-TYPE
	SYNTAX	INTEGER { 
			one-hour(0),
			six-hours(1),
			twelve-hours(2),
			twentyfour-hours(3),
			five-days(4)
		} 
        ACCESS  read-write
        STATUS  mandatory
        DESCRIPTION
        "This object specifies the time interval after which the authentication
	counters will be reset to zero."
        DEFVAL { 2 }      
        --CONFIGURABLE   
        ::= { usrUserManGroup 207 }
	
	usrAcctSyslogFrequency  OBJECT-TYPE
	SYNTAX	INTEGER { 
			one-hour(0),
			six-hours(1),
			twelve-hours(2),
			twentyfour-hours(3),
			five-days(4)
		} 
        ACCESS  read-write
        STATUS  mandatory
        DESCRIPTION
        "This object specifies the time interval after which the accounting
	counters will be reset to zero."
        DEFVAL { 2 }      
        --CONFIGURABLE   
        ::= { usrUserManGroup 208 }

        usrUserManRadiusPrimaryPref     OBJECT-TYPE
        SYNTAX  INTEGER (1..3)
        ACCESS  read-write
        STATUS  mandatory
        DESCRIPTION
                "Primary Auth  Server preference value when using PREFERED
                 algorithm"     
        --CONFIGURABLE
        ::= { usrUserManGroup 209 }
        
        usrUserManRadiusSecondaryPref   OBJECT-TYPE
        SYNTAX  INTEGER (1..3)
        ACCESS  read-write
        STATUS  mandatory
        DESCRIPTION
                "Secondary Auth  Server preference value when using PREFERED
                 algorithm"     
        --CONFIGURABLE
        ::= { usrUserManGroup 210 }
        
        usrUserManRadiusTertiaryPref    OBJECT-TYPE
        SYNTAX  INTEGER (1..3)
        ACCESS  read-write
        STATUS  mandatory
        DESCRIPTION
                "Tertiary Auth  Server preference value when using PREFERED
                 algorithm"     
        --CONFIGURABLE
        ::= { usrUserManGroup 211 }
        
        usrUserManPerServerRetryCount   OBJECT-TYPE
        SYNTAX  INTEGER
        ACCESS  read-write
        STATUS  mandatory
        DESCRIPTION
                "Per Server Retry Count when using PREFERED algorithm"  
        --CONFIGURABLE
        ::= { usrUserManGroup 212 }
        
        usrUserManPerAcctServerRetryCount       OBJECT-TYPE
        SYNTAX  INTEGER
        ACCESS  read-write
        STATUS  mandatory
        DESCRIPTION
                "Per Server Retry Count for Acct Servers"       
        --CONFIGURABLE
        ::= { usrUserManGroup 213 }

        usrUserManRadiusAcctCDRState     OBJECT-TYPE
        SYNTAX  INTEGER {
                        enabled(1),
                        disabled(2)
                        }
        ACCESS  read-write
        STATUS  mandatory
        DESCRIPTION
                "Indicates whether to send Call Detail Record in ACCT Stop req." 
        --CONFIGURABLE
        ::= { usrUserManGroup 214 }

        usrUserManRadiusAcctAggregateRoundRobinCount     OBJECT-TYPE
        SYNTAX  INTEGER (0..2147483647)
        ACCESS  read-only
        STATUS  mandatory
        DESCRIPTION
                "The total number of times the servers are switched in the 
		primary and secondary server group"
        ::= { usrUserManGroup 215 }
 
        usrUserManRadiusAcctAggregatePacketDiscardCount  OBJECT-TYPE
        SYNTAX  INTEGER (0..2147483647)
        ACCESS  read-only
        STATUS  mandatory
        DESCRIPTION
                "The total number of packets discarded in the primary and 
		secondary server group"
        ::= { usrUserManGroup 216 }
 
        usrUserManRadiusAcctAverageQueuePercentFull    OBJECT-TYPE
        SYNTAX  INTEGER (0..100)
        ACCESS  read-only
        STATUS  mandatory
        DESCRIPTION
                "The average of percentage of the queue filled in the primary 
		and secondary server group"
        ::= { usrUserManGroup 217 }
 
        usrUserManRadiusAcctAggregateOutstandingPacketCount      OBJECT-TYPE
        SYNTAX  INTEGER (0..2147483647)
        ACCESS  read-only
        STATUS  mandatory
        DESCRIPTION
                "The total number of packets outstanding in the primary 
		and secondary server group"
        ::= { usrUserManGroup 218 }

    uumPrioratizeAuthServer     OBJECT-TYPE
        SYNTAX  INTEGER
        ACCESS  read-write
        STATUS  mandatory
        DESCRIPTION   
        "In Round Robin Feature, Try the first auth server initially"
        --CONFIGURABLE
         ::= { usrUserManGroup 219 }
 
    usrResourceFreeForTunnelInitiator      OBJECT-TYPE
     	SYNTAX  INTEGER {
            enabled(1),
            disabled(2)
        }
        ACCESS  read-write
        STATUS  mandatory
        DESCRIPTION
                "For a tunneled call(l2tp/pptp) user get authenticated at both
                 call initiator and call terminator thus uses 2 resources. If
                 enabled resources at the initiator is freed immediatly after
                 authentication else only when user goes away."
                DEFVAL { enabled }
        --CONFIGURABLE
        ::= { usrUserManGroup 220 }

        usrRadiusNasPortStyle OBJECT-TYPE
        SYNTAX  INTEGER {
                standard(1),
                format-one(2)
                }
        ACCESS  read-write
        STATUS  mandatory
        DESCRIPTION
				"Takes STANDARD or format_one(UUNET) style for attribute values"
        --CONFIGURABLE
        ::= { usrUserManGroup 234 }

	usrRebootIndicationStyle  OBJECT-TYPE
        SYNTAX  INTEGER {
		fall-through(1),
		preferred-server(2)
	} 
        ACCESS  read-write
        STATUS  mandatory
        DESCRIPTION
        "Whether reboot indiaction is sent in fall-through fashion or in 
		round-robin manner according to server preference. 
		Default is fall-through style"
        DEFVAL { 1 }      
        --CONFIGURABLE   
        ::= { usrUserManGroup 222 }

        usrUserManRadiusAcctPrimaryPref    OBJECT-TYPE
        SYNTAX  INTEGER (1..3)
        ACCESS  read-write
        STATUS  mandatory
        DESCRIPTION
                "Primary Acct  Server preference value"
        --CONFIGURABLE
        ::= { usrUserManGroup 223 }
        
		usrUserManRadiusAcctSecondaryPref    OBJECT-TYPE
        SYNTAX  INTEGER (1..3)
        ACCESS  read-write
        STATUS  mandatory
        DESCRIPTION
                "Secondary Acct  Server preference value"
        --CONFIGURABLE
        ::= { usrUserManGroup 224 }
		
		usrUserManRadiusAcctBackupPrimaryFirstPref    OBJECT-TYPE
        SYNTAX  INTEGER (1..3)
        ACCESS  read-write
        STATUS  mandatory
        DESCRIPTION
                "Acct  Server preference value"
        --CONFIGURABLE
        ::= { usrUserManGroup 225 }
		
		usrUserManRadiusAcctBackupPrimarySecondPref    OBJECT-TYPE
        SYNTAX  INTEGER (1..3)
        ACCESS  read-write
        STATUS  mandatory
        DESCRIPTION
                "Acct  Server preference value"
        --CONFIGURABLE
        ::= { usrUserManGroup 226 }
		
		usrUserManRadiusAcctBackupSecondaryFirstPref    OBJECT-TYPE
        SYNTAX  INTEGER (1..3)
        ACCESS  read-write
        STATUS  mandatory
        DESCRIPTION
                "Acct  Server preference value"
        --CONFIGURABLE
        ::= { usrUserManGroup 227 }
		
		usrUserManRadiusAcctBackupSecondarySecondPref    OBJECT-TYPE
        SYNTAX  INTEGER (1..3)
        ACCESS  read-write
        STATUS  mandatory
        DESCRIPTION
                "Acct  Server preference value"
        --CONFIGURABLE
        ::= { usrUserManGroup 228 }

	usrUserManAuthFailTrapsState  OBJECT-TYPE
         SYNTAX  INTEGER {
                enabled(1),
                disabled(2)
                }
         ACCESS  read-write
         STATUS  mandatory
         DESCRIPTION
             "Whether the User Authentication Failure Trap is enabled or disabled."
         DEFVAL { enabled }
         --CONFIGURABLE
         ::= { usrUserManGroup 231 }

	usrRadiusDNISAuthNasPortStyle  OBJECT-TYPE
        SYNTAX  INTEGER (0..1) 
        ACCESS  read-write
        STATUS  mandatory
        DESCRIPTION
        "DNIS authentication nas port , default means fill the correct
		 value. null-value means, always send 0 for this attribute
		 during the dnis authentication request"
        DEFVAL { 1 }      
        --CONFIGURABLE   
        ::= { usrUserManGroup 237 }

	usrUserManReportedSpanDensity	OBJECT-TYPE
	SYNTAX	INTEGER (1..33)
	ACCESS	read-write
	STATUS	mandatory
	DESCRIPTION
		"Used when reporting RADIUS NAS-PORT attribute.
	         The reported NAS-PORT attribute for a call is
		 computed as: <slot#> * spanDensity[slot#] * usrUserManReportedSpanDensity +
                              <span#> *  usrUserManReportedSpanDensity +
		              <channel#> + usrUserManSlotSpanChanOffset
		 Default value is 24."
     	--CONFIGURABLE
	::= { usrUserManGroup 238 }

	usrUserManSlotNo OBJECT-TYPE
	SYNTAX	INTEGER (1..16)
	ACCESS	read-write
	STATUS	mandatory
	DESCRIPTION
		"The slot Number"
	--CONFIGURABLE
	::= { usrUserManGroup 239 }

	usrUserManNoOfSpans OBJECT-TYPE
	SYNTAX	OCTET STRING (SIZE (1..16))
	ACCESS	read-write
	STATUS	mandatory
	DESCRIPTION
		"The No of spans in a slot"
	--CONFIGURABLE
	::= { usrUserManGroup 240 }

	usrUserManSpanDensityStyle OBJECT-TYPE
	SYNTAX	INTEGER {
                global(1),
                spanbased(2)
                }
	ACCESS	read-write
	STATUS	mandatory
	DESCRIPTION
		"The span density style"
	--CONFIGURABLE
	::= { usrUserManGroup 241 }
    
	usrRadiusCFGAuthServiceType      OBJECT-TYPE
    SYNTAX  INTEGER
    ACCESS  read-write
    STATUS  mandatory
    DESCRIPTION
           "The service type set fot  authenticaton request.
			Default 0 means no value set."
    --CONFIGURABLE
    ::= { usrUserManGroup 242 }

    usrUserManEnhancedTunnelingAcct OBJECT-TYPE
    SYNTAX  TruthValue
    ACCESS  read-write
    STATUS  mandatory
    DESCRIPTION
        "If set to true(1), the new accounting status type packets for
         tunneled calls will be sent. if set to false(2), they will not
         be sent."
    DEFVAL { true }
    --CONFIGURABLE
    ::= { usrUserManGroup 243 }

     usrReturnCallRejectCode  OBJECT-TYPE
         SYNTAX INTEGER(0|1)   
        
         ACCESS  read-write      
         STATUS  mandatory     
         DESCRIPTION
             "If the value is 1 the HARC will return the call reject code to the DSP card, otherwise if it is zero it will disable the call reject code feature"
         --CONFIGURABLE
         ::= { usrUserManGroup 250 }	


	usrUserManAuthFailure TRAP-TYPE
        ENTERPRISE  usrUserManTraps
        VARIABLES   {    
                usrUserManRadiusIP,
                usrUserManRadiusAltIP,
                usrUserManRadiusTertiaryIP
        }
        DESCRIPTION     "This trap is generated when 
			authentication fails for a user."
        --#TYPE "Alarm"
        ::= 1

	usrUserManRadiusBusyoutTrap TRAP-TYPE  
        ENTERPRISE  usrUserManTraps
        VARIABLES   {     
                usrUserManRadiusIP,
                usrUserManRadiusAltIP,
                usrUserManRadiusTertiaryIP,
                usrUserManRadiusAcctIP,
                usrUserManRadiusAcctFirstBackupIP,
                usrUserManRadiusAcctSecondBackupIP,
                usrUserManRadiusAcctAltIP, 
                usrUserManRadiusAcctAltFirstBackupIP,
                usrUserManRadiusAcctAltSecondBackupIP
        }
        DESCRIPTION     "This trap is generated when none of the authentication or accounting
servers can be contacted from the NAS and we mark the ports busy."
        --#TYPE "Alarm"
        ::= 2 
END
--
--	usr_config.mib - The U.S. Robotics Configuration MIB
--
--
-- Author:         Jim Halpin
--
-- $Id: usr_config.mib,v 1.39.2.12 1998/06/01 23:35:25 eshaji Exp $
--
--  | Copyright (c) 1995-97 U.S. Robotics Access Corp., Skokie, IL 60076   |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-CONFIG-MIB DEFINITIONS ::= BEGIN

	IMPORTS
          OBJECT-TYPE
                  FROM RFC-1212
		TRAP-TYPE
			   FROM RFC-1215
		TruthValue
			   FROM SNMPv2-TC
          DisplayString, usrConfig, UsrConfigStatus, UsrNetLogicalId,
		UsrUserName
                  FROM USR-DEFINITIONS-MIB;


   -- textual conventions
   -- 
   -- textual conventions are like pre-processor macro in 'C'
   --        (i.e. #define statements)
   -- Use them to define your own 'datatypes'

   -- Network Encapsulation Types. This enumeration should match the one 
   -- in pilgrim/config/include/config_public.h

	UsrCfgEncapsulations ::= INTEGER {
						 none(0),
	                          ethernetII(1),
		  	    	           snap(2),
				           dsap(3),
				           ethernet8023Novell(4),
			     	      ppp(5),
			          	 frameRelay(6),
				           slip(7),
     	                     arap(8),	
          	                loop(9),
                               frameRelayMgmt(10),
                               bridge(11),
                               atm1483(12),
                               atm1577(13),
                               atmLane(14),
                               mcns(15)
			}



   -- Begin managed object definitions here...

-- The Config Group



usrCfgVersion OBJECT-TYPE
	SYNTAX      DisplayString
	ACCESS      read-only
	STATUS      mandatory
	DESCRIPTION
		"The current software version of the Config Process."
::= { usrConfig 1}


usrCfgConfigFileName OBJECT-TYPE
	SYNTAX      DisplayString
	ACCESS      read-only
	STATUS      mandatory
	DESCRIPTION		
		"The name of a ConfigFile to read/write  permanent database records."
::= { usrConfig 2 }

usrCfgCFMStatusFlag  OBJECT-TYPE
	SYNTAX	  UsrConfigStatus
	ACCESS      read-write
	STATUS      mandatory
	DESCRIPTION
		"Setting the value of this object to `save' causes the values
		 of the Config Group to be written out to the current config
		 file, which is stored in the cfgConfigFile object. While
		 the new ConfigFile is being written, the config process
		 will set the value of this flag set to `saving''. Any
		 attempts to set the value while it is  not `normal'
		 (i.e. the file is currently being written to the
		 ConfigFile) while result in a badValue error being
		 returned. Setting the value to `normal' will result in no
		 action."
::= { usrConfig 3 }

usrCfgCFMStatusNetFlag  OBJECT-TYPE
	SYNTAX	UsrConfigStatus
	ACCESS      read-write
	STATUS      mandatory
	DESCRIPTION
		"Setting the value of this object to `save' causes the values
		 of all the Network Table entries to be written out to the
		 current config file, which is stored in the cfgConfigFile
		 object. While the new ConfigFile is being written, the config
		 process will set the value of this flag set to `saving''. Any
		 attempts to set the value while it is  not `normal'
		 (i.e. the file is currently being written to the
		 ConfigFile) while result in a badValue error being
		 returned. Setting the value to `normal' will result in no
		 action."
::= { usrConfig 4 }

usrCfgCFMStatusIfFlag  OBJECT-TYPE
	SYNTAX	UsrConfigStatus
	ACCESS      read-write
	STATUS      mandatory
	DESCRIPTION
		"Setting the value of this object to `save' causes the values
		 of all the IF Table entries to be written out to the
		 current config file, which is stored in the cfgConfigFile
		 object. While the new ConfigFile is being written, the config
		 process will set the value of this flag set to `saving''. Any
		 attempts to set the value while it is  not `normal'
		 (i.e. the file is currently being written to the
		 ConfigFile) while result in a badValue error being
		 returned. Setting the value to `normal' will result in no
		 action."
::= { usrConfig 5 }

usrCfgCFMStatusNetSvcFlag OBJECT-TYPE
	SYNTAX		UsrConfigStatus
	ACCESS      	read-write
	STATUS      	mandatory
	DESCRIPTION
		"Setting the value of this object to `save' causes the values
		 of the Network Service Table to be written out to the
		 current config file, which is stored in the usrCfgConfigFile
		 object. While the new ConfigFile is being written, the config
		 process will set the value of this flag set to `saving''. Any
		 attempts to set the value while it is  not `normal'
		 (i.e. the file is currently being written to the
		 ConfigFile) while result in a badValue error being
		 returned. Setting the value to `normal' will result in no
		 action."
::= { usrConfig 6 }

usrCfgNetTable OBJECT-TYPE
	SYNTAX     SEQUENCE OF UsrCfgNetEntry
	ACCESS     not-accessible
	STATUS     mandatory
	DESCRIPTION
		"A list of Networks currently configured in the Netserver
		 system."
::= { usrConfig 7 }

usrCfgNetEntry OBJECT-TYPE
	SYNTAX      UsrCfgNetEntry
	ACCESS      not-accessible
	STATUS      mandatory
	DESCRIPTION
		"An entry containing management information applicable to a
		 particular network."
	INDEX { usrCfgNetName }
::= { usrCfgNetTable 1}

UsrCfgNetEntry ::=
	SEQUENCE {
          usrCfgNetName DisplayString,
		usrCfgNetIfName DisplayString,
		usrCfgNetProtoType INTEGER,
		usrCfgNetEncapType UsrCfgEncapsulations,
		usrCfgNetAddress OCTET STRING,
		usrCfgNetStatus INTEGER,
          usrCfgNetLogicalId UsrNetLogicalId,
		usrCfgNetType INTEGER,
		usrCfgNetUserName UsrUserName,
		usrCfgNetCFMStatusFlag UsrConfigStatus,
		usrCfgNewNetIfName DisplayString,
		usrCfgNewNetAddress OCTET STRING,
		usrCfgNewNetEncapType UsrCfgEncapsulations,
		usrCfgNetRemoteAddress OCTET STRING,
		usrCfgNetWanType INTEGER
		}

usrCfgNetName OBJECT-TYPE
	SYNTAX      DisplayString (SIZE (1..32))
	ACCESS      not-accessible
	STATUS      mandatory
	DESCRIPTION
		"The name of this network. Network names can either be assigned
           by a network administrator when the Network is created. Or it will
           generated by the Configuration Process when it adds the network to
		 its internal table. Generated network names will be formed by
		 concatenating the ascii forms of the protocol name, network address
		 and port number separated by hyphens."
::= { usrCfgNetEntry 1}

usrCfgNetIfName OBJECT-TYPE
	SYNTAX      DisplayString (SIZE (1..32))
	ACCESS      read-write
	STATUS      mandatory
	DESCRIPTION
		"The name of the interface this network runs on top of."
	--CONFIGURABLE
::= { usrCfgNetEntry 2 }

usrCfgNetProtoType OBJECT-TYPE
	SYNTAX     INTEGER {
                         ip(1),
		               ipx(2),
		               at(3),
				     bridge(5),
					frameRelayMgmt(6),
					frameRelayDlci(7),
					ppp(8),
					slip(9)
			          }
	ACCESS     read-write
	STATUS     mandatory
	DESCRIPTION
		"The Level 3 protocol running over this network."
	--CONFIGURABLE
::= { usrCfgNetEntry 3 } 

usrCfgNetAddress OBJECT-TYPE
	SYNTAX      OCTET STRING
	ACCESS      read-write
	STATUS      mandatory
	DESCRIPTION
		"The address which identifies the network. The format of
		 this object is dependent on the protocol running on this
		 network."
	--CONFIGURABLE
::= { usrCfgNetEntry 4 }



usrCfgNetEncapType OBJECT-TYPE
	SYNTAX      UsrCfgEncapsulations
	ACCESS      read-write
	STATUS      mandatory
	DESCRIPTION
		"The type of encapsulation employed by this network."
	--CONFIGURABLE
::= { usrCfgNetEntry 5 }

usrCfgNetStatus OBJECT-TYPE
	SYNTAX      INTEGER {
					initializing(1),
					configuring(2),
					enable(3),  -- Set to this value to enable network 
			          enabling(4),
                         disable(5), -- Set to this value to disable network 
                         disabling(6),
			          invalid(7), -- Set to this value to remove network
			          terminating(8),
					reconfigure(9) -- Set this value to reconfigure a
                                        -- static IP Network.
			          }
	ACCESS      read-write
	STATUS      mandatory
	DESCRIPTION
		"The current status of the network entry. The value of this
		 object can be set to one of four values, 'enable', 'disable',
		 'invalid' or 'reconfigure'.

		 Setting the value of 'invalid' causes the network to be removed.

		 The 'enable' value enables a network currently in the 'disable'
		 state.

		 Setting the value to 'disable', disables a network in the 
		 'enable' state. 

		 'reconfigure' will result in the network temporarily disabled
		 and re-configured using any non-NULL values in the usrCfgNewNet...
		 objects. This allows a Network Manager to change an existing
		 network's address, encapsulation, or interface without having to
		 remove the router from service. This status can only be used on
		 static IP networks. Any attempt to 'reconfigure' any other type of
		 network will result in a 'badValue' error.

		 Attempts to set the value of this object to any other values
		 is illegal and will cause a 'badValue' error to be generated."
	--CONFIGURABLE
::= { usrCfgNetEntry 6 }

usrCfgNetLogicalId OBJECT-TYPE
	SYNTAX      UsrNetLogicalId
	ACCESS      read-only
	STATUS      mandatory
	DESCRIPTION
		"The logical identifier for this network assigned by the Pilgrim
           forwarder process which owns this network. The value of the
		 LogicalId is returned to the Config Process in the
		 FWD_ENABLE_NETWORK_RSP IPC message."
::= { usrCfgNetEntry 7 }

usrCfgNetType OBJECT-TYPE
	SYNTAX      INTEGER {
	                      static(1),
			            dynamic(2),
                           automatic(3)
                         }
	ACCESS      read-only
	STATUS      mandatory
	DESCRIPTION
		"Networks configured via network management interaction are
           static networks.

           Networks created to service incoming calls are dynamic networks.

           Networks created automatically every time the system reboots (i.e.
           the IP Loopback Network are automatic networks. Automatic networks
           are essentially read-only network entries, the cannot be enabled,
           disabled or deleted."
::= { usrCfgNetEntry 8 }

usrCfgNetUserName OBJECT-TYPE
	SYNTAX       UsrUserName
	ACCESS       read-write
	STATUS       mandatory
	DESCRIPTION
		"The name of a user (location) associated with a dedicated circuit
		 type network. This object's value is only meaningfull for Data Link
		 Control networks (PPP, SLIP, Frame Relay, etc...) over 
		 dedicated/permanent circuits. This name is passed to the Data
		 Link Control Process when the network is created
		 (ADD NETWORK command). The DLCP will use the name to lookup a
		 location profile in User Manager database. For non-dedicated
		 circuit networks, this object's value will always be a 
		 NULL string. Attempts to SET or change the value of this object
		 for non-dedicated circuit networks will fail."
	--CONFIGURABLE
::= { usrCfgNetEntry 9 }

usrCfgNetCFMStatusFlag OBJECT-TYPE
	SYNTAX	UsrConfigStatus
	ACCESS      read-write
	STATUS      mandatory
	DESCRIPTION
		"Setting the value of this object to `save' causes the values
		 of this Network Table entriy to be written out to the
		 current config file, which is stored in the usrCfgConfigFile
		 object. While the new ConfigFile is being written, the config
		 process will set the value of this flag set to `saving''. Any
		 attempts to set the value while it is  not `normal'
		 (i.e. the file is currently being written to the
		 ConfigFile) while result in a badValue error being
		 returned. Setting the value to `normal' will result in no
		 action."
::= { usrCfgNetEntry 10 }


--
-- The following three objects are used in conjunction with the 'reconfigure'
-- network status. Any object with a non-NULL/zero value, will be used
-- to configure the network setting when a 'reconfigure' request is made
-- through the usrCfgNetStatus object.
--
-- NOTE: These objects and the associated 'reconfigure' command only
--       apply to static IP Networks. Attempts to set values for these
--       objects for any other type of network will fail.
--

usrCfgNewNetIfName OBJECT-TYPE
	SYNTAX      DisplayString (SIZE (0..32))
	ACCESS      read-write
	STATUS      mandatory
	DESCRIPTION
		"The name of the interface this network runs on top of."
::= { usrCfgNetEntry 11 }

usrCfgNewNetAddress OBJECT-TYPE
	SYNTAX      OCTET STRING
	ACCESS      read-write
	STATUS      mandatory
	DESCRIPTION
		"The address which identifies the network. The format of
		 this object is dependent on the protocol running on this
		 network."
::= { usrCfgNetEntry 12 }



usrCfgNewNetEncapType OBJECT-TYPE
	SYNTAX      UsrCfgEncapsulations
	ACCESS      read-write
	STATUS      mandatory
	DESCRIPTION
		"The type of encapsulation employed by this network."
::= { usrCfgNetEntry 13 }


usrCfgNetRemoteAddress OBJECT-TYPE
        SYNTAX      OCTET STRING
        ACCESS      read-write
        STATUS      mandatory
        DESCRIPTION
                "The IP address of the remote router for the network
                 configured as an IP Numbered-Point-To-Point network."
        --CONFIGURABLE
::= { usrCfgNetEntry 14 }

usrCfgNetWanType OBJECT-TYPE
        SYNTAX     INTEGER {
                         none(0),
                         unptp(1),
                         nptp(2),
                         network(3)
                        }
        ACCESS     read-write
        STATUS     mandatory
        DESCRIPTION
                "The Wan Type determines the type of the IP network
                 created on top of the WAN (eg., Frame Relay)."
        --CONFIGURABLE
::= { usrCfgNetEntry 15 }


usrCfgIfTable OBJECT-TYPE
	SYNTAX     SEQUENCE OF UsrCfgIfEntry
	ACCESS     not-accessible
	STATUS     mandatory
	DESCRIPTION
		"A list of Interface Names currently configured in the Netserver
		 system."
::= { usrConfig 8 }

usrCfgIfEntry OBJECT-TYPE
	SYNTAX      UsrCfgIfEntry
	ACCESS      not-accessible
	STATUS      mandatory
	DESCRIPTION
		"An entry containing management information applicable to a
		 particular Interface."
	INDEX { usrCfgIfName }
::= { usrCfgIfTable 1}

UsrCfgIfEntry ::=
	SEQUENCE {
          usrCfgIfName DisplayString,
		usrCfgIfIndex INTEGER,
		usrCfgIfAdminStatus INTEGER,
		usrCfgIfLinkUpDownTrapEnable INTEGER,
		usrCfgIfPromiscuousMode TruthValue,
		usrCfgIfInFilter DisplayString,
		usrCfgIfOutFilter DisplayString,
		usrCfgIfFilterAccess INTEGER,
		usrCfgIfSdlCmds INTEGER,
		usrCfgIfSdlCmdResults INTEGER,
		usrCfgIfSysIndex INTEGER,
	        usrCfgIfManualSwitch INTEGER,
		usrCfgIfPolicy DisplayString,
		usrCfgIfPolicyAccess INTEGER,
		usrCfgIfType  INTEGER
		}

usrCfgIfName OBJECT-TYPE
	SYNTAX      DisplayString (SIZE (1..32))
	ACCESS      not-accessible
	STATUS      mandatory
	DESCRIPTION
		"The name of this interface.  The value of this
           object is the same as the ifName object of the standard Interface
           table (RFC-1573). This table allows the Pilgrim CLI process to
           translate Interface names into ifIndex values. All the other tables
           in the Pilgrim system relating to interfaces are indexed by the
           ifIndex value of the related interface."
::= { usrCfgIfEntry 1}

usrCfgIfIndex OBJECT-TYPE
	SYNTAX      INTEGER
	ACCESS      read-only
	STATUS      mandatory
	DESCRIPTION
		"The interface index of this interface taken from the standard 
           (RFC-1573) Interface MIB."
::= { usrCfgIfEntry 2 }

usrCfgIfAdminStatus OBJECT-TYPE
       SYNTAX  INTEGER {
                   up(1),       -- ready to pass packets
                   down(2)
               }
	  ACCESS  read-write
       STATUS  mandatory
       DESCRIPTION
               "The permanently configured state of the interface."
	--CONFIGURABLE
::= { usrCfgIfEntry 3 }

usrCfgIfLinkUpDownTrapEnable  OBJECT-TYPE
       SYNTAX      INTEGER { enabled(1), disabled(2) }
       ACCESS  read-write
       STATUS  mandatory
       DESCRIPTION
               "The permanently configured value, which indicates whether 
			 linkUp/linkDown traps should be generated for this
			 interface."
	--CONFIGURABLE
::= { usrCfgIfEntry 4 }

usrCfgIfPromiscuousMode  OBJECT-TYPE
       SYNTAX      TruthValue
	  ACCESS      read-write
       STATUS      mandatory
       DESCRIPTION
               "This object has a value of false(2) if this interface
               only accepts packets/frames that are addressed to this
               station.  This object has a value of true(1) when the
               station accepts all packets/frames transmitted on the
               media.  The value true(1) is only legal on certain
               types of media.  If legal, setting this object to a
               value of true(1) may require the interface to be reset
               before becoming effective.

               The value of ifPromiscuousMode does not affect the
               reception of broadcast and multicast packets/frames by
               the interface."
	--CONFIGURABLE
::= { usrCfgIfEntry 5 }


usrCfgIfInFilter OBJECT-TYPE
	SYNTAX      DisplayString (SIZE(0..20))
	ACCESS      read-write
	STATUS      mandatory
	DESCRIPTION "The name of the input filter for a specific interface."
      --CONFIGURABLE
::= { usrCfgIfEntry 6 }

usrCfgIfOutFilter OBJECT-TYPE
	SYNTAX      DisplayString (SIZE(0..20))
	ACCESS      read-write
	STATUS      mandatory
	DESCRIPTION "The name of the output filter for a specific interface."
       --CONFIGURABLE
::= { usrCfgIfEntry 7 }

usrCfgIfFilterAccess OBJECT-TYPE
       SYNTAX      INTEGER {
	                        off (0),
                             on (1)
                           }
       ACCESS      read-write
       STATUS      mandatory
       DESCRIPTION "This switch will allow user filters to override the
                    interface filters. If set to 'off', user filters do not
				override the interface filters. If set to 'on' user
				filters can override the interface filters."
       --CONFIGURABLE
::= {usrCfgIfEntry 8 }

usrCfgIfSdlCmds OBJECT-TYPE
       	SYNTAX INTEGER{
                normal(1),
		download(2),
		forceLinkDown(3)
 	    }
	ACCESS read-write
	STATUS mandatory
	DESCRIPTION
		"The Software Download Commands are as follows:
		normal: 
		This mode is for normal operation.
		download:
		This command trigger the download for this device.
		forceLinkDown:
		Force the Link to go down while a connection is in progress
 		and download. "
        DEFVAL { normal }
	::= { usrCfgIfEntry 9 }

usrCfgIfSdlCmdResults OBJECT-TYPE
       	SYNTAX INTEGER{
		notSelected(1),
		pending(2),
		active(3),
		failed(4),
		complete(5),
		portBusy(6)
 	    }
	ACCESS read-write
	STATUS mandatory
	DESCRIPTION
		"The Software Download status are as follows:
 		notSelected: 
		The particular Device is not selected for software download.
		This mode is for normal operation.
 		pending:
		This Device was selected for download, but it has not started.
 		active:
		This Device is currently being downloaded to.
 		failed:
		The download process failed for some reason in this device.
 		complete:
		This Device was successfully downloaded.
		portBusy:
		This Device is busy."
        DEFVAL { notSelected }
	::= { usrCfgIfEntry 10 }

	usrCfgIfSysIndex OBJECT-TYPE
       	SYNTAX INTEGER
	ACCESS read-only
	STATUS mandatory
	DESCRIPTION
		"The index of the Positron System Table that this interface
		 belongs to. The value of this object will always be zero on
		 non-Positron systems."
	::= { usrCfgIfEntry 11 }


usrCfgIfManualSwitch OBJECT-TYPE
	SYNTAX INTEGER
	ACCESS read-write
	STATUS mandatory
	DESCRIPTION
		"This switch controls the Interface status, when a SAVE ALL
		 is issued and it was not disabled by the user. It should not
		 be modified, it is only used by CFM."
	--CONFIGURABLE
::= { usrCfgIfEntry 12  }

usrCfgIfPolicy OBJECT-TYPE
	SYNTAX      DisplayString (SIZE(0..20))
	ACCESS      read-write
	STATUS      mandatory
	DESCRIPTION "The name of the  policy for a specific interface."
      --CONFIGURABLE
::= { usrCfgIfEntry 13 }

usrCfgIfPolicyAccess OBJECT-TYPE
       SYNTAX      INTEGER {
	                        off (0),
                             on (1)
                           }
       ACCESS      read-write
       STATUS      mandatory
       DESCRIPTION "This switch will allow user policy to override the
                    interface policy. If set to 'off', user policies do not
				override the interface policy. If set to 'on' user
				policy can override the interface policy."
       --CONFIGURABLE
::= {usrCfgIfEntry 14 }

usrCfgIfType OBJECT-TYPE  
    SYNTAX INTEGER
    ACCESS read-only
    STATUS mandatory    
    DESCRIPTION 
        "The type of interface, distinguished according to
        the physical/link protocol(s) immediately below
        the network layer in the protocol stack."
::= { usrCfgIfEntry 15  } 


usrCfgModuleTable OBJECT-TYPE
	SYNTAX     SEQUENCE OF UsrCfgModuleEntry
	ACCESS     not-accessible
	STATUS     mandatory
	DESCRIPTION
		"A list of RoboExec Software modules currently configured in the
		 Netserver system."
::= { usrConfig 9 }

usrCfgModuleEntry OBJECT-TYPE
	SYNTAX      UsrCfgModuleEntry
	ACCESS      not-accessible
	STATUS      mandatory
	DESCRIPTION
		"An entry containing management information applicable to a
		 particular Module."
	INDEX { usrCfgModName }
::= { usrCfgModuleTable 1}

UsrCfgModuleEntry ::=
	SEQUENCE {
          usrCfgModName
			DisplayString,
		usrCfgModType
			INTEGER,
		usrCfgModFileName
			DisplayString,
		usrCfgModCfgFileName
			DisplayString,
		usrCfgModDescr
			DisplayString,
		usrCfgModMasterProcess
			DisplayString,
		usrCfgModStatus
			INTEGER
		}

usrCfgModName OBJECT-TYPE
	SYNTAX      DisplayString (SIZE (1..32))
	ACCESS      not-accessible
	STATUS      mandatory
	DESCRIPTION
		"The name of this module."
::= { usrCfgModuleEntry 1}

usrCfgModType OBJECT-TYPE
	SYNTAX      INTEGER { linked(1), loadable(2) }
	ACCESS      read-only
	STATUS      mandatory
	DESCRIPTION
		"The module type."
::= { usrCfgModuleEntry 2}


usrCfgModFileName OBJECT-TYPE
	SYNTAX      DisplayString
	ACCESS      read-write
	STATUS      mandatory
	DESCRIPTION
		"The module's down-loadable file name. For 'linked' modules
		 the value will always be a zero length string, and no
		 SET operations will be allowed. If no file name is specified
		 when a new entry is added to the table, the Config Process will
		 attempt to load the file '@file//<usrCfgModName.mod"
	--CONFIGURABLE
::= { usrCfgModuleEntry 3}

usrCfgModCfgFileName OBJECT-TYPE
	SYNTAX      DisplayString
	ACCESS      read-write
	STATUS      mandatory
	DESCRIPTION
		"The module's Configuration file name. This file contains the
		 module's permanent configuration records. The value of this
		 object is passed to the module's master process's initialization
		 routine via the 'init_arg' parameter."
	--CONFIGURABLE
::= { usrCfgModuleEntry 4}

usrCfgModDescr OBJECT-TYPE
	SYNTAX      DisplayString (SIZE(0..128))
	ACCESS      read-only
	STATUS      mandatory
	DESCRIPTION
		"A longer string describing the module."
::= { usrCfgModuleEntry 5}

usrCfgModMasterProcess OBJECT-TYPE
	SYNTAX      DisplayString (SIZE(1..32))
	ACCESS      read-only
	STATUS      mandatory
	DESCRIPTION
		"The name of the master process of this module."
::= { usrCfgModuleEntry 6}

usrCfgModStatus OBJECT-TYPE
	SYNTAX      INTEGER {	initializing(1),
						configuring(2),
						loading(3),
						loaded(4),
						terminate(5),
						terminating(6),
						unload(7),
						unloading(8),
						broken(9) }
	ACCESS      read-write
	STATUS      mandatory
	DESCRIPTION
		"Status flags to control and display the module's current state.
		 Only the values 'terminate' and 'unload' may be set by a
		 Network Manager process. Adding a new entry to the table will
		 trigger the Config Process to load the module."
::= { usrCfgModuleEntry 7}


usrCfgAvailServiceTable OBJECT-TYPE
	SYNTAX SEQUENCE OF USRCfgAvailServiceEntry
	ACCESS not-accessible
	STATUS mandatory
	DESCRIPTION
		"This table defines the available services from the router."
::= { usrConfig 10 }

usrCfgAvailServiceEntry OBJECT-TYPE
	SYNTAX USRCfgAvailServiceEntry
	ACCESS not-accessible
	STATUS mandatory
	DESCRIPTION
		"An entry containing management information for a 
		particular available service."
	INDEX { usrCfgAvailServiceIndex }
::= { usrCfgAvailServiceTable 1 }

USRCfgAvailServiceEntry ::=
	SEQUENCE {
		usrCfgAvailServiceIndex
			INTEGER,
		usrCfgAvailServiceName
			DisplayString,
		usrCfgAvailServiceDescription
			DisplayString,
		usrCfgAvailServiceType
			INTEGER,
		usrCfgAvailServiceProtocol
			INTEGER,
		usrCfgAvailServiceModuleName
			DisplayString
	 }

usrCfgAvailServiceIndex OBJECT-TYPE
	SYNTAX INTEGER
	ACCESS not-accessible
	STATUS mandatory
	DESCRIPTION
		"An index into this table."
::= { usrCfgAvailServiceEntry 1 }

usrCfgAvailServiceName OBJECT-TYPE
	SYNTAX DisplayString (SIZE(1..32))
	ACCESS read-only
	STATUS mandatory
	DESCRIPTION
		"The handle by which this service is known."
::= { usrCfgAvailServiceEntry 2 }

usrCfgAvailServiceDescription OBJECT-TYPE
	SYNTAX DisplayString
	ACCESS read-only
	STATUS mandatory
	DESCRIPTION
		"A textual description of the service."
::= { usrCfgAvailServiceEntry 3 }

usrCfgAvailServiceType OBJECT-TYPE
	SYNTAX INTEGER {
			cfgSrvNetwork(1),
			cfgSrvTerminal(2),
			cfgSrvBoth(3),
			cfgSrvNeither(4)
		}
	ACCESS read-only
	STATUS mandatory
	DESCRIPTION
		"What type of service does this entry describe?."
::= { usrCfgAvailServiceEntry 4 }

usrCfgAvailServiceProtocol OBJECT-TYPE
	SYNTAX INTEGER {
			cfgSrvTCP(1),
			cfgSrvUDP(2),
			cfgSrcIPX(3),
			cfgSrvSPX(4),
			cfgSrvDDP(5),
			cfgSrvADSP(6),
			cfgSrvNCSI(7)
		}
	ACCESS read-only
	STATUS mandatory
	DESCRIPTION
		"This describes the Transport protocol on which the service resides."
::= { usrCfgAvailServiceEntry 5 }

usrCfgAvailServiceModuleName OBJECT-TYPE
	SYNTAX DisplayString (SIZE(1..32))
	ACCESS read-only
	STATUS mandatory
	DESCRIPTION
		"The Pilgrim module which implements this service.."
::= { usrCfgAvailServiceEntry 6 }


usrCfgNetworkServiceTable OBJECT-TYPE
	SYNTAX SEQUENCE OF UsrCfgNetworkServiceEntry
	ACCESS not-accessible
	STATUS mandatory
	DESCRIPTION
		"This table defines the Network services provided by Pilgrim"
::= { usrConfig 11 }

usrCfgNetworkServiceEntry OBJECT-TYPE
	SYNTAX UsrCfgNetworkServiceEntry
	ACCESS not-accessible
	STATUS mandatory
	DESCRIPTION
		"An entry containing management information for a 
		particular network service."
	INDEX { usrCfgNetworkServiceAdminName }
::= { usrCfgNetworkServiceTable 1 }

UsrCfgNetworkServiceEntry ::=
	SEQUENCE {
		usrCfgNetworkServiceAdminName
			DisplayString,
		usrCfgNetworkServiceName
			DisplayString,
		usrCfgNetworkServiceSocketNumber
			INTEGER,
		usrCfgNetworkServiceAncillaryData
			OCTET STRING,
		usrCfgNetworkServiceCloseActiveServices
			TruthValue,
		usrCfgNetworkServiceStatus
			INTEGER,
		usrCfgNetworkServiceCFMStatusFlag
			UsrConfigStatus
	 }

usrCfgNetworkServiceAdminName OBJECT-TYPE
	SYNTAX DisplayString (SIZE(1..32))
	ACCESS not-accessible
	STATUS mandatory
	DESCRIPTION
		"The name by which the administrator identifies this service."
::= { usrCfgNetworkServiceEntry 1 }

usrCfgNetworkServiceName OBJECT-TYPE
	SYNTAX DisplayString (SIZE(1..32))
	ACCESS read-write
	STATUS mandatory
	DESCRIPTION
		"The available service providing this network service.
		Must be the an entry from the Available Services Table."
	--CONFIGURABLE
::= { usrCfgNetworkServiceEntry 2 }

usrCfgNetworkServiceSocketNumber OBJECT-TYPE
	SYNTAX INTEGER (0..65535)
	ACCESS read-write
	STATUS mandatory
	DESCRIPTION
		"The number of the socket for this service."
	--CONFIGURABLE
::= { usrCfgNetworkServiceEntry 3 }

usrCfgNetworkServiceAncillaryData OBJECT-TYPE
	SYNTAX OCTET STRING
	ACCESS read-write
	STATUS mandatory
	DESCRIPTION
		"This specifies any other data that the service needs
		for its definition."
	--CONFIGURABLE
::= { usrCfgNetworkServiceEntry 4 }

usrCfgNetworkServiceCloseActiveServices OBJECT-TYPE
	SYNTAX TruthValue
	ACCESS read-write
	STATUS mandatory
	DESCRIPTION
		"This variable determines if active sessions using this service
		are closed when the service is set to inactive or invalid"
	--CONFIGURABLE
::= { usrCfgNetworkServiceEntry 5 }

usrCfgNetworkServiceStatus OBJECT-TYPE
	SYNTAX INTEGER {
			enable(1),
			disable(2),
			delete(3)
		}
	ACCESS read-write
	STATUS mandatory
	DESCRIPTION
		"Setting this variable to delete removes the service."
	--CONFIGURABLE
::= { usrCfgNetworkServiceEntry 6 }

usrCfgNetworkServiceCFMStatusFlag OBJECT-TYPE
	SYNTAX	UsrConfigStatus
	ACCESS      read-write
	STATUS      mandatory
	DESCRIPTION
		"Setting the value of this object to `save' causes the values
		 of this Network Service Table entry to be written out to the
		 current config file, which is stored in the usrCfgConfigFile
		 object. While the new ConfigFile is being written, the config
		 process will set the value of this flag set to `saving''. Any
		 attempts to set the value while it is  not `normal'
		 (i.e. the file is currently being written to the
		 ConfigFile) while result in a badValue error being
		 returned. Setting the value to `normal' will result in no
		 action."
::= { usrCfgNetworkServiceEntry 7 }

usrCfgRebootFlag OBJECT-TYPE
	SYNTAX	INTEGER {
				normal(1),
				reboot(2),
				shutdown(3),
				resetConfiguration(4)
			}
	ACCESS      read-write
	STATUS      mandatory
	DESCRIPTION
		"Setting the value of this object to `reboot' causes the
		 the system to gracefully shutdown and then reboot. Setting
		 the value to `shutdown' causes the system to shutdown and not
		 reboot automatically. The value `resetConfiguration' will
		 reset the system configuration to the 'factory default'
		 configuration and then reboot the system. Setting
		 the value to `normal' will result in no action."
::= { usrConfig 12 }

usrCfgTransmitAuthenName OBJECT-TYPE
	SYNTAX UsrUserName
	ACCESS read-write
	STATUS mandatory
	DESCRIPTION
		"The System wide transmit authentication user name."
	--CONFIGURABLE
::= { usrConfig 13 }

usrCfgSystemVersion OBJECT-TYPE
	SYNTAX DisplayString
	ACCESS read-only
	STATUS mandatory
	DESCRIPTION
		"The software release version of this system."
::= { usrConfig 14 }

usrCfgImageFileName OBJECT-TYPE
	SYNTAX DisplayString
	ACCESS read-only
	STATUS mandatory
	DESCRIPTION
		"The file name of the software image which this product loads
           when the system reboots. The value of this object is used by the
           USR Access Router Manager when it downloads a new version of the
           router software."
::= { usrConfig 15 }

usrCfgDownLoadStatus OBJECT-TYPE
	SYNTAX	INTEGER {
				normal(1),
				triggerDownLoad(2),
				deletingImageFile(3),
				readyForDownLoad(4)
			}
	ACCESS      read-write
	STATUS      mandatory
	DESCRIPTION
		"This value is used to  prepare the system to receive a
		 new system image via TFTP. A Network Management
		 station initiates a system image download by setting the
		 value of this object to 'triggerDownLoad'. The system then sets
		 the state to 'deletingImageFile', while it removs the current
		 image file from the flash file system. This frees up space in the
		 flash file system for the new image. 

		 When the old image file is deleted, the value of this will be
		 changed to 'readyForDownLoad'. The NMS is expected to poll
		 this MIB object until this state is reached. Then it can 
		 begin a TFTP download of the new image file.

		 (NOTE: if the system crashes or reboots during the 
		 'deleteingImageFile' or 'readyForDownLoad' states, the system
		 will NOT reboot, and the image must be update via a console
		 port Software Down Load.)

		 After the new system image TFTP download has been completed,
		 the NMS **MUST** set this object back to the 'normal' state.
		 A system shutdown or reboot via the usrCfgRebootFlag object 
		 will not be allowed unless the this object has been reset to
		 'normal'."
::= { usrConfig 16 }


usrCfgLossOfServiceChecking OBJECT-TYPE
	SYNTAX TruthValue
	ACCESS read-write
	STATUS optional
	DESCRIPTION
		"Specifies whether the configurator will allow the modems to
		 be busied out if a loss of service is detected.
		 This feature may not be available on all systems."
	DEFVAL	{ 1 }
	--CONFIGURABLE
::= { usrConfig 17 }

usrCfgBulkFileGroup OBJECT IDENTIFIER ::= { usrConfig 18 }

usrCfgBulkFileStatus OBJECT-TYPE
	SYNTAX	INTEGER {
				normal(1),
				createBulkFile(2),
				creatingBulkFile(3),
				restoreBulkFile(4),
				restoringBulkFile(5),
				bulkFileError(6)
			}
	ACCESS      read-write
	STATUS      mandatory
	DESCRIPTION
		"This object is used to allow the system to prepare a
		 Bulk configuration file that is retrievable via TFTP.
		 A bulk configuration file is created by settting the
		 value of this object to 'createBulkFile'. The system
		 then sets this object to 'creatingBulkFile' and
		 concatenates the individual .cfg files into a single
		 file indicated by the object usrCfgBulkFileName.

		 The individual .cfg files can be restored by setting
		 the value of this object to 'restoreBulkFile'. The
		 system then sets this object to 'restoringBulkFile'
		 and splits the file indicated by the object
		 usrCfgBulkFileName into the individual .cfg files.
		 Note: the file indicated by the object usrCfgBulkFileName
		 must be present in the file system for this to succeed.

		 The operation is completed when the value of this object
		 is set back to 'normal' or 'bulkFileError' which indicates
		 that an error occurred."
::= { usrCfgBulkFileGroup 1 }

usrCfgBulkFileName OBJECT-TYPE
	SYNTAX	DisplayString (SIZE(0..32))
	ACCESS      read-write
	STATUS      mandatory
	DESCRIPTION
		"This is the name of the Bulk File that will be acted upon
		 when usrCfgBulkFileStatus is set to 'createBulkFile' or
		 'restoreBulkFile'."
	DEFVAL { "ConfigBulkFile" }
	--CONFIGURABLE
::= { usrCfgBulkFileGroup 2 }

usrCfgBulkFileErrorMessage OBJECT-TYPE
	SYNTAX	OCTET STRING
	ACCESS	read-only
	STATUS	mandatory
	DESCRIPTION
		"When the value of usrCfgBulkFileStatus is 'bulkFileError',
		 this object will indicate the error that occurred."
::= { usrCfgBulkFileGroup 3 }


usrConfigTraps OBJECT IDENTIFIER ::= { usrConfig 19 }

usrCfgDynNetCreated TRAP-TYPE
	ENTERPRISE usrConfigTraps
	VARIABLES { usrCfgNetName }
	DESCRIPTION
		"A usrCfgDynNetCreated message signifies that the sending 
		 US Robotics Remote Access Router has just established a
		 Dynamic Network to service a dialup network user."
::= 1

usrCfgDynNetRemoved TRAP-TYPE
	ENTERPRISE usrConfigTraps
	VARIABLES { usrCfgNetName }
	DESCRIPTION
		"A usrCfgDynNetRemoved trap signifies that the sending 
		 US Robotics Remote Access Router has just removed a
		 Dynamic Network associated with a recently disconnected
		 dialup network user"
::= 2


usrCfgTunnelConnTable OBJECT-TYPE
	SYNTAX     SEQUENCE OF UsrCfgTunnelConnEntry
	ACCESS     not-accessible
	STATUS     mandatory
	DESCRIPTION
		"A list of dynamic tunneling connections currently
           active in the Netserver system."
::= { usrConfig 20 }

usrCfgTunnelConnEntry OBJECT-TYPE
	SYNTAX      UsrCfgTunnelConnEntry
	ACCESS      not-accessible
	STATUS      mandatory
	DESCRIPTION
		"An entry containing management information applicable to a
		 particular Connection."
	INDEX { usrCfgTunnelConnIfName }
::= { usrCfgTunnelConnTable 1}

UsrCfgTunnelConnEntry ::=
	SEQUENCE {
          usrCfgTunnelConnIfName DisplayString,
		usrCfgTunnelConnUserName OCTET STRING,
		usrCfgTunnelConnTunnelType INTEGER,
		usrCfgTunnelConnStartTime INTEGER
		}

usrCfgTunnelConnIfName OBJECT-TYPE
	SYNTAX      DisplayString (SIZE (1..32))
	ACCESS      not-accessible
	STATUS      mandatory
	DESCRIPTION
		"The name of this dynamic tunneling interface."
::= { usrCfgTunnelConnEntry 1}

usrCfgTunnelConnUserName OBJECT-TYPE
	SYNTAX      OCTET STRING (SIZE (1..32))
	ACCESS      read-only
	STATUS      mandatory
	DESCRIPTION
		"The name of the user for this connection."
::= { usrCfgTunnelConnEntry 2}

usrCfgTunnelConnTunnelType OBJECT-TYPE
	SYNTAX      INTEGER {
                    pptp(1),
                    l2f(2),
                   l2tp(3),
                    atmp(4),
                    vtp(5),
                    ah(6),
                    ip-ip(7),
                    min-ip-ip(8),
                    esp(9),
                    gre(10),
                    drs(11)
                    }
	ACCESS      read-only
	STATUS      mandatory
	DESCRIPTION
		"The tunneling protocol used for this connection."
::= { usrCfgTunnelConnEntry 3}

usrCfgTunnelConnStartTime OBJECT-TYPE
	SYNTAX      INTEGER
	ACCESS      read-only
	STATUS      mandatory
	DESCRIPTION
          "The start time of the connection."
::= { usrCfgTunnelConnEntry 4}

usrCfgSecurityService OBJECT-TYPE                                          
        SYNTAX  INTEGER {
                    radius(1),
                    tacacsplus(2)                                          
                }                                                          
        ACCESS      read-write
        STATUS      mandatory
        DESCRIPTION
                "Specifies the security service client process that gets started
                at boot time."
        DEFVAL  { 1 } 
    --CONFIGURABLE
::= { usrConfig 21 }

usrCfgLogicalIfTable OBJECT-TYPE
    SYNTAX     SEQUENCE OF UsrCfgLogicalIfEntry
    ACCESS     not-accessible
    STATUS     mandatory
    DESCRIPTION
        "A list of Logical Interface Names currently configured in the Netserver
         system."
::= { usrConfig 22 }

usrCfgLogicalIfEntry OBJECT-TYPE
    SYNTAX      UsrCfgLogicalIfEntry
    ACCESS      not-accessible
    STATUS      mandatory
    DESCRIPTION
        "An entry containing management information applicable to a
         particular Interface."
    INDEX { usrCfgLogicalIfName }
::= { usrCfgLogicalIfTable 1}

UsrCfgLogicalIfEntry ::=
    SEQUENCE {
             usrCfgLogicalIfName DisplayString
             }

usrCfgLogicalIfName OBJECT-TYPE
    SYNTAX      DisplayString (SIZE (1..32))
    ACCESS      read-write
    STATUS      mandatory
    DESCRIPTION
        "The name of this interface. "
	--CONFIGURABLE
::= { usrCfgLogicalIfEntry 1}

usrCfgLogicalIfRefTable OBJECT-TYPE
    SYNTAX     SEQUENCE OF UsrCfgLogicalIfRefEntry
    ACCESS     not-accessible
    STATUS     mandatory
    DESCRIPTION
        "A list of Logical Interface Names and Index. This table is used as a refererence for 
         retrieving the stored index of LogicalIf"
::= { usrConfig 23 }

usrCfgLogicalIfRefEntry OBJECT-TYPE
    SYNTAX      UsrCfgLogicalIfRefEntry
    ACCESS      not-accessible
    STATUS      mandatory
    DESCRIPTION
        "An entry containing management information applicable to a
         particular Interface."
    INDEX { usrCfgLogicalIfRefName }
::= { usrCfgLogicalIfRefTable 1}

UsrCfgLogicalIfRefEntry ::=
    SEQUENCE {
             usrCfgLogicalIfRefName     DisplayString,
             usrCfgLogicalIfRefIndex    INTEGER
             }

usrCfgLogicalIfRefName OBJECT-TYPE
    SYNTAX      DisplayString (SIZE (1..32))
    ACCESS      read-write
    STATUS      mandatory
    DESCRIPTION
        "The name of this interface. "
	--CONFIGURABLE
::= { usrCfgLogicalIfRefEntry 1}

usrCfgLogicalIfRefIndex OBJECT-TYPE
    SYNTAX      INTEGER
    ACCESS      read-write
    STATUS      mandatory
    DESCRIPTION
        "The index of this logical interface. "
	--CONFIGURABLE
::= { usrCfgLogicalIfRefEntry 2}

usrCfgResetEEpromStatus OBJECT-TYPE
        SYNTAX      TruthValue
        ACCESS      read-write
        STATUS      mandatory
        DESCRIPTION
                " Specifies whether boot prom needs to be initialised."
    --CONFIGURABLE
::= { usrConfig 24 }
 

usrCfgModemGroupFilterTable OBJECT-TYPE
    SYNTAX     SEQUENCE OF UsrCfgModemGroupFilterEntry
    ACCESS     not-accessible
    STATUS     mandatory
    DESCRIPTION
         "list of filter operations in a particular modem group"
::= { usrConfig 28 }

usrCfgModemGroupFilterEntry OBJECT-TYPE
    SYNTAX      UsrCfgModemGroupFilterEntry
    ACCESS      not-accessible
    STATUS      mandatory
    DESCRIPTION
        "An entry containing management information applicable to a
         particular modem group."
    INDEX { usrCfgModemGroupName }
::= { usrCfgModemGroupFilterTable 1}

UsrCfgModemGroupFilterEntry ::=
    SEQUENCE {
             usrCfgModemGroupName DisplayString,
             usrCfgModemGroupFilterAccess  INTEGER,
             usrCfgModemGroupInFilter DisplayString,
             usrCfgModemGroupOutFilter DisplayString
             }

usrCfgModemGroupName OBJECT-TYPE
    SYNTAX      DisplayString (SIZE (1..32))
    ACCESS      not-accessible
    STATUS      mandatory
    DESCRIPTION
        "The name of this modem group. "
    --CONFIGURABLE
::= { usrCfgModemGroupFilterEntry 1}

usrCfgModemGroupFilterAccess OBJECT-TYPE
        SYNTAX      INTEGER {
                            off (0),
                             on (1)
                           }
        ACCESS      read-write
        STATUS      mandatory
     DESCRIPTION
                " This is for setting a filter access for all the
                interfaces in a particular modem group."
    --CONFIGURABLE
::= { usrCfgModemGroupFilterEntry 2 }

usrCfgModemGroupInFilter OBJECT-TYPE
    SYNTAX      DisplayString (SIZE(0..20))
    ACCESS      read-write
    STATUS      mandatory
    DESCRIPTION "The name of the input filter for a specific modem group."
      --CONFIGURABLE
::= { usrCfgModemGroupFilterEntry 3 }

usrCfgModemGroupOutFilter OBJECT-TYPE
    SYNTAX      DisplayString (SIZE(0..20))
    ACCESS      read-write
    STATUS      mandatory
    DESCRIPTION "The name of the output filter for a specific group."
       --CONFIGURABLE
::= { usrCfgModemGroupFilterEntry 4 }

usrCfgTransmitPassword OBJECT-TYPE
    SYNTAX  OCTET STRING (SIZE (1..32))
    ACCESS  write-only
    STATUS  mandatory
    DESCRIPTION
        "Sytem password transmitted with auth name, when password is not 
		 avialable from other sources"
    --CONFIGURABLE
    ::= { usrConfig 33 }


	
END  

--
-- For the revision history to work correctly, after a new MIB file has been
-- added to the CVS repository the first time the CVS Admin person needs to
-- set the correct comment string delimter for the file.
--
-- $Log: usr_config.mib,v $
-- Revision 1.39.2.12  1998/06/01 23:35:25  eshaji
-- Fix for MR6857, SHOWALL support
--
-- Revision 1.39.2.11  1998/05/18 17:34:51  eshaji
-- Fix for MR5658, Config Bulk File saving EEPPROM settings + filter files
--
-- Revision 1.39.2.10  1998/05/13 19:22:06  tingh
-- for logical DS1 interface. added usrCfgLogicalIfTable and usrCfgLogicalIfRefTable
--
-- Revision 1.39.2.9  1998/04/28 18:27:41  mfreed
-- IP_SECURITY ( Policy Manager) support added
--
-- Revision 1.39.2.8  1998/01/23 21:12:03  psd
-- Support for single config file.
--
-- Revision 1.39.2.7  1998/01/19 20:28:04  psd
-- Moved usrCfgSecurityService after the tunnel table entries.
--
-- Revision 1.39.2.6  1998/01/10 01:38:02  merge
-- Tacacs+ merge
--
-- Revision 1.39.2.5  1997/12/19 13:20:22  psd
-- Another merge from 2.0
--
-- Revision 1.39.2.4  1997/11/05 12:59:22  psd
-- Added a Tunneling connection table.
--
-- Revision 1.39.2.3  1997/10/20 14:23:47  edjean
-- Add Bulk File funtionality to Pilgrim
--
-- Revision 1.39.2.2  1997/09/17 19:06:25  psd
-- Merged 2.0 to 3.0
--
--Revision 1.42.2.3  1997/09/04  14:14:55  psd
--Changed range of usrCfgIfInFilter and usrCfgIfOutFilter from 0-15 to 0-20
--
--Revision 1.42.2.2  1997/09/03  18:38:47  psd
--Updated UsrCfgEncapsulations
--
--Revision 1.42.2.1  1997/09/03  14:39:32  psd
--Changed usrCfgAvailServiceProtocol from read-write to read-only.
--
--Revision 1.42  1997/08/05  13:15:23  naga
--Bug Fix for #1709 - improper/duplicate  definition of usrCfgAvailServiceEnry
--
-- Revision 1.41  1997/07/02 21:47:32  jhalpin
-- Update  before my final farewell...
--
-- Revision 1.40  1997/06/04 18:55:15  edjean
-- bug# 1183, add portBusy field to support mdm sdl
--
--Revision 1.39.2.1  1997/07/01  13:27:12  pfc
--Merge in changes from mainline branch
--
-- Revision 1.39  1997/04/08 19:26:36  jhalpin
-- Add Positron usrCfgIfSysIndex object
--
-- Revision 1.38  1997/03/31 17:14:22  jhalpin
-- Add AUTOMATIC Networks
--
-- Revision 1.37  1997/03/03 15:06:12  pfc
-- Add RADIUS timeout objects
--
-- Revision 1.36  1997/02/19 16:02:41  jhalpin
-- RECONFIGURE IP NETWORK support
--
-- Revision 1.35  1997/02/10 19:51:39  pfc
-- Add usr_ping mib and modify configurator mib to support busy out commands
--
-- Revision 1.34.4.1  1997/02/03 19:48:20  jhalpin
-- Add New Network table MIB objects
--
-- Revision 1.34  1996/10/03 20:13:57  edjean
-- Add Mib support for SDL, EJB
--
-- Revision 1.33  1996/09/20 21:10:22  jhalpin
-- Merg in LANLinker changes
--
-- Revision 1.32  1996/09/05 19:03:03  jhalpin
-- Xmit user name support
--
-- Revision 1.31  1996/08/08 19:50:51  jhalpin
-- Merge in SHUTDOWN and RESET changes from LANLinker branch
--
-- Revision 1.30  1996/07/23 21:25:11  jhalpin
-- Merge in LANLinker branch changes
--
-- Revision 1.29  1996/07/17 18:06:00  jhalpin
-- Merge in LANLinker bugfixes
--
-- Revision 1.28.2.8  1997/02/14 19:46:07  jhalpin
-- Change ConfigFile object to read-only
--
-- Revision 1.28.2.7  1997/01/21 14:37:37  jhalpin
-- Cleanup comments/descriptions about reconfigure network support
--
-- Revision 1.28.2.6  1997/01/20 22:52:12  jhalpin
-- RECONFIGURE NETWORK support
--
-- Revision 1.28.2.5  1996/09/20 19:43:39  jhalpin
-- Support new version number structure and system image download
--
-- Revision 1.28.2.4  1996/09/04 13:29:48  jhalpin
-- Add in XmitAuthenName object
--
-- Revision 1.28.2.3  1996/08/08 15:22:09  jhalpin
-- Add shutdown support, consolidate reboot/reset MIB objects
--
-- Revision 1.28.2.2  1996/07/23 21:08:58  jhalpin
-- Add in Reboot and ResetConfiguration MIB objects
--
-- Revision 1.28.2.1  1996/07/17 17:26:39  jhalpin
-- Enable networks by default when added, bug #: 19960709144124
--
-- Revision 1.28  1996/06/13 12:43:58  jhalpin
-- Change NetUp to NetEnable and NetDown to NetDisable
--
-- Revision 1.27  1996/06/07 12:42:28  jhalpin
-- Get rid on unneccesary enumeration macros
--
-- Revision 1.26  1996/05/01 17:23:54  jhalpin
-- Fix Filter Access description
--
-- Revision 1.25  1996/04/26 15:39:06  jhalpin
-- Add filter objects to usrCfgIfTable
--
-- Revision 1.24  1996/04/04 19:40:38  jhalpin
-- Fix encasualtion enums
--
-- Revision 1.23  1996/03/26 22:04:15  psd
-- Removed the CONFIGURABLE flag from the Config File object.
--
-- Revision 1.22  1996/03/18 15:34:07  psd
-- Changed the enumeration for usrCfgNetworkServiceSocketNumber.
--
-- Revision 1.21  1996/03/17 20:32:37  jhalpin
-- New encapsulations and protocols
--
-- Revision 1.20  1996/03/15 21:09:58  psd
-- Added two CFM save flags for Network Services.
--
-- Revision 1.19  1996/03/13 14:34:39  psd
-- Removed usrCfgNetworkServiceModemGroup from the Network Service table.
--
-- Revision 1.18  1996/03/08 22:14:14  jhalpin
-- Change NetConfigFlag to NetCFMStatuFlag
--
-- Revision 1.17  1996/03/08 19:30:43  psd
-- Added a range of INTEGERs for usrCfgNetworkServiceSocketNumber and
-- usrCfgNetworkServiceModemGroup.
--
-- Revision 1.16  1996/03/06 22:06:21  psd
-- Added the Available Services Table and Network Services Table.
--
-- Revision 1.15  1996/02/29 17:58:04  jhalpin
-- Update Module Table state values, add User Name to Network Table
--
-- Revision 1.14  1996/02/16 22:05:25  jhalpin
-- CONFIGURABLE keywords added
--
-- Revision 1.13  1996/02/13 19:31:01  jhalpin
-- Module Table
--
-- Revision 1.12  1996/02/07 20:08:23  jhalpin
-- Complete support for usrCfgIfTable objects
--
-- Revision 1.11  1996/02/01 21:50:59  jhalpin
-- Fix up InterfaceIndex macro for interface related mib files, fix netStatus comment in usr_config.mib
--
-- Revision 1.10  1996/01/25 19:38:08  jhalpin
-- Fix encapsulation enumeration
--
-- Revision 1.9  1996/01/25 17:51:44  jhalpin
-- Updated Network Table
--
-- Revision 1.8  1996/01/16 19:57:49  jhalpin
-- Remove load host object
--
-- Revision 1.7  1996/01/02 18:57:18  jhalpin
-- SAVE Network and Interface flags
--
-- Revision 1.6  1995/12/26 21:38:39  jhalpin
-- Support the usrCfgIfTable to map if names to ifIndex values
--
-- Revision 1.5  1995/12/12 23:02:26  jhalpin
-- Cleaned up network table
--
-- Revision 1.4  1995/12/12 02:20:37  jhalpin
-- Update for Named Networks
--
-- Revision 1.3  1995/11/17 17:12:15  jhalpin
-- Updated RoboExec and usrConfig MIB sources
--
-- Revision 1.2  1995/10/13 19:20:46  jhalpin
-- Fixed Network Table indices, and swapped order of netAddr and encapType in MIB
--
-- Revision 1.1  1995/09/12 14:22:29  jhalpin
-- Config Process Private MIB
--
--
--
--
-- Local Variables:
-- tab-width:5
-- tab-stop-list:( 5 10 15 20 25 30 35 40 45 50 55 60 65 70 75 80)
-- End:
--
--
--	REmib.mib - The RoboExec MIB
--
--
-- Author:	    Jim Halpin
--
-- $Id: REmib.mib,v 1.21.8.6 1998/06/15 22:43:01 gjoesph Exp $
--
--  | Copyright (c) 1995 U.S. Robotics Access Corp., Skokie, IL 60076		|
--  |														|
--  | The information in this software is subject to change without notice |
--  | and should not be construed as a commitment by U.S. Robotics Access	|
--  | Corp.													|
--  |														|
--  | U.S. Robotics Access Corp. assumes no responsibility for the use or	|
--  | reliability of its software on equipment which is not supplied by	|
--  | U.S. Robotics Access Corp.									|
--  |														|
--  | This software is furnished under a license and may be copied only	|
--  | with the inclusion of the above copyright notice. This software, or	|
--  | any other copies thereof, may not be provided or otherwise made		|
--  | available to any other person except to one who agrees to these		|
--  | license terms. Title to and ownership of the software shall at all	|
--  | times remain in U.S. Robotics Access Corp.						|
--

   ROBOEXEC-RESOURCES-MIB DEFINITIONS ::= BEGIN

   IMPORTS
	  Counter								FROM RFC1155-SMI
	  OBJECT-TYPE							FROM RFC-1212
	  roboExec, DisplayString, UsrConfigStatus	FROM USR-DEFINITIONS-MIB;


   usrreSystem		  OBJECT IDENTIFIER ::= { roboExec 1 }
   usrreSWRun		  OBJECT IDENTIFIER ::= { roboExec 2 }
   usrreEvents		  OBJECT IDENTIFIER ::= { roboExec 3 }
   usrreCounters	  OBJECT IDENTIFIER ::= { roboExec 5 }
   usrreNames		  OBJECT IDENTIFIER ::= { roboExec 6 }
   usrreFiles		  OBJECT IDENTIFIER ::= { roboExec 7 }



   -- textual conventions

   -- memory size, expressed in units of 1024bytes
   KBytes ::=	  INTEGER (0..2147483647)


   DateAndTime ::= OCTET STRING (SIZE (8 | 11))
   --	   A date-time specification for the local time of day.
   --	   This data type is intended to provide a consistent
   --	   method of reporting date information.
   --
   --		  field  octets  contents			   range
   --		  _____  ______  ________			   _____
   --		    1	 1-2	  year				   0..65536
   --					  (in network byte order)
   --		    2	  3	  month				   1..12
   --		    3	  4	  day				   1..31
   --		    4	  5	  hour				   0..23
   --		    5	  6	  minutes				   0..59
   --		    6	  7	  seconds				   0..60
   --					  (use 60 for leap-second)
   --		    7	  8	  deci-seconds			   0..9
   --		    8	  9	  direction from UTC	   "+" / "-"
   --					  (in ascii notation)
   --		    9	 10	  hours from UTC		   0..11
   --		   10	 11	  minutes from UTC		   0..59
   --
   --		  Note that if only local time is known, then
   --		  timezone information (fields 8-10) is not present.



   -- The RoboExec Resources System Group
   --
   -- Implementation of this group is mandatory for all RoboExec systems.
   usrreSystemDate OBJECT-TYPE
	  SYNTAX DateAndTime
	  ACCESS read-write
	  STATUS mandatory
	  DESCRIPTION
		    "The RoboExec's notion of the local date and time of
		    day."
	  ::= { usrreSystem 1 }

   usrreMemorySize OBJECT-TYPE
	  SYNTAX KBytes
	  ACCESS read-only
	  STATUS mandatory
	  DESCRIPTION
		    "The amount of physical main memory maintained by
		    the RoboExec."
	  ::= { usrreSystem 2 }

   usrreFreeMemorySize OBJECT-TYPE
	  SYNTAX KBytes
	  ACCESS read-only
	  STATUS mandatory
	  DESCRIPTION
		    "The amount of free physical main memory maintained by
		    the RoboExec."
	  ::= { usrreSystem 3 }

   usrreTextSize OBJECT-TYPE
	  SYNTAX INTEGER (0..2147483647)
	  ACCESS read-only
	  STATUS mandatory
	  DESCRIPTION
		    "The number of bytes of text (code) in the executable."
	  ::= { usrreSystem 4 }

   usrreInitDataSize OBJECT-TYPE
	  SYNTAX INTEGER (0..2147483647)
	  ACCESS read-only
	  STATUS mandatory
	  DESCRIPTION
		    "The number of bytes of initialized data in the executable."
	  ::= { usrreSystem 5 }

   usrreUninitDataSize OBJECT-TYPE
	  SYNTAX INTEGER (0..2147483647)
	  ACCESS read-only
	  STATUS mandatory
	  DESCRIPTION
		    "The number of bytes of uninitialized data in the executable."
	  ::= { usrreSystem 6 }

   usrreStackSize OBJECT-TYPE
	  SYNTAX INTEGER (0..2147483647)
	  ACCESS read-only
	  STATUS mandatory
	  DESCRIPTION
		    "The size of the stack in bytes provided for the executable."
	  ::= { usrreSystem 7 }

   usrreMaxHeapAllocated OBJECT-TYPE
	  SYNTAX KBytes
	  ACCESS read-only
	  STATUS mandatory
	  DESCRIPTION
		    "The maximum amount of memory ever allocated from the
		    RoboExec heap."
	  ::= { usrreSystem 8 }

   usrreLargestMemoryBlockAddress OBJECT-TYPE
       SYNTAX DisplayString
       ACCESS read-only
       STATUS mandatory
       DESCRIPTION
              "The address of the largest memory block ever
               allocated from heap."
       ::= { usrreSystem 9 }

      usrreLargestMemoryBlockSize OBJECT-TYPE
       SYNTAX KBytes
       ACCESS read-only
       STATUS mandatory
       DESCRIPTION
              "The size (in kilobytes) of the largest memory block ever 
               allocated from heap."
       ::= { usrreSystem 10 }

      usrreLargestMemoryBlockCorrelator OBJECT-TYPE
       SYNTAX DisplayString
       ACCESS read-only
       STATUS mandatory
       DESCRIPTION
              "An ASCII string indicating what process allocated 
               the largest memory block from heap."
       ::= { usrreSystem 11 }

      usrreLargestMemoryBlockState OBJECT-TYPE
       SYNTAX INTEGER {
                free(0),             -- Memory block was freed for further reuse
                allocated(1)  
            }       
       ACCESS read-only
       STATUS mandatory
       DESCRIPTION
              "The state of the largest memory block:
                        0 - was freed for further reuse;
                        1 - is allocated."
       ::= { usrreSystem 12 }


      usrreCPULoadAvg OBJECT-TYPE
	  SYNTAX INTEGER (0..100)
       ACCESS read-only
       STATUS mandatory
       DESCRIPTION
              "System CPU load Percentage (Instantaneous)."
       ::= { usrreSystem 13 }

      usrreCPULoadAvgMinute OBJECT-TYPE
	  SYNTAX INTEGER (0..100)
       ACCESS read-only
       STATUS mandatory
       DESCRIPTION
              "System CPU load Percentage for last minute."
       ::= { usrreSystem 14 }

      usrreCPULoadAvgHour OBJECT-TYPE
	  SYNTAX INTEGER (0..100)
       ACCESS read-only
       STATUS mandatory
       DESCRIPTION
              "System CPU load Percentage for last hour."
       ::= { usrreSystem 15 }

      usrreCPULoadAvgDay OBJECT-TYPE
	  SYNTAX INTEGER (0..100)
       ACCESS read-only
       STATUS mandatory
       DESCRIPTION
              "System CPU load Percentage for last day."
       ::= { usrreSystem 16 }

     usrreFreeMemorySize1HourBefore OBJECT-TYPE
      SYNTAX KBytes
      ACCESS read-only
      STATUS mandatory
      DESCRIPTION
            "The amount of free physical main memory maintained by
            the RoboExec 1 Hour Before."
      ::= { usrreSystem 17 }
 
      usrreFreeMemorySize12HourBefore OBJECT-TYPE
      SYNTAX KBytes
      ACCESS read-only
      STATUS mandatory
      DESCRIPTION
            "The amount of free physical main memory maintained by
            the RoboExec 12 Hour Before."
      ::= { usrreSystem 18 }
 
      usrreFreeMemorySize24HourBefore OBJECT-TYPE
      SYNTAX KBytes
      ACCESS read-only
      STATUS mandatory
      DESCRIPTION
            "The amount of free physical main memory maintained by
            the RoboExec 24 Hours Before."
      ::= { usrreSystem 19 }
 
      usrreTotalBufferCache OBJECT-TYPE
      SYNTAX KBytes
      ACCESS read-only
      STATUS mandatory
      DESCRIPTION
            "The amount of total allocated buffer cache maintained
             by RoboExec."
      ::= { usrreSystem 20 }
 
      usrreFreeBufferCache OBJECT-TYPE
      SYNTAX KBytes
      ACCESS read-only
      STATUS mandatory
      DESCRIPTION
            "The amount of free buffer cache maintained by
             RoboExec."
      ::= { usrreSystem 21 }

      usrreFlashMemorySize OBJECT-TYPE
	  SYNTAX KBytes
	  ACCESS read-only
	  STATUS mandatory
	  DESCRIPTION
		    "The amount of physical flash memory maintained by
		    the RoboExec."
	  ::= { usrreSystem 22 }


   -- The RoboExec Resources Running Software Group
   --
   -- Implementation of this group is mandatory.
   --
   -- The reSWRunTable contains an entry for each distinct piece of
   -- software that is running or loaded into physical or virtual
   -- memory in preparation for running.  This includes the RoboExec's
   -- operating system, device drivers, and applications.

   usrreSWRunTable OBJECT-TYPE
	  SYNTAX SEQUENCE OF UsrreSWRunEntry
	  ACCESS not-accessible
	  STATUS mandatory
	  DESCRIPTION
		    "The (conceptual) table of software running on the
		    RoboExec."
	  ::= { usrreSWRun 1 }

   usrreSWRunEntry OBJECT-TYPE
	  SYNTAX UsrreSWRunEntry
	  ACCESS not-accessible
	  STATUS mandatory
	  DESCRIPTION
		    "A (conceptual) entry for one piece of software
		    running on the RoboExec Note that because the installed
		    software table only contains information for
		    software stored locally on this RoboExec, not every
		    piece of running software will be found in the
		    installed software table.	 This is true of software
		    that was loaded and run from a non-local source,
		    such as a network-mounted file system.

		    As an example of how objects in this table are
		    named, an instance of the reSWRunName object might
		    be named reSWRunName.1287"
	  INDEX { usrreSWRunIndex }
	  ::= { usrreSWRunTable 1 }

   UsrreSWRunEntry ::= SEQUENCE {
		 usrreSWRunIndex		INTEGER,
		 usrreSWRunName		DisplayString,
		 usrreSWRunType		INTEGER,
		 usrreSWRunStatus		INTEGER,
		 usrreSWRunStartTime	INTEGER,
		 usrreSWRunMsgSent		Counter,
		 usrreSWRunMsgRcvd		Counter,
      	 usrreSWRunMsgPassedFrom Counter,
		 usrreSWRunMsgPassedTo	Counter,
		 usrreSWRunMboxScheduled	Counter,
		 usrreSWRunAllocated	KBytes,
		 usrreSWRunFreed		KBytes
	  }

   usrreSWRunIndex OBJECT-TYPE
	  SYNTAX INTEGER (1..2147483647)
	  ACCESS not-accessible
	  STATUS mandatory
	  DESCRIPTION
		    "A unique value for each piece of software running
		    on the RoboExec.  Wherever possible, this should be the
		    system's native, unique identification number."
	  ::= { usrreSWRunEntry 1 }

   usrreSWRunName OBJECT-TYPE
	  SYNTAX DisplayString (SIZE (0..64))
	  ACCESS read-only
	  STATUS mandatory
	  DESCRIPTION
		    "The name of the RoboExec Process."
	  ::= { usrreSWRunEntry 2 }

   usrreSWRunType OBJECT-TYPE
	  SYNTAX INTEGER {
			    unknown(1),
			    operatingSystem(2),
			    deviceDriver(3),
			    application(4),
			    forwarder(5)
		    }
	  ACCESS read-only
	  STATUS mandatory
	  DESCRIPTION
			"The type of this software."
	  ::= { usrreSWRunEntry 3 }

   usrreSWRunStatus OBJECT-TYPE
	  SYNTAX INTEGER {
			running(1),
			runnable(2),	 -- waiting for resource (CPU, memory, IO)
			notRunnable(3), -- loaded but waiting for event
 			invalid(4)	 -- not loaded
		 }
	  ACCESS read-only
	  STATUS mandatory
	  DESCRIPTION
		    "The status of this running piece of software."
	  ::= { usrreSWRunEntry 4 }

   usrreSWRunStartTime OBJECT-TYPE
	 SYNTAX INTEGER (0..2147483647)
      ACCESS read-only
      STATUS mandatory
      DESCRIPTION
             "The time when this process started. 
              NOTE: Time equal 0 indicates that per process
              statistic information is not capturing."
      ::= { usrreSWRunEntry 5 }

   usrreSWRunMsgSent OBJECT-TYPE
	 SYNTAX Counter
      ACCESS read-only
      STATUS mandatory
      DESCRIPTION
             "Number of messages were sent by this process.
              NOTE: Number of messages equal 0 indicates
              that per process statistic information is not capturing."
      ::= { usrreSWRunEntry 6 }

   usrreSWRunMsgRcvd OBJECT-TYPE
	 SYNTAX Counter
      ACCESS read-only
      STATUS mandatory
      DESCRIPTION
             "Number of messages were received by this process.
              NOTE: Number of messages equal 0 indicates
              that per process statistic information is not capturing."
      ::= { usrreSWRunEntry 7 }

   usrreSWRunMsgPassedFrom OBJECT-TYPE
	 SYNTAX Counter
      ACCESS read-only
      STATUS mandatory
      DESCRIPTION
             "Number of messages were passed from this process.
              NOTE: Number of messages equal 0 indicates
              that per process statistic information is not capturing."
      ::= { usrreSWRunEntry 8 }

   usrreSWRunMsgPassedTo OBJECT-TYPE
	 SYNTAX Counter
      ACCESS read-only
      STATUS mandatory
      DESCRIPTION
             "Number of messages were passed this process.
              NOTE: Number of messages equal 0 indicates
              that per process statistic information is not capturing."
      ::= { usrreSWRunEntry 9 }

   usrreSWRunMboxScheduled OBJECT-TYPE
	 SYNTAX Counter
      ACCESS read-only
      STATUS mandatory
      DESCRIPTION
             "The total number of times all mailboxes owned by 
             this process were scheduled.
             NOTE: Number equal 0 indicates
             that per process statistic information is not capturing."
      ::= { usrreSWRunEntry 10 }

   usrreSWRunAllocated OBJECT-TYPE
	 SYNTAX KBytes
      ACCESS read-only
      STATUS mandatory
      DESCRIPTION
             "The total amount of memory that was allocated for
             this process.
             NOTE: 0 KB indicates that per process statistic 
             information is not capturing."
      ::= { usrreSWRunEntry 11 }

   usrreSWRunFreed OBJECT-TYPE
	 SYNTAX KBytes
      ACCESS read-only
      STATUS mandatory
      DESCRIPTION
             "The total amount of memory that was freed while
             this process was running.
             NOTE: 0 KB indicates that per process statistic 
             information is not capturing."
      ::= { usrreSWRunEntry 12 }


   -- The RoboExec Logging Level Group
   --
   -- Implementation of this group is mandatory for all RoboExec's
   --
   -- The reLogLevelTable contains an entry for each software 
   -- facility running on the RoboExec.

   usrreLogLevelConfigFileName OBJECT-TYPE
	  SYNTAX DisplayString
	  ACCESS read-write
	  STATUS mandatory
	  DESCRIPTION		
		    "The name of a ConfigFile to read/write permanent database
		    records. If the value of this object is an empty string, then
		    the process uses the default name
		    `@file://RoboExecNMProcess.cfg'. "
	  ::= { usrreEvents 1 }

   usrreLogLevelCFMStatusFlag	 OBJECT-TYPE
	  SYNTAX UsrConfigStatus
	  ACCESS read-write
	  STATUS mandatory
	  DESCRIPTION
		    "Setting the value of this object to `save' causes the values
			of the RoboExec Logging Level Groupt to be written out to the
			current config file, which is stored in the
			reLogLevelConfigFileName object. While the new ConfigFile is
			being written, the value of this flag will be set to `saving''.
			Any attempts to set the value while it is  not `normal'
			(i.e. the file is currently being written to the ConfigFile)
			will result in a badValue error being returned. Setting the
			value to `normal' will result in no action."
	  ::= { usrreEvents 2 }

   usrreLogLevelTable OBJECT-TYPE
	  SYNTAX SEQUENCE OF UsrreLogLevelEntry
	  ACCESS not-accessible
	  STATUS mandatory
	  DESCRIPTION
		    "The (conceptual) table of event log levels for the
		    RoboExec."
	  ::= { usrreEvents 3 }

   usrreLogLevelEntry OBJECT-TYPE
	  SYNTAX UsrreLogLevelEntry
	  ACCESS not-accessible
	  STATUS mandatory
	  DESCRIPTION
		    "A (conceptual) entry for one facility on the RoboExec

		    As an example of how objects in this table are
		    named, an instance of the reSWRunName object might
		    be named reSWRunName.1287"
	  INDEX { usrreLLFacility }
	  ::= { usrreLogLevelTable 1 }

   UsrreLogLevelEntry ::= SEQUENCE {
		 usrreLLFacility	   INTEGER,
		 usrreLLFacilityName   DisplayString,
		 usrreLLLogLevel	   INTEGER
	  }

   usrreLLFacility OBJECT-TYPE
	  SYNTAX INTEGER (1..64)
	  ACCESS not-accessible
	  STATUS mandatory
	  DESCRIPTION
		    "A unique value for each software facility
		    on the RoboExec."
	  ::= { usrreLogLevelEntry 1 }

   usrreLLFacilityName OBJECT-TYPE
	  SYNTAX DisplayString (SIZE (0..64))
	  ACCESS read-only
	  STATUS mandatory
	  DESCRIPTION
		    "A textual name of the software facility."
	  ::= { usrreLogLevelEntry 2 }

   usrreLLLogLevel OBJECT-TYPE
	  SYNTAX INTEGER { critical(0),
				    unusual(1),
				    common(2),
				    verbose(3),
				    debug(4) }
	  ACCESS read-write
	  STATUS mandatory
	  DESCRIPTION
		    "The Logging level for this software facility."
	  --CONFIGURABLE
	  ::= { usrreLogLevelEntry 3 }

   usrreEvLocalFile OBJECT-TYPE
	  SYNTAX DisplayString
	  ACCESS read-only
	  STATUS mandatory
	  DESCRIPTION
		    "The file name of the local NVRAM logfile."
	  ::= { usrreEvents 4 }

   usrreEvOldLocalFile OBJECT-TYPE
	  SYNTAX DisplayString
	  ACCESS read-only
	  STATUS mandatory
	  DESCRIPTION
		    "The name of the file that the Event Handler should copy the
		    old LocalFile contents to when the pilgrim system reboots."
	  ::= { usrreEvents 5 }

   usrreEvCriticalMsgsTable OBJECT-TYPE
	  SYNTAX SEQUENCE OF UsrreEvCriticalMsgsEntry
	  ACCESS not-accessible
	  STATUS mandatory
	  DESCRIPTION
		    "The (conceptual) table of critical event messages."
	  ::= { usrreEvents 6 }

   usrreEvStatus OBJECT-TYPE
	  SYNTAX INTEGER {
		disable(0),
		enable(1)
	}
	  ACCESS read-write
	  STATUS mandatory
	  DESCRIPTION
              "This switch allows disabling or enabling all logging
               of critical events to the local flash file system.
               This is disable by default."
	  --CONFIGURABLE
	  ::= { usrreEvents 7 }

   usrreEvCriticalMsgsEntry OBJECT-TYPE
	  SYNTAX UsrreEvCriticalMsgsEntry
	  ACCESS not-accessible
	  STATUS mandatory
	  DESCRIPTION
		    "A (conceptual) entry for one critical event message."
	  INDEX { usrreEvCritMsgTimeStamp }
	  ::= { usrreEvCriticalMsgsTable 1 }

   UsrreEvCriticalMsgsEntry ::= SEQUENCE {
	  usrreEvCritMsgTimeStamp INTEGER,
	  usrreEvCriticalMsg  DisplayString
	}

   usrreEvCritMsgTimeStamp OBJECT-TYPE
	  SYNTAX INTEGER
	  ACCESS not-accessible
	  STATUS mandatory
	  DESCRIPTION
		    "Index into the table of critical event messages saved in the
		    NVRAM local file. This represents the time, in hundredths of
		    seconds since system startup, at which the critical event
		    occurred."
	  ::= { usrreEvCriticalMsgsEntry 1 }

   usrreEvCriticalMsg OBJECT-TYPE
	  SYNTAX DisplayString
	  ACCESS read-only
	  STATUS mandatory
	  DESCRIPTION
		    "Text of a critical event message."
	  ::= { usrreEvCriticalMsgsEntry 2 }



   -- The RoboExec System Counters Group
   --
   -- This group references counters defined in the RoboExec for
   -- certain system calls.
   -- This section of the MIB is still under development and it is likely
   -- that counters will be obseleted or more counters will be added.
   --
   -- Implementation of this group is mandatory for a RoboExec system.
   --

   -- Define the groups within the counters group

   usrreCntBuffers	OBJECT IDENTIFIER ::= { usrreCounters 1 }
   usrreCntHeap	OBJECT IDENTIFIER ::= { usrreCounters 2 }
   usrreCntMessage	OBJECT IDENTIFIER ::= { usrreCounters 3 }
   usrreCntEvents	OBJECT IDENTIFIER ::= { usrreCounters 4 }
   usrreCntNames	OBJECT IDENTIFIER ::= { usrreCounters 5 }
   usrreCntSched	OBJECT IDENTIFIER ::= { usrreCounters 6 }

	--
	-- Counters for the buffer calls
	--
	usrreCBgetBuffer OBJECT-TYPE
		SYNTAX Counter
		ACCESS read-only
		STATUS mandatory
		DESCRIPTION	"The number of times exec_get_buffer() was called"
		::= { usrreCntBuffers 1 }

	usrreCBfreeBchain OBJECT-TYPE
		SYNTAX Counter
		ACCESS read-only
		STATUS mandatory
		DESCRIPTION	"The number of times exec_free_bchain() was called"
		::= { usrreCntBuffers 2 }

	usrreCBreplicateBufdesc OBJECT-TYPE
		SYNTAX Counter
		ACCESS read-only
		STATUS mandatory
		DESCRIPTION	"The number of times exec_replicate_bufdesc() was called"
		::= { usrreCntBuffers 3 }

	usrreCBreplicateListToBchain OBJECT-TYPE
		SYNTAX Counter
		ACCESS read-only
		STATUS mandatory
		DESCRIPTION	"The number of times exec_replicate_list_to_bchain() was called"
		::= { usrreCntBuffers 4 }

	usrreCBreplPartialBchain OBJECT-TYPE
		SYNTAX Counter
		ACCESS read-only
		STATUS mandatory
		DESCRIPTION	"The number of times exec_repl_partial_bchain() was called"
		::= { usrreCntBuffers 5 }

	usrreCBduplicateBchain OBJECT-TYPE
		SYNTAX Counter
		ACCESS read-only
		STATUS mandatory
		DESCRIPTION	"The number of times exec_duplicate_bchain() was called"
		::= { usrreCntBuffers 6 }

	usrreCBpullupBchain OBJECT-TYPE
		SYNTAX Counter
		ACCESS read-only
		STATUS mandatory
		DESCRIPTION	"The number of times exec_pullup_bchain() was called"
		::= { usrreCntBuffers 7 }

	usrreCBjoinBchains OBJECT-TYPE
		SYNTAX Counter
		ACCESS read-only
		STATUS mandatory
		DESCRIPTION	"The number of times exec_join_bchains() was called"
		::= { usrreCntBuffers 8  }

	usrreCBtrimBchain OBJECT-TYPE
		SYNTAX Counter
		ACCESS read-only
		STATUS mandatory
		DESCRIPTION	"The number of times exec_trim_bchain() was called"
		::= { usrreCntBuffers 9 }

	usrreCBmaskBchain OBJECT-TYPE
		SYNTAX Counter
		ACCESS read-only
		STATUS mandatory
		DESCRIPTION	"The number of times exec_mask_bchain() was called"
		::= { usrreCntBuffers 10 }

	usrreCBunmaskBchain OBJECT-TYPE
		SYNTAX Counter
		ACCESS read-only
		STATUS mandatory
		DESCRIPTION	"The number of times exec_unmask_bchain() was called"
		::= { usrreCntBuffers 11 }

	usrreCBsetBchainSize OBJECT-TYPE
		SYNTAX Counter
		ACCESS read-only
		STATUS mandatory
		DESCRIPTION	"The number of calls to exec_set_bchain_size()."
		::= { usrreCntBuffers 12 }

	usrreCBbchainSize OBJECT-TYPE
		SYNTAX Counter
		ACCESS read-only
		STATUS mandatory
		DESCRIPTION	"The number of calls to exec_bchain_size()."
		::= { usrreCntBuffers 13 }

	usrreCBbchainCount OBJECT-TYPE
		SYNTAX Counter
		ACCESS read-only
		STATUS mandatory
		DESCRIPTION	"The number of calls to exec_bchain_count()."
		::= { usrreCntBuffers 14 }

	usrreCBcheckBchain OBJECT-TYPE
		SYNTAX Counter
		ACCESS read-only
		STATUS mandatory
		DESCRIPTION	"The number of calls to exec_check_bchain()."
		::= { usrreCntBuffers 15 }

	usrreCBcopyBchainToBlock OBJECT-TYPE
		SYNTAX Counter
		ACCESS read-only
		STATUS mandatory
		DESCRIPTION	"The number of calls to exec_copy_bchain_to_block()."
		::= { usrreCntBuffers 16 }

	usrreCBcopyBlockToBchain OBJECT-TYPE
		SYNTAX Counter
		ACCESS read-only
		STATUS mandatory
		DESCRIPTION	"The number of calls to exec_copy_block_to_bchain()."
		::= { usrreCntBuffers 17 }

	usrreCBprependToBchain OBJECT-TYPE
		SYNTAX Counter
		ACCESS read-only
		STATUS mandatory
		DESCRIPTION	"The number of calls to exec_prepend_to_bchain()."
		::= { usrreCntBuffers 18 }

	usrreCBappendToBchain OBJECT-TYPE
		SYNTAX Counter
		ACCESS read-only
		STATUS mandatory
		DESCRIPTION	"The number of calls to exec_append_to_bchain()."
		::= { usrreCntBuffers 19 }

	usrreCBdetachBuffer OBJECT-TYPE
		SYNTAX Counter
		ACCESS read-only
		STATUS mandatory
		DESCRIPTION	"The number of calls to exec_detach_buffer()."
		::= { usrreCntBuffers 20 }

	usrreCBbufferFromBlock OBJECT-TYPE
		SYNTAX Counter
		ACCESS read-only
		STATUS mandatory
		DESCRIPTION	"The number of calls to exec_buffer_from_block()."
		::= { usrreCntBuffers 21 }

	usrreCBallocProtocolBuffer OBJECT-TYPE
		SYNTAX Counter
		ACCESS read-only
		STATUS mandatory
		DESCRIPTION	"The number of calls to exec_alloc_protocol_buffer()."
		::= { usrreCntBuffers 22 }

	usrreCBsplitBchain OBJECT-TYPE
		SYNTAX Counter
		ACCESS read-only
		STATUS mandatory
		DESCRIPTION	"The number of calls to exec_split_bchain()."
		::= { usrreCntBuffers 23 }

	usrreCBtimestampBchain OBJECT-TYPE
		SYNTAX Counter
		ACCESS read-only
		STATUS mandatory
		DESCRIPTION	"The number of calls to exec_timestamp_bchain()."
		::= { usrreCntBuffers 24 }

	usrreCBtimediffBchain OBJECT-TYPE
		SYNTAX Counter
		ACCESS read-only
		STATUS mandatory
		DESCRIPTION	"The number of calls to exec_timediff_bchain()."
		::= { usrreCntBuffers 25 }

	usrreCBbchainSetCorrelator OBJECT-TYPE
		SYNTAX Counter
		ACCESS read-only
		STATUS mandatory
		DESCRIPTION	"The number of calls to exec_bchain_set_correlator()."
		::= { usrreCntBuffers 26 }

	usrreCBprotectBchain OBJECT-TYPE
		SYNTAX Counter
		ACCESS read-only
		STATUS mandatory
		DESCRIPTION	"The number of calls to exec_protect_bchain()."
		::= { usrreCntBuffers 27 }

	usrreCBunprotectBchain OBJECT-TYPE
		SYNTAX Counter
		ACCESS read-only
		STATUS mandatory
		DESCRIPTION	"The number of calls to exec_unprotect_bchain()."
		::= { usrreCntBuffers 28 }

	--
	-- Counters for the memory heap calls
	--
	usrreCHallocateHeap OBJECT-TYPE
		SYNTAX Counter
		ACCESS read-only
		STATUS mandatory
		DESCRIPTION	"The number of calls to exec_allocate_heap()."
		::= { usrreCntHeap 1 }

	usrreCHfreeHeap OBJECT-TYPE
		SYNTAX Counter
		ACCESS read-only
		STATUS mandatory
		DESCRIPTION	"The number of calls to exec_free_heap()."
		::= { usrreCntHeap 2 }

	usrreCHreallocHeap OBJECT-TYPE
		SYNTAX Counter
		ACCESS read-only
		STATUS mandatory
		DESCRIPTION	"The number of calls to exec_realloc_heap()."
		::= { usrreCntHeap 3 }

	usrreCHduplicateHeap OBJECT-TYPE
		SYNTAX Counter
		ACCESS read-only
		STATUS mandatory
		DESCRIPTION	"The number of calls to exec_duplicate_heap()."
		::= { usrreCntHeap 4 }

	usrreCHheapCoalesce OBJECT-TYPE
		SYNTAX Counter
		ACCESS read-only
		STATUS mandatory
		DESCRIPTION	"The number of calls to exec_heap_coalesce()."
		::= { usrreCntHeap 5 }

	usrreCHcoalesceToABlock OBJECT-TYPE
		SYNTAX Counter
		ACCESS read-only
		STATUS mandatory
		DESCRIPTION	"The number of successful calls to exec_coalesce_to_a_block()."
		::= { usrreCntHeap 6 }

	usrreCHheapInfo OBJECT-TYPE
		SYNTAX Counter
		ACCESS read-only
		STATUS mandatory
		DESCRIPTION	"The number of calls to exec_heap_info()."
		::= { usrreCntHeap 7 }

	usrreCHheapSetCorrelator OBJECT-TYPE
		SYNTAX Counter
		ACCESS read-only
		STATUS mandatory
		DESCRIPTION	"The number of calls to exec_heap_set_correlator()."
		::= { usrreCntHeap 8 }

	usrreCHuseHeap OBJECT-TYPE
		SYNTAX Counter
		ACCESS read-only
		STATUS mandatory
		DESCRIPTION	"The number of calls to exec_use_heap()."
		::= { usrreCntHeap 9 }

	usrreCHheapGetUseCnt OBJECT-TYPE
		SYNTAX Counter
		ACCESS read-only
		STATUS mandatory
		DESCRIPTION	"The number of calls to exec_heap_get_usecnt()."
		::= { usrreCntHeap 10 }

	usrreCHfreeCacheBlocks OBJECT-TYPE
		SYNTAX Counter
		ACCESS read-only
		STATUS mandatory
		DESCRIPTION	"The number of outstanding free blocks in the heap cache."
		::= { usrreCntHeap 11 }

	usrreCHfreeHeapBlocks OBJECT-TYPE
		SYNTAX Counter
		ACCESS read-only
		STATUS mandatory
		DESCRIPTION	"The number of outstanding free blocks in the heap's heap."
		::= { usrreCntHeap 12 }

	usrreCHheapCheckProtection OBJECT-TYPE
		SYNTAX Counter
		ACCESS read-only
		STATUS mandatory
		DESCRIPTION	"The number of calls to exec_heap_check_protection()."
		::= { usrreCntHeap 13 }

	usrreCHheapSetProtection OBJECT-TYPE
		SYNTAX Counter
		ACCESS read-only
		STATUS mandatory
		DESCRIPTION	"The number of calls to exec_heap_set_protection()."
		::= { usrreCntHeap 14 }

	usrreCHheapRemoveProtection OBJECT-TYPE
		SYNTAX Counter
		ACCESS read-only
		STATUS mandatory
		DESCRIPTION	"The number of calls to exec_heap_remove_protection()."
		::= { usrreCntHeap 15 }

	usrreCHheapProtectionInfo OBJECT-TYPE
		SYNTAX Counter
		ACCESS read-only
		STATUS mandatory
		DESCRIPTION	"The number of calls to exec_heap_protection_info()."
		::= { usrreCntHeap 16 }

	--
	-- Counters for the message calls
	--
	usrreCMallocMsg OBJECT-TYPE
		SYNTAX Counter
		ACCESS read-only
		STATUS mandatory
		DESCRIPTION	"The number of calls to exec_alloc_msg()."
		::= { usrreCntMessage 1 }

	usrreCMfreemsg OBJECT-TYPE
		SYNTAX Counter
		ACCESS read-only
		STATUS mandatory
		DESCRIPTION	"The number of calls to exec_freemsg()."
		::= { usrreCntMessage 2 }

	usrreCMwasMsgPassed OBJECT-TYPE
		SYNTAX Counter
		ACCESS read-only
		STATUS mandatory
		DESCRIPTION	"The number of calls to exec_was_msg_passed()."
		::= { usrreCntMessage 3 }

	usrreCMrespondToMsg OBJECT-TYPE
		SYNTAX Counter
		ACCESS read-only
		STATUS mandatory
		DESCRIPTION	"The number of calls to exec_respond_to_msg()."
		::= { usrreCntMessage 4 }

	usrreCMmessageSend OBJECT-TYPE
		SYNTAX Counter
		ACCESS read-only
		STATUS mandatory
		DESCRIPTION	"The number of calls to exec_message_send()."
		::= { usrreCntMessage 5 }

	usrreCMsendmsg OBJECT-TYPE
		SYNTAX Counter
		ACCESS read-only
		STATUS mandatory
		DESCRIPTION	"The number of calls to exec_sendmsg()."
		::= { usrreCntMessage 6 }

	usrreCMreceiveMail OBJECT-TYPE
		SYNTAX Counter
		ACCESS read-only
		STATUS mandatory
		DESCRIPTION	"The number of calls to exec_receive_mail()."
		::= { usrreCntMessage 7 }

	usrreCMpassmsg OBJECT-TYPE
		SYNTAX Counter
		ACCESS read-only
		STATUS mandatory
		DESCRIPTION	"The number of calls to exec_passmg()."
		::= { usrreCntMessage 8 }

	usrreCMcountMail OBJECT-TYPE
		SYNTAX Counter
		ACCESS read-only
		STATUS mandatory
		DESCRIPTION	"The number of calls to exec_count_mail()."
		::= { usrreCntMessage 9 }

	--
	-- Counters for the event calls
	--
	usrreCEevents OBJECT-TYPE
		SYNTAX Counter
		ACCESS read-only
		STATUS mandatory
		DESCRIPTION	"The number of calls to exec_events()."
		::= { usrreCntEvents 1 }

	usrreCEeventsLogged OBJECT-TYPE
		SYNTAX Counter
		ACCESS read-only
		STATUS mandatory
		DESCRIPTION	"The number of calls to exec_events() that were logged."
		::= { usrreCntEvents 2 }

	usrreCEeventsDropped OBJECT-TYPE
		SYNTAX Counter
		ACCESS read-only
		STATUS mandatory
		DESCRIPTION	"The number of calls to exec_events() that were dropped."
		::= { usrreCntEvents 3 }


	--
	-- Counters for the Name calls
	--
	usrreCNregisterName OBJECT-TYPE
		SYNTAX Counter
		ACCESS read-only
		STATUS mandatory
		DESCRIPTION	"The number of calls to exec_register_name()."
		::= { usrreCntNames 1 }

	usrreCNresolveName OBJECT-TYPE
		SYNTAX Counter
		ACCESS read-only
		STATUS mandatory
		DESCRIPTION	"The number of calls to exec_resolve_name()."
		::= { usrreCntNames 2 }

	usrreCNremoveName OBJECT-TYPE
		SYNTAX Counter
		ACCESS read-only
		STATUS mandatory
		DESCRIPTION	"The number of calls to exec_remove_name()."
		::= { usrreCntNames 3 }

	usrreCNremoveNameForData OBJECT-TYPE
		SYNTAX Counter
		ACCESS read-only
		STATUS mandatory
		DESCRIPTION
			"The number of names that were removed because the data they
			 pointed to was no longer there (mailbox delete e.g.)."
		::= { usrreCntNames 4 }

	usrreCNremoveNameForProc OBJECT-TYPE
		SYNTAX Counter
		ACCESS read-only
		STATUS mandatory
		DESCRIPTION
			"The number of names that were removed because the process
			 that owned them was killed."
		::= { usrreCntNames 5 }


	--
	-- Counters for the scheduling information
	--
	usrreCScurrentMsgsQueued OBJECT-TYPE
		SYNTAX Counter
		ACCESS read-only
		STATUS mandatory
		DESCRIPTION	"The current number of messages queued."
		::= { usrreCntSched 1 }

	usrreCSmaxMsgsQueued OBJECT-TYPE
		SYNTAX Counter
		ACCESS read-only
		STATUS mandatory
		DESCRIPTION	"The all time high number of messages queued."
		::= { usrreCntSched 2 }

	usrreCSrunTotalMsgsQueued OBJECT-TYPE
		SYNTAX Counter
		ACCESS read-only
		STATUS mandatory
		DESCRIPTION	"The a running total of the messages queued."
		::= { usrreCntSched 3 }

	usrreCScurrentMboxesReady OBJECT-TYPE
		SYNTAX Counter
		ACCESS read-only
		STATUS mandatory
		DESCRIPTION	"The current number of mailboxes ready to run."
		::= { usrreCntSched 4 }

	usrreCSmaxMboxesReady OBJECT-TYPE
		SYNTAX Counter
		ACCESS read-only
		STATUS mandatory
		DESCRIPTION	"The all time high number of mailboxes ready to run."
		::= { usrreCntSched 5 }

	usrreCSrunTotalMboxesReady OBJECT-TYPE
		SYNTAX Counter
		ACCESS read-only
		STATUS mandatory
		DESCRIPTION	"The a running total of the mailboxes ready to run."
		::= { usrreCntSched 6 }

	usrreCSschedLoops OBJECT-TYPE
		SYNTAX Counter
		ACCESS read-only
		STATUS mandatory
		DESCRIPTION
			"The number of times we've run through the scheduling loop."
		::= { usrreCntSched 7 }


	--
	-- The RoboExec Name Group
	--
	usrreNameTable OBJECT-TYPE
		SYNTAX SEQUENCE OF UsrreNameEntry
		ACCESS not-accessible
		STATUS mandatory
		DESCRIPTION
			  "The (conceptual) table of the names kept by the RoboExec."
		::= { usrreNames 1 }

	 usrreNameEntry OBJECT-TYPE
		SYNTAX UsrreNameEntry
		ACCESS not-accessible
		STATUS mandatory
		DESCRIPTION
			  "A (conceptual) entry for one name."
		INDEX { usrreNameType, usrreNameName }
		::= { usrreNameTable 1 }

	 UsrreNameEntry ::= SEQUENCE {
		usrreNameType			DisplayString,
		usrreNameName		 	DisplayString,
		usrreNameIntOrString	INTEGER,
		usrreNameIntValue		INTEGER,
		usrreNameStringValue	DisplayString,
		usrreNameOwner			INTEGER
		}

	 usrreNameType OBJECT-TYPE
		SYNTAX DisplayString (SIZE (0..64))
		ACCESS not-accessible
		STATUS mandatory
		DESCRIPTION
			  "The internal type of the name."
		::= { usrreNameEntry 1 }

	 usrreNameName OBJECT-TYPE
		SYNTAX DisplayString (SIZE (0..64))
		ACCESS not-accessible
		STATUS mandatory
		DESCRIPTION
			  "The name in the RoboExec"
		::= { usrreNameEntry 2 }

	 usrreNameIntOrString OBJECT-TYPE
		SYNTAX INTEGER {
				  integer(1),
				  string(2),
				  neither(3)
			  }
		ACCESS read-only
		STATUS mandatory
		DESCRIPTION
			"Is the data for this name a string or an integer?"
		::= { usrreNameEntry 3 }

	 usrreNameIntValue OBJECT-TYPE
		SYNTAX INTEGER
		ACCESS read-only
		STATUS mandatory
		DESCRIPTION
			  "If the name has a numerical value, this is it.
			   Otherwise, this value is 0."
		::= { usrreNameEntry 4 }

	 usrreNameStringValue OBJECT-TYPE
		SYNTAX DisplayString (SIZE (0..200))
		ACCESS read-only
		STATUS mandatory
		DESCRIPTION
			  "If the name has a string value, this is it.
			   Otherwise, this value is blank."
		::= { usrreNameEntry 5 }

	 usrreNameOwner OBJECT-TYPE
		SYNTAX INTEGER
		ACCESS read-only
		STATUS mandatory
		DESCRIPTION
			"The process ID of the owner of this name.
			This should correlate with the usrreSWRunIndex."
		::= { usrreNameEntry 6 }


	--
	-- The RoboExec FileSystem Group
	--

	--
	-- File system information
	--
	usrreFSInfoTable OBJECT-TYPE
		SYNTAX SEQUENCE OF UsrreFSInfoEntry
		ACCESS not-accessible
		STATUS mandatory
		DESCRIPTION
			  "The (conceptual) table of the File System information kept
			   by the RoboExec."
		::= { usrreFiles 1 }

	 usrreFSInfoEntry OBJECT-TYPE
		SYNTAX UsrreFSInfoEntry
		ACCESS not-accessible
		STATUS mandatory
		DESCRIPTION
			  "A (conceptual) entry for one file system."
		INDEX { usrreFSInfoIndex }
		::= { usrreFSInfoTable 1 }

	 UsrreFSInfoEntry ::= SEQUENCE {
		usrreFSInfoIndex		INTEGER,
		usrreFSInfoName		DisplayString,
		usrreFSInfoType		INTEGER
		}

	 usrreFSInfoIndex OBJECT-TYPE
		SYNTAX INTEGER
		ACCESS not-accessible
		STATUS mandatory
		DESCRIPTION
			  "And index to the file systems."
		::= { usrreFSInfoEntry 1 }

	 usrreFSInfoName OBJECT-TYPE
		SYNTAX DisplayString (SIZE (0..64))
		ACCESS read-only
		STATUS mandatory
		DESCRIPTION
			  "A name given to the file system."
		::= { usrreFSInfoEntry 2 }

	 usrreFSInfoType OBJECT-TYPE
		SYNTAX INTEGER {
				flashRAM(1),
				ram(2),
				floppyDisk(3),
				hardDisk(4)
			  }
		ACCESS read-only
		STATUS mandatory
		DESCRIPTION
			"The type of this file system."
		::= { usrreFSInfoEntry 3 }


	--
	-- File Table
	--
	usrreFileTable OBJECT-TYPE
		SYNTAX SEQUENCE OF UsrreFileTableEntry
		ACCESS not-accessible
		STATUS mandatory
		DESCRIPTION
			  "The (conceptual) table of the files for a file system."
		::= { usrreFiles 2 }

	 usrreFileTableEntry OBJECT-TYPE
		SYNTAX UsrreFileTableEntry
		ACCESS not-accessible
		STATUS mandatory
		DESCRIPTION
			  "A (conceptual) entry for one file system."
		INDEX { usrreFileTableFileSystem, usrreFileTableName }
		::= { usrreFileTable 1 }

	 UsrreFileTableEntry ::= SEQUENCE {
		usrreFileTableFileSystem	INTEGER,
		usrreFileTableName		 DisplayString,
		usrreFileTableSize		 INTEGER,
		usrreFileTableRenameTo	 DisplayString,
		usrreFileTableStatus	 INTEGER,
		usrreFileTableCopyTo	 DisplayString,
		usrreFileTableErrorString DisplayString
		}

	 usrreFileTableFileSystem OBJECT-TYPE
		SYNTAX INTEGER
		ACCESS not-accessible
		STATUS mandatory
		DESCRIPTION
			  "The file system containing this file. This must
			   match the file system from the File System Info Table."
		::= { usrreFileTableEntry 1 }

	 usrreFileTableName OBJECT-TYPE
		SYNTAX DisplayString (SIZE (0..64))
		ACCESS not-accessible
		STATUS mandatory
		DESCRIPTION
			  "The name given to the file."
		::= { usrreFileTableEntry 2 }

	 usrreFileTableSize OBJECT-TYPE
		SYNTAX INTEGER
		ACCESS read-only
		STATUS mandatory
		DESCRIPTION
			"The size, in octets, of the file."
		::= { usrreFileTableEntry 3 }

	 usrreFileTableRenameTo OBJECT-TYPE
		SYNTAX DisplayString (SIZE (0..64))
		ACCESS read-write
		STATUS mandatory
		DESCRIPTION
			"In order to change the name of this file, the
			new name should be written to this object."
		::= { usrreFileTableEntry 4 }

	usrreFileTableStatus OBJECT-TYPE
		SYNTAX INTEGER {
				normal(1),
				delete(2),
				copying(3),       -- File copying in progress
				failed(4)         -- Operation failed		
			}
		ACCESS read-write
		STATUS mandatory
		DESCRIPTION
			"The status of the file. Valid row entries in this
			table have the status field set to normal.
			The settable value is delete: write 2 to this variable 
			to delete the file. The values normal(1), in_progress(3), 
			and failed(4) are read-only"
		::= { usrreFileTableEntry 5 }

	usrreFileTableCopyTo OBJECT-TYPE
		SYNTAX DisplayString (SIZE (0..64))
		ACCESS read-write
		STATUS mandatory
		DESCRIPTION
			"In order to copy this file, the
			new name should be written to this object."
		::= { usrreFileTableEntry 6 }

	usrreFileTableErrorString OBJECT-TYPE
         SYNTAX  DisplayString (SIZE (0..255))
         ACCESS  read-only
         STATUS  mandatory
         DESCRIPTION
            "The error string returned when file copy or rename fails.
             Otherwise, this field is NULL."		
		::= { usrreFileTableEntry 7 }

	 END

--
-- For the revision history to work correctly, after a new MIB file has been
-- added to the CVS repository the first time the CVS Admin person needs to
-- set the correct comment string delimter for the file.
--
-- $Log: REmib.mib,v $
-- Revision 1.21.8.6  1998/06/15 22:43:01  gjoesph
-- new command show memory utilization
--
-- Revision 1.21.8.5  1998/03/03 03:41:01  mharper
-- MR5669 CPU utilization estimates
--
-- Revision 1.21.8.4  1997/12/19 13:20:16  psd
-- Another merge from 2.0
--
--Revision 1.25.2.2  1997/12/15  20:34:20  olga
--Add ability to turn writing critical events to flash ON/OFF (MR# 3301)
--
-- Revision 1.25.2.1  1997/09/05 15:09:24  psd
-- Changes to MIBs so that they compile using the SimpleTester.
--
--Revision 1.25  1997/07/15  21:20:14  olga
--Extend usrreSWRunStartTime value's range to accept 0. MR# 1703
--
-- Revision 1.24  1997/06/18 20:48:26  olga
-- Add heap statistics as it was required in MR666
--
-- Revision 1.23  1997/05/30 15:29:27  olga
-- Add support for Copy Files via SNMP
--
-- Revision 1.22  1997/05/27 18:03:51  olga
-- Add MIB support for File Copying
--
-- Revision 1.21.8.3  1997/09/17 19:06:16  psd
-- Merged 2.0 to 3.0
--
--Revision 1.21.8.2  1997/06/18  23:39:21  olga
--Add heap statistics as was required in MR666
--
-- Revision 1.21.8.1  1997/05/30 20:51:59  olga
-- Merge Copy File Process into the pilgtim30 branch
--
-- Revision 1.21  1996/10/03 20:40:04  olga
-- Add per process statistics
--
-- Revision 1.20  1996/09/30 20:38:31  pfc
-- flashROM -> flashRAM
--
-- Revision 1.19  1996/09/30 20:31:31  pfc
-- Add scheduling counters and file system mibs
--
-- Revision 1.18  1996/09/25 21:09:24  pfc
-- Add scheduling counters
--
-- Revision 1.17  1996/09/10 18:16:49  olga
-- Add new entries into REmib.mib
--
-- Revision 1.16  1996/08/20 18:44:28  pfc
-- Add name MIB group
--
-- Revision 1.15  1996/08/19 15:36:06  pfc
-- Add a lot of counters to track usage
--
-- Revision 1.14  1996/05/08 19:42:40  jhalpin
-- Make Critical Event files read-only
--
-- Revision 1.13  1996/04/15 15:22:19  pfc
-- Prefix the symbol names with usr
--
-- Revision 1.12  1996/04/11 18:48:27  pfc
-- Add some variables to make dad happy
--
-- Revision 1.11  1996/03/26 22:05:13  psd
-- Removed the CONFIGURABLE flag from the Config File object.
--
-- Revision 1.10  1996/03/21 16:26:39  psd
-- Added the Critical Event table.
--
-- Revision 1.9  1996/03/18 23:25:59  jhalpin
-- Update mib files
--
-- Revision 1.8  1996/02/22 21:23:31  pfc
-- More in the egg
--
-- Revision 1.7  1996/02/22 21:08:01  pfc
-- Add easter egg
--
-- Revision 1.6  1996/01/26 20:11:04  pfc
-- RunStatus should be read-only
--
-- Revision 1.5  1995/11/17 17:12:13  jhalpin
-- Updated RoboExec and usrConfig MIB sources
--
-- Revision 1.4  1995/10/26 20:48:48  jhalpin
-- Got rid on nonexistent MIB Objects, fixed DisplayStrings, and removed missing subids
--
-- Revision 1.3  1995/09/21 19:05:42  pfc
-- Delete unused imports.
--
-- Revision 1.2  1995/09/18 20:27:16  pfc
-- 1) Put the RoboExec mib in the right place under Pilgrim.
-- 2) Add the logging level table into the RoboExec MIB
--
-- Revision 1.1  1995/08/31 14:43:50  jhalpin
-- Add template info and clean up.
--
--
--
--
-- Local Variables:
-- tab-width:5
-- tab-stop-list:( 5 10 15 20 25 30 35 40 45 50 55 60 65 70 75 80)
-- End:
--
--
--	EEgg.mib - The Pilgrim Easter Egg MIB
--
--  | Copyright (c) 1996 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

   EASTER-EGG-MIB DEFINITIONS ::= BEGIN

   IMPORTS
       OBJECT-TYPE              FROM RFC-1212
       roboExec, DisplayString  FROM USR-DEFINITIONS-MIB;

   usrreEasterEgg     OBJECT IDENTIFIER ::= { roboExec 4 }

   -- The RoboExec Easter Egg Group
   --
   -- Implementation of this group is purely at the whim of the implementors
   --
   -- The reEasterEggTable contains an entry for each member of the
   -- team working on the Pilgrim project

   usrreEasterEggTable OBJECT-TYPE
       SYNTAX SEQUENCE OF UsrreEasterEggEntry
       ACCESS not-accessible
       STATUS mandatory
       DESCRIPTION
              "The table of Pilgrim developers."
       ::= { usrreEasterEgg 1 }

   usrreEasterEggEntry OBJECT-TYPE
       SYNTAX UsrreEasterEggEntry
       ACCESS not-accessible
       STATUS mandatory
       DESCRIPTION
              "An entry for one Pilgrim developer."
       INDEX { usrreEEIndex }
       ::= { usrreEasterEggTable 1 }

   UsrreEasterEggEntry ::= SEQUENCE {
           usrreEEIndex         INTEGER,
           usrreEEName          DisplayString,
           usrreEENickName      DisplayString,
           usrreEEQuote         DisplayString
       }

   usrreEEIndex OBJECT-TYPE
       SYNTAX INTEGER
       ACCESS read-only
       STATUS mandatory
       DESCRIPTION
              "A unique value for each Pilgrim developer."
       ::= { usrreEasterEggEntry 1 }

   usrreEEName OBJECT-TYPE
       SYNTAX DisplayString (SIZE (0..64))
       ACCESS read-only
       STATUS mandatory
       DESCRIPTION
              "A textual name of the developer."
       ::= { usrreEasterEggEntry 2 }

   usrreEENickName OBJECT-TYPE
       SYNTAX DisplayString (SIZE (0..64))
       ACCESS read-only
       STATUS mandatory
       DESCRIPTION
              "Another name for the same person..."
	  --GORDY
       ::= { usrreEasterEggEntry 3 }

   usrreEEQuote OBJECT-TYPE
       SYNTAX DisplayString
       ACCESS read-only
       STATUS mandatory
       DESCRIPTION
              "A quote of note..."
	  --GORDY
       ::= { usrreEasterEggEntry 4 }

   usrJimbo OBJECT-TYPE
       SYNTAX DisplayString
       ACCESS read-only
       STATUS mandatory
       DESCRIPTION
              "An entry in the MIB tree to honor the designer of
		     the Pilgrim Network Management Architecture."
       --GORDY
       ::= { usrreEasterEgg 2 }

   END

--
-- For the revision history to work correctly, after a new MIB file has been
-- added to the CVS repository the first time the CVS Admin person needs to
-- set the correct comment string delimter for the file.
--
-- $Log: EEgg.mib,v $
-- Revision 1.1.10.2  1997/09/17 19:06:13  psd
-- Merged 2.0 to 3.0
--
--Revision 1.2  1997/07/02  14:44:45  pfc
--An honorarium
--
--Revision 1.1.10.1  1997/07/10  15:20:45  pfc
--Merge forward
--
-- Revision 1.1  1996/04/15 15:22:20  pfc
-- Prefix the symbol names with usr
--
--
--
--
--
-- Local Variables:
-- tab-width:5
-- tab-stop-list:( 5 10 15 20 25 30 35 40 45 50 55 60 65 70 75 80)
-- End:
--
--
--	usr_ipx.mib - A template MIB file for Pilgrim MIB modules
--
--
-- Author:         Craig C. Boyle
--
-- $Id: usr_ipx.mib,v 1.14.8.4 1998/05/19 22:52:28 senthil Exp $
--
--  | Copyright (c) 1995 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

IpxHost-MIB DEFINITIONS ::= BEGIN

	IMPORTS
		  Counter32
				  FROM SNMPv2-SMI
          OBJECT-TYPE
                  FROM RFC-1212
          PhysAddress, usrIpx, UsrConfigStatus, DisplayString
                  FROM USR-DEFINITIONS-MIB;

   -- textual conventions
   -- 
   -- textual conventions are like pre-processor macro in 'C'
   --        (i.e. #define statements)
   -- Use them to define your own 'datatypes'

   -- memory size, expressed in units of 1024bytes
   KBytes ::=    INTEGER (0..2147483647)

   NetNumber ::= OCTET STRING (SIZE(4))

   UsrIpxStates ::= INTEGER   {
                              initializing(1),
					     enable(2),          -- Normal state following powerup of reenable.
                              shutdown(3),        -- Immediately following a disable command.
                              disable(4)          -- Following RIP shutdown. 
     	                    }

   -- Begin managed object definitions here...

	usrIpxVersionNumber OBJECT-TYPE
         SYNTAX   INTEGER
         ACCESS   read-only
         STATUS   mandatory
         DESCRIPTION
            "The version number for the IPX module."
         ::= { usrIpx 1 }

     usrIpxSplitEqualCostRoutes OBJECT-TYPE
		SYNTAX   INTEGER {
			disable(0),
			enable(1)
			}
         ACCESS   read-write
         STATUS   mandatory
         DESCRIPTION
            "Allow splitting of equal cost routes. IPX maintains multiple routes to 
             the same destination network.  When this field is enabled IPX will split
             traffic over the multiple routes.  This is also know as load balancing.
             Not currently supported by the code."
         ::= { usrIpx 2 }

	usrIpxProtocolPriority OBJECT-TYPE
         SYNTAX   INTEGER (1..3)
         ACCESS   read-write
         STATUS   mandatory
         DESCRIPTION
            	"The IPX priority relative to other protocols. Not currently supported
                by the code."
         ::= { usrIpx 3 }

	usrIpxMaxRegisteredPaths OBJECT-TYPE
         SYNTAX   INTEGER (1..255)
         ACCESS   read-write
         STATUS   mandatory
         DESCRIPTION
            	"The maximum number of routes to be maintained in the box. Not currently supported
                by the code."
         ::= { usrIpx 4 }

	usrIpxDefaultGateway OBJECT-TYPE
         SYNTAX   OCTET STRING (SIZE(10))
         ACCESS   read-write
         STATUS   mandatory
         DESCRIPTION
            	"The Default Gateway. The first leading bytes are IPX network number and the
                trailing 6 bytes of this string should contain ethernet address."
         --CONFIGURABLE
         ::= { usrIpx 5 }

     usrIpxRipTracingState OBJECT-TYPE
          SYNTAX      INTEGER {
                        disable(0),
                        enable(1)
                       }
          ACCESS      read-write
          STATUS      mandatory
          DESCRIPTION "The state of RIP Packet Tracing. When this is enabled 
                       each packet that the IPX RIP software receives is 
                       printed to the console. This object is only applicable
                       on specially compiled DEBUG software versions."
         --CONFIGURABLE
     ::= {usrIpx 6}

     usrIpxSapTracingState OBJECT-TYPE
          SYNTAX      INTEGER {
                        disable(0),
                        enable(1)
                       }
          ACCESS      read-write
          STATUS      mandatory
          DESCRIPTION "The state of SAP Packet Tracing. When this is enabled
                       each packet that the IPX SAP software receives is
                       printed to the console. This object is only applicable
                       on specially compiled DEBUG software versions."
         --CONFIGURABLE
     ::= {usrIpx 7}


-- IPX Static Route
--

	usrIpxStaticRouteTable OBJECT-TYPE
         SYNTAX  SEQUENCE OF USRIPXStaticRouteEntry 
         ACCESS  not-accessible
         STATUS  mandatory
         DESCRIPTION
            ""
	::= { usrIpx 8 }

     usrIpxStaticRouteEntry OBJECT-TYPE
        SYNTAX      USRIPXStaticRouteEntry
        ACCESS      not-accessible
        STATUS      mandatory
        DESCRIPTION "Each entry corresponds to one static route."
        INDEX   {
                usrIpxStaticRouteSysInstance,
                usrIpxStaticRouteCircIndex,
                usrIpxStaticRouteNetNum
               }
     ::= {usrIpxStaticRouteTable 1}

     USRIPXStaticRouteEntry ::= 
          SEQUENCE {
               usrIpxStaticRouteSysInstance
                    INTEGER,
               usrIpxStaticRouteCircIndex
                    INTEGER,
               usrIpxStaticRouteNetNum
                    NetNumber,
               usrIpxStaticRouteExistState
                    INTEGER,
               usrIpxStaticRouteTicks
                    INTEGER,
               usrIpxStaticRouteHopCount
                    INTEGER,
               usrIpxStaticRouteNextHopNICAddress
                    PhysAddress,
               usrIpxStaticRouteNextHopNetNum
                    NetNumber
               }

     usrIpxStaticRouteSysInstance OBJECT-TYPE
          SYNTAX      INTEGER
          ACCESS      read-write
          STATUS      mandatory
          DESCRIPTION "The unique identifier of the instance of IPX to
                      which this row corresponds."
     ::= {usrIpxStaticRouteEntry 1}

     usrIpxStaticRouteCircIndex OBJECT-TYPE
          SYNTAX      INTEGER
          ACCESS      read-write
          STATUS      mandatory
          DESCRIPTION "The unique identifier of the circuit used to
                      reach the first hop in the static route."
     ::= {usrIpxStaticRouteEntry 2}

     usrIpxStaticRouteNetNum OBJECT-TYPE
          SYNTAX      NetNumber
          ACCESS      read-write
          STATUS      mandatory
          DESCRIPTION "The IPX network number of the route's destination."
          --CONFIGURABLE
     ::= {usrIpxStaticRouteEntry 3}

     usrIpxStaticRouteExistState OBJECT-TYPE
          SYNTAX      INTEGER {
                        off(1),
                        on(2)
                       }
          ACCESS      read-write
          STATUS      mandatory
          DESCRIPTION "The validity of this static route.  Entries with the
                       value set to off may be deleted from the table at the
                       implementation's discretion."
     ::= {usrIpxStaticRouteEntry 4}

     usrIpxStaticRouteTicks OBJECT-TYPE
          SYNTAX      INTEGER
          ACCESS      read-write
          STATUS      mandatory
          DESCRIPTION "The delay, in ticks, to reach the route's destination."
          --CONFIGURABLE
     ::= {usrIpxStaticRouteEntry 5}

     usrIpxStaticRouteHopCount OBJECT-TYPE
          SYNTAX      INTEGER
          ACCESS      read-write
          STATUS      mandatory
          DESCRIPTION "The number of router hops necessary to reach the destination."
          --CONFIGURABLE
     ::= {usrIpxStaticRouteEntry 6}

     usrIpxStaticRouteNextHopNICAddress OBJECT-TYPE
          SYNTAX      PhysAddress
          ACCESS      read-write
          STATUS      mandatory
          DESCRIPTION "The NIC address of the next router in the routing path to the destination."
          --CONFIGURABLE
     ::= {usrIpxStaticRouteEntry 7}

     usrIpxStaticRouteNextHopNetNum OBJECT-TYPE
          SYNTAX      NetNumber
          ACCESS      read-write
          STATUS      mandatory
          DESCRIPTION "The Next Hop Network Number of the router in the routing path to the destination."
          --CONFIGURABLE
     ::= {usrIpxStaticRouteEntry 8}



-- Static Services Table
--   This table contains information for all services reached via a
--   static route.

	usrIpxStaticServTable OBJECT-TYPE
   		SYNTAX      SEQUENCE OF USRIPXStaticServEntry
   		ACCESS      not-accessible
   		STATUS      mandatory
   		DESCRIPTION "The Static Services table contains information about
                     all services reached via statically configured routes."
   	::= {usrIpx 9}

	usrIpxStaticServEntry OBJECT-TYPE
   		SYNTAX      USRIPXStaticServEntry
   		ACCESS      not-accessible
   		STATUS      mandatory
   		DESCRIPTION "Each entry corresponds to one service."
   		INDEX       {
               	     usrIpxStaticServSysInstance,
                		usrIpxStaticServCircIndex,
                		usrIpxStaticServName,
                		usrIpxStaticServType
               	   }
   	::= {usrIpxStaticServTable 1}

	USRIPXStaticServEntry ::= 
     		SEQUENCE {
                           usrIpxStaticServSysInstance
                              INTEGER,
                           usrIpxStaticServCircIndex
                              INTEGER,
                           usrIpxStaticServName
                              OCTET STRING,
                           usrIpxStaticServType
                              OCTET STRING,
                           usrIpxStaticServExistState
                              INTEGER,
                           usrIpxStaticServNetNum
                              NetNumber,
                           usrIpxStaticServNode
                              OCTET STRING,
                           usrIpxStaticServSocket
                              OCTET STRING,
                           usrIpxStaticServHopCount
                              INTEGER,
                           usrIpxStaticServNextHopNICAddress
                              PhysAddress,
                           usrIpxStaticServNextHopNetNum
                              NetNumber
                          }

	usrIpxStaticServSysInstance OBJECT-TYPE
   		SYNTAX      INTEGER
   		ACCESS      read-write
   		STATUS      mandatory
   		DESCRIPTION "The unique identifier of the instance of IPX to which
          		   this entry corresponds."
	::= {usrIpxStaticServEntry 1}

	usrIpxStaticServCircIndex OBJECT-TYPE
   		SYNTAX      INTEGER
   		ACCESS      read-write
   		STATUS      mandatory
   		DESCRIPTION "The circuit used to reach this service."
   	::= {usrIpxStaticServEntry 2}

	usrIpxStaticServName OBJECT-TYPE
   		SYNTAX      OCTET STRING (SIZE(1..48))
   		ACCESS      read-write
   		STATUS      mandatory
   		DESCRIPTION "The service name."
          --CONFIGURABLE
   	::= {usrIpxStaticServEntry 3}

	usrIpxStaticServType OBJECT-TYPE
   		SYNTAX      OCTET STRING (SIZE(2))
   		ACCESS      read-write
   		STATUS      mandatory
   		DESCRIPTION "The service type."
          --CONFIGURABLE
   	::= {usrIpxStaticServEntry 4}

	usrIpxStaticServExistState OBJECT-TYPE
   		SYNTAX      INTEGER {
          	              off(1),
               	         on(2)
                    	   }
   		ACCESS      read-write
   		STATUS      mandatory
   		DESCRIPTION "The validity of this static service.  Entries with the
          		   value set to off may be deleted from the table at the
                       implementation's discretion."
   	::= {usrIpxStaticServEntry 5}

	usrIpxStaticServNetNum OBJECT-TYPE
   		SYNTAX      NetNumber
   		ACCESS      read-write
   		STATUS      mandatory
   		DESCRIPTION "The IPX network number portion of the IPX address of the
                       service."
          --CONFIGURABLE
   	::= {usrIpxStaticServEntry 6}

	usrIpxStaticServNode OBJECT-TYPE
   		SYNTAX      OCTET STRING (SIZE(6))
   		ACCESS      read-write
   		STATUS      mandatory
   		DESCRIPTION "The node portion of the IPX address of the service."
          --CONFIGURABLE
   	::= {usrIpxStaticServEntry 7}

	usrIpxStaticServSocket OBJECT-TYPE
   		SYNTAX      OCTET STRING (SIZE(2))
   		ACCESS      read-write
   		STATUS      mandatory
   		DESCRIPTION "The socket portion of the IPX address of the service."
          --CONFIGURABLE
   	::= {usrIpxStaticServEntry 8}

	usrIpxStaticServHopCount OBJECT-TYPE
   		SYNTAX      INTEGER
   		ACCESS      read-write
   		STATUS      mandatory
   		DESCRIPTION "The number of router hops to the server on which the service resides."
          --CONFIGURABLE
   	::= {usrIpxStaticServEntry 9}

	usrIpxStaticServNextHopNICAddress OBJECT-TYPE
   		SYNTAX      PhysAddress
   		ACCESS      read-write
   		STATUS      mandatory
   		DESCRIPTION "The NIC address of next router in the path to the 
                       server on which the service resides."
          --CONFIGURABLE
   	::= {usrIpxStaticServEntry 10}

	usrIpxStaticServNextHopNetNum OBJECT-TYPE
   		SYNTAX      NetNumber
   		ACCESS      read-write
   		STATUS      mandatory
   		DESCRIPTION "The network number of the next router in path to the 
                       server on which the service resides."
          --CONFIGURABLE
   	::= {usrIpxStaticServEntry 11}





-- Portal MIB Variables
--

	usrIpxPortalTable OBJECT-TYPE
         SYNTAX  SEQUENCE OF USRIpxPortalEntry 
         ACCESS  not-accessible
         STATUS  mandatory
         DESCRIPTION
            ""
	::= { usrIpx 10 }


     usrIpxPortalEntry OBJECT-TYPE
        SYNTAX      USRIpxPortalEntry
        ACCESS      not-accessible
        STATUS      mandatory
        DESCRIPTION "Each entry corresponds to one static route."
        INDEX   {
                usrIpxPortalSysInstance,
                usrIpxPortalPortNumber
               }
     ::= {usrIpxPortalTable 1}

     USRIpxPortalEntry ::= 
          SEQUENCE {
               usrIpxPortalSysInstance
                    INTEGER,
               usrIpxPortalPortNumber
                    INTEGER,
               usrIpxPortalNetBiosState
                    INTEGER,
               usrIpxPortalNetworkDelay
                    INTEGER,
               usrIpxPortalMaxNumberRipEntries
                    INTEGER,
               usrIpxPortalMaxNumberSapEntries
                    INTEGER,
               usrIpxPortalRipBroadcastState
                    INTEGER,
               usrIpxPortalSapBroadcastState
                    INTEGER,
               usrIpxPortalRipPeriodicState
                    INTEGER,
               usrIpxPortalSapPeriodicState
                    INTEGER,
               usrIpxPortalNetBiosNameCachingState
                    INTEGER,
               usrIpxPortalNetBiosHops
                    INTEGER,
               usrIpxPortalDiagnosticState
                    INTEGER,
               usrIpxPortalNetBiosNameCachingTimer
                    INTEGER,
               usrIpxPortalMaxLearningRetries
                    INTEGER,
			   usrIpxPortalIpxwanState
                    INTEGER,
               usrIpxPortalLargeHopCount
                    Counter32,
               usrIpxPortalNetbsLargeHopCount
                    Counter32,
               usrIpxPortalNoNetRipPkt
                    Counter32,
               usrIpxPortalPathNotFoundToRoute
                    Counter32,
               usrIpxPortalNumberOfAgedRoutes
                    Counter32,
               usrIpxPortalWrongNetRipPkt
                    Counter32,
               usrIpxPortalNumberOfAgedSaps
                    Counter32,
               usrIpxPortalNumberOfWDogReqRcvd
                    Counter32,
               usrIpxPortalNumberOfWDogRspSent
                    Counter32,
               usrIpxPortalNumberOfSerialPktsRcvd
                    Counter32,
               usrIpxPortalNumberOfEchoReqRcvd
                    Counter32,
               usrIpxPortalNumberOfEchoRspSent
                    Counter32,
               usrIpxPortalNumberOfPktsTooLargeRcvd
                    Counter32,
			   usrIpxPortalRipReceiveState
					INTEGER,
			   usrIpxPortalSapReceiveState
					INTEGER
               }


     usrIpxPortalSysInstance OBJECT-TYPE
          SYNTAX      INTEGER
          ACCESS      read-write
          STATUS      mandatory
          DESCRIPTION "The unique identifier of the instance of IPX to
                      which this row corresponds."
     ::= {usrIpxPortalEntry 1}

     usrIpxPortalPortNumber OBJECT-TYPE
          SYNTAX      INTEGER
          ACCESS      read-write
          STATUS      mandatory
          DESCRIPTION "The unique identifier for this IPX portal."
     ::= {usrIpxPortalEntry 2}

     usrIpxPortalNetBiosState OBJECT-TYPE
          SYNTAX      INTEGER {
                        disable(0),
                        enable(1)
                       }
          ACCESS      read-write
          STATUS      mandatory
          DESCRIPTION "The state of NetBios Processing. When enabled the router maintains a
                       NetBios name table."
     ::= {usrIpxPortalEntry 3}

     usrIpxPortalNetworkDelay OBJECT-TYPE
          SYNTAX      INTEGER
          ACCESS      read-write
          STATUS      mandatory
          DESCRIPTION "The delay, in ticks, for this portal interface."
     ::= {usrIpxPortalEntry 4}

     usrIpxPortalMaxNumberRipEntries OBJECT-TYPE
          SYNTAX      INTEGER
          ACCESS      read-write
          STATUS      mandatory
          DESCRIPTION "The maximum number of entries within a RIP packet."
     ::= {usrIpxPortalEntry 5}

     usrIpxPortalMaxNumberSapEntries OBJECT-TYPE
          SYNTAX      INTEGER
          ACCESS      read-write
          STATUS      mandatory
          DESCRIPTION "The maximum number of entries within a SAP packet."
     ::= {usrIpxPortalEntry 6}

     usrIpxPortalRipBroadcastState OBJECT-TYPE
          SYNTAX      INTEGER {
                        disable(0),
                        enable(1)
                       }
          ACCESS      read-write 
          STATUS      mandatory
          DESCRIPTION "RIP broadcast packet state. When enabled IPX RIP will be enabled
                       to send out RIP request packets transmitted over this portal. 
                       To totally disable RIP traffic usrIpxPortalRipPeriodicState
                       must also be set to disable."
     ::= {usrIpxPortalEntry 7}

     usrIpxPortalSapBroadcastState OBJECT-TYPE
          SYNTAX      INTEGER {
                        disable(0),
                        enable(1)
                       }
          ACCESS      read-write
          STATUS      mandatory
          DESCRIPTION "SAP broadcast packet state. When enabled IPX SAP will be enabled
                       to send out SAP request packets transmitted over this portal. 
                       To totally disable SAP traffic usrIpxPortalSapPeriodicState
                       must also be set to disable."
     ::= {usrIpxPortalEntry 8}

     usrIpxPortalRipPeriodicState OBJECT-TYPE
          SYNTAX      INTEGER {
                        disable(0),
                        enable(1)
                       }
          ACCESS      read-write
          STATUS      mandatory
          DESCRIPTION "RIP periodic state."
     ::= {usrIpxPortalEntry 9}

     usrIpxPortalSapPeriodicState OBJECT-TYPE
          SYNTAX      INTEGER {
                        disable(0),
                        enable(1)
                       }
          ACCESS      read-write
          STATUS      mandatory
          DESCRIPTION "Controls sending periodic SAP broadcasts over this portal."
     ::= {usrIpxPortalEntry 10}

     usrIpxPortalNetBiosNameCachingState OBJECT-TYPE
          SYNTAX      INTEGER {
                        disable(0),
                        enable(1)
                       }
          ACCESS      read-write
          STATUS      mandatory
          DESCRIPTION "NetBios name caching state. When enabled IPX will maintain a table
                       of NetBios names"
     ::= {usrIpxPortalEntry 11}

     usrIpxPortalNetBiosHops OBJECT-TYPE
          SYNTAX      INTEGER (0..65535)
          ACCESS      read-write
          STATUS      mandatory
          DESCRIPTION "NetBios maximum number of hops."
     ::= {usrIpxPortalEntry 12}

     usrIpxPortalDiagnosticState OBJECT-TYPE
          SYNTAX      INTEGER {
                        disable(0),
                        enable(1)
                       }
          ACCESS      read-write
          STATUS      mandatory
          DESCRIPTION "Diagnostic state."
     ::= {usrIpxPortalEntry 13}

     usrIpxPortalNetBiosNameCachingTimer OBJECT-TYPE
          SYNTAX      INTEGER
          ACCESS      read-write
          STATUS      mandatory
          DESCRIPTION "NetBios name caching timer."
     ::= {usrIpxPortalEntry 14}

     usrIpxPortalMaxLearningRetries OBJECT-TYPE
          SYNTAX      INTEGER
          ACCESS      read-write
          STATUS      mandatory
          DESCRIPTION "Maximum number of learning retries."
     ::= {usrIpxPortalEntry 15}

	 usrIpxPortalIpxwanState OBJECT-TYPE
          SYNTAX      INTEGER {
                        disable(0),
                        enable(1)
                       }
          ACCESS      read-write
          STATUS      mandatory
          DESCRIPTION "Ipxwan State."
         --CONFIGURABLE
     ::= {usrIpxPortalEntry 16}
     usrIpxPortalLargeHopCount OBJECT-TYPE
          SYNTAX      Counter32
          ACCESS      read-only
          STATUS      mandatory
          DESCRIPTION "Displays number of IPX pkts with Large hop count."
         --CONFIGURABLE
     ::= {usrIpxPortalEntry 17}
     usrIpxPortalNetbsLargeHopCount OBJECT-TYPE
          SYNTAX      Counter32
          ACCESS      read-only
          STATUS      mandatory
          DESCRIPTION "Displays number of Netbios pkts with Large hop count."
         --CONFIGURABLE
     ::= {usrIpxPortalEntry 18}
     usrIpxPortalNoNetRipPkt OBJECT-TYPE
          SYNTAX      Counter32
          ACCESS      read-only
          STATUS      mandatory
          DESCRIPTION "Displays number of Netbios pkts with Large hop count."
         --CONFIGURABLE
     ::= {usrIpxPortalEntry 19}

	 usrIpxPortalPathNotFoundToRoute OBJECT-TYPE
          SYNTAX      Counter32
          ACCESS      read-only
          STATUS      mandatory
          DESCRIPTION "Displays number of Netbios pkts with Large hop count."
         --CONFIGURABLE
     ::= {usrIpxPortalEntry 20}
     usrIpxPortalNumberOfAgedRoutes OBJECT-TYPE
          SYNTAX      Counter32
          ACCESS      read-only
          STATUS      mandatory
          DESCRIPTION "Displays number of routes that r aged in routing table"
         --CONFIGURABLE
     ::= {usrIpxPortalEntry 21}
     usrIpxPortalWrongNetRipPkt OBJECT-TYPE
          SYNTAX      Counter32
          ACCESS      read-only
          STATUS      mandatory
          DESCRIPTION "Displays number of routes that r aged in routing table"
         --CONFIGURABLE
     ::= {usrIpxPortalEntry 22}
     usrIpxPortalNumberOfAgedSaps OBJECT-TYPE
          SYNTAX      Counter32
          ACCESS      read-only
          STATUS      mandatory
          DESCRIPTION "Displays number of routes that r aged in routing table"
         --CONFIGURABLE
     ::= {usrIpxPortalEntry 23}
     usrIpxPortalNumberOfWDogReqRcvd OBJECT-TYPE
          SYNTAX      Counter32
          ACCESS      read-only
          STATUS      mandatory
          DESCRIPTION "Displays number of routes that r aged in routing table"
         --CONFIGURABLE
     ::= {usrIpxPortalEntry 24}
	 usrIpxPortalNumberOfWDogRspSent OBJECT-TYPE
          SYNTAX      Counter32
          ACCESS      read-only
          STATUS      mandatory
          DESCRIPTION "Displays number of routes that r aged in routing table"
         --CONFIGURABLE
     ::= {usrIpxPortalEntry 25}
     usrIpxPortalNumberOfSerialPktsRcvd OBJECT-TYPE
          SYNTAX      Counter32
          ACCESS      read-only
          STATUS      mandatory
          DESCRIPTION "Displays number of routes that r aged in routing table"
         --CONFIGURABLE
     ::= {usrIpxPortalEntry 26}
     usrIpxPortalNumberOfEchoReqRcvd OBJECT-TYPE
          SYNTAX      Counter32
          ACCESS      read-only
          STATUS      mandatory
          DESCRIPTION "Displays number of routes that r aged in routing table"
         --CONFIGURABLE
     ::= {usrIpxPortalEntry 27}
     usrIpxPortalNumberOfEchoRspSent OBJECT-TYPE
          SYNTAX      Counter32
          ACCESS      read-only
          STATUS      mandatory
          DESCRIPTION "Displays number of routes that r aged in routing table"
         --CONFIGURABLE
     ::= {usrIpxPortalEntry 29}
     usrIpxPortalNumberOfPktsTooLargeRcvd OBJECT-TYPE
          SYNTAX      Counter32
          ACCESS      read-only
          STATUS      mandatory
          DESCRIPTION "Displays number of routes that r aged in routing table"
         --CONFIGURABLE
     ::= {usrIpxPortalEntry 30}
	 usrIpxPortalRipReceiveState OBJECT-TYPE
          SYNTAX      INTEGER {
                        disable(0),
                        enable(1)
                       }
          ACCESS      read-write
          STATUS      mandatory
          DESCRIPTION "RIP receive packet state. When enabled IPX RIP will be enabled
                       to receive RIP packets over this portal.
                       To totally disable RIP traffic usrIpxPortalRipPeriodicState
                       must also be set to disable."
		--CONFIGURABLE
     ::= {usrIpxPortalEntry 31}
	 usrIpxPortalSapReceiveState OBJECT-TYPE
          SYNTAX      INTEGER {
                        disable(0),
                        enable(1)
                       }
          ACCESS      read-write
          STATUS      mandatory
          DESCRIPTION "SAP receive packet state. When enabled IPX SAP will be enabled
                       to receive SAP packets over this portal.
                       To totally disable SAP traffic usrIpxPortalSapPeriodicState
                       must also be set to disable."
         --CONFIGURABLE
     ::= {usrIpxPortalEntry 32}
 
     
     usrIpxDynamicNetworkRangeStart OBJECT-TYPE
         SYNTAX   NetNumber
         ACCESS   read-write
         STATUS   mandatory
         DESCRIPTION
            	"This is the first number in a range of network numbers IPX 
                uses to dynamically assign to dial-in users.  The end of 
                the range is determined by the object usrIpxMaxDynamicNetworkNumbers"
         --CONFIGURABLE
     ::= { usrIpx 11 }

     usrIpxMaxDynamicNetworkNumbers OBJECT-TYPE
          SYNTAX      INTEGER
          ACCESS      read-write
          STATUS      mandatory
          DESCRIPTION "Maximum number of network addresses available to allocate to
                       dial-in users."
         --CONFIGURABLE
     ::= { usrIpx 12 }


     usrIpxSaveConfigFlag OBJECT-TYPE
          SYNTAX      UsrConfigStatus
          ACCESS      read-write
          STATUS      mandatory
          DESCRIPTION "Setting the value of this object to `save' causes the values
		 of the IPX configuration to be written out to the current IPX
		 config file, which is stored in the ipxConfigFile object. While
		 the new ConfigFile is being written, the IPX process
		 will set the value of this flag set to `saving''. Any
		 attempts to set the value while it is  not `normal'
		 (i.e. the file is currently being written to the
		 ConfigFile) will result in a badValue error being
		 returned. Setting the value to `normal' will result in no
		 action."
     ::= { usrIpx 13 }

	usrIpxConfigFileName OBJECT-TYPE
		SYNTAX      DisplayString
		ACCESS      read-only
		STATUS      mandatory
		DESCRIPTION		
		  "The name of a ConfigFile to read/write permanent database records.
		   If the value of this object is an empty string, then the
		   IPX process uses the default name `@file://IpxProcess.cfg'. "
	::= { usrIpx 14 }

     usrIpxState OBJECT-TYPE
          SYNTAX      UsrIpxStates 
          ACCESS      read-only
          STATUS      mandatory
          DESCRIPTION "Ipx state."
     ::= { usrIpx 15 }

     usrIpxEnable OBJECT-TYPE
          SYNTAX      INTEGER {
                        disable(0),
                        enable(1)
                       }
          ACCESS      read-write
          STATUS      mandatory
          DESCRIPTION "To enable or disable IPX.  When Disable is set the RIP process
                       will send out shutdown messages on all its ports in order
                       to inform neighboring routers that our routes are no longer
                       valid."
         --CONFIGURABLE
     ::= { usrIpx 16 }


-- USR Service Table
--   This table contains information for all services acquired via a
--   static sap or learned sap using a reduced set of indices which is common
--   to both Static and Non-Static SAPs. This is possible in the USR application
--   as a Static SAP entry that is added to the Static table does in the add process 
--   fill out the Non-Static field members that are contained in the same entry
--   structure. 
--   For the USR application, one entry structure is used for both Static and Non-Static 
--   and the instance index for both entries, although contained in different field 
--   members is always hard-wired to '1', and the Circuit index for Static entries is 
--   always hardwired to '0'.
--   Notes: (1.) This table was added to provide delete capability for learned saps
--          which requires write access. Write access is not available for
--          the IPX Service Table contained in the novell ipx mib.
--          In addition it also provides the mechanism to delete learned or
--          or statically entered saps.
--          (2.) The USR implementation of rows for both Static and Non-Static 
--          primary entries is a doubly linked list which has both entry types linked 
--          into one list. This one list is anchored at a common point which the mib 
--          entry for each of the two types refer to as starting point for accessing
--          that type's specific row instance. The whole list is actually scanned
--          for matching indices. This is conceptually different implementation
--          than what one might expect from a strictly SNMP mib row implementation,
--          where a binary tree structure might be expected with a node in the tree
--          representing an instance and providing branching to other nodes for
--          multiple instances. The USR application's implementation for mib rows is
--          is a non-sorted (all new Static and Non-Static SAP entries are always
--          added to the end of the list) linked list.
--          (3.) The intention for this table is only to provide a mapping overlay
--          of the Static and Non-Static row entries in order to provide a means
--          for deleting learned SAP entries as well as statically entered SAP entries.

	usrIpxServTable OBJECT-TYPE
   		SYNTAX      SEQUENCE OF USRIpxServEntry
   		ACCESS      not-accessible
   		STATUS      mandatory
   		DESCRIPTION "The Services table contains information about
                     all services reached via statically entered saps
	                or learned saps."
   	::= {usrIpx 17}

	usrIpxServEntry OBJECT-TYPE
   		SYNTAX      USRIpxServEntry
   		ACCESS      not-accessible
   		STATUS      mandatory
   		DESCRIPTION "Each entry corresponds to one service."
   		INDEX       {
                		usrIpxServName,
                		usrIpxServType
               	   }
   	::= {usrIpxServTable 1}

	USRIpxServEntry ::= 
     		SEQUENCE {
                           usrIpxServName
                              OCTET STRING,
                           usrIpxServType
                              OCTET STRING,
                           usrIpxServExistState
                              INTEGER,
                           usrIpxServProtocol
                              INTEGER,
                           usrIpxServNetNum
                              NetNumber,
                           usrIpxServNode
                              OCTET STRING,
                           usrIpxServSocket
                              OCTET STRING,
                           usrIpxServHopCount
                              INTEGER
                          }

	usrIpxServName OBJECT-TYPE
   		SYNTAX      OCTET STRING (SIZE(1..48))
   		ACCESS      read-write
   		STATUS      mandatory
   		DESCRIPTION "The service name."
          --CONFIGURABLE
   	::= {usrIpxServEntry 1}

	usrIpxServType OBJECT-TYPE
   		SYNTAX      OCTET STRING (SIZE(2))
   		ACCESS      read-write
   		STATUS      mandatory
   		DESCRIPTION "The service type."
          --CONFIGURABLE
   	::= {usrIpxServEntry 2}

	usrIpxServExistState OBJECT-TYPE
   		SYNTAX      INTEGER {
          	              off(1),
               	         on(2)
                    	   }
   		ACCESS      read-write
   		STATUS      mandatory
   		DESCRIPTION "The validity of this service.  Entries with the
          		   value set to off may be deleted from the table at the
                       implementation's discretion."
   	::= {usrIpxServEntry 3}

	usrIpxServProtocol OBJECT-TYPE
   		SYNTAX      INTEGER {
                        other(1),
                        local(2),
                        nlsp(4),
                        static(5),
                        sap(6)
                       }
   		ACCESS      read-write
   		STATUS      mandatory
   		DESCRIPTION "The protocol from which knowledge of this service was
          	        obtained."
   ::= {usrIpxServEntry 4}

	usrIpxServNetNum OBJECT-TYPE
   		SYNTAX      NetNumber
   		ACCESS      read-write
   		STATUS      mandatory
   		DESCRIPTION "The IPX network number portion of the IPX address of the
                       service."
          --CONFIGURABLE
   	::= {usrIpxServEntry 5}

	usrIpxServNode OBJECT-TYPE
   		SYNTAX      OCTET STRING (SIZE(6))
   		ACCESS      read-write
   		STATUS      mandatory
   		DESCRIPTION "The node portion of the IPX address of the service."
          --CONFIGURABLE
   	::= {usrIpxServEntry 6}

	usrIpxServSocket OBJECT-TYPE
   		SYNTAX      OCTET STRING (SIZE(2))
   		ACCESS      read-write
   		STATUS      mandatory
   		DESCRIPTION "The socket portion of the IPX address of the service."
          --CONFIGURABLE
   	::= {usrIpxServEntry 7}

	usrIpxServHopCount OBJECT-TYPE
   		SYNTAX      INTEGER
   		ACCESS      read-write
   		STATUS      mandatory
   		DESCRIPTION "The number of router hops to the server on which the 
                       service resides."
          --CONFIGURABLE
   	::= {usrIpxServEntry 8}

usrIpxDelServiceAll OBJECT-TYPE
    SYNTAX  INTEGER {
            nonStatic(0)
         }
    ACCESS  read-write
    STATUS  mandatory
    DESCRIPTION "This object is used to clear the whole SAP table.
		       Current support is only for clearing all non-static
                 SAP entries."
   ::= { usrIpx 18 }
 

-- Destination Table - this table almost duplicate a destination table
-- from standard novell_ipx.mib with an exception of a new field:
-- usrIpxDestExistState
--
--   The Destination table contains information about all known
--   destinations.  The routing information shown in this table represents
--   the path currently being used to reach the destination.

usrIpxDestTable OBJECT-TYPE
   SYNTAX      SEQUENCE OF USRIPXDestEntry
   ACCESS      not-accessible
   STATUS      mandatory
   DESCRIPTION "The Destination table contains information about all
                known destinations."
   ::= {usrIpx 19}

usrIpxDestEntry OBJECT-TYPE
   SYNTAX      USRIPXDestEntry
   ACCESS      not-accessible
   STATUS      mandatory
   DESCRIPTION "Each entry corresponds to one destination."
   INDEX       {
                usrIpxDestSysInstance,
                usrIpxDestNetNum
               }
   ::= {usrIpxDestTable 1}

USRIPXDestEntry ::= SEQUENCE {
                     usrIpxDestSysInstance
                        INTEGER,
                     usrIpxDestNetNum
                        NetNumber,
                     usrIpxDestProtocol
                        INTEGER,
                     usrIpxDestTicks
                        INTEGER,
                     usrIpxDestHopCount
                        INTEGER,
                     usrIpxDestNextHopCircIndex
                        INTEGER,
                     usrIpxDestNextHopNICAddress
                        PhysAddress,
                     usrIpxDestNextHopNetNum
                        NetNumber,
                     usrIpxDestExistState
                        INTEGER
                    }

usrIpxDestSysInstance OBJECT-TYPE
   SYNTAX      INTEGER
   ACCESS      read-only
   STATUS      mandatory
   DESCRIPTION "The unique identifier of the instance of IPX
                to which this row corresponds."
   ::= {usrIpxDestEntry 1}

usrIpxDestNetNum OBJECT-TYPE
   SYNTAX      NetNumber
   ACCESS      read-only
   STATUS      mandatory
   DESCRIPTION "The IPX network number of the destination."
   ::= {usrIpxDestEntry 2}

usrIpxDestProtocol OBJECT-TYPE
   SYNTAX      INTEGER {
                        other(1),
                        local(2),
                        rip(3),
                        nlsp(4),
                        static(5)
                       }
   ACCESS      read-only
   STATUS      mandatory
   DESCRIPTION "The routing protocol from which knowledge of this
                destination was obtained."
   ::= {usrIpxDestEntry 3}

usrIpxDestTicks OBJECT-TYPE
   SYNTAX      INTEGER
   ACCESS      read-only
   STATUS      mandatory
   DESCRIPTION "The delay in ticks to reach this destination."
   ::= {usrIpxDestEntry 4}

usrIpxDestHopCount OBJECT-TYPE
   SYNTAX      INTEGER
   ACCESS      read-only
   STATUS      mandatory
   DESCRIPTION "The number of hops necessary to reach the destination."
   ::= {usrIpxDestEntry 5}

usrIpxDestNextHopCircIndex OBJECT-TYPE
   SYNTAX      INTEGER
   ACCESS      read-only
   STATUS      mandatory
   DESCRIPTION "The unique identifier of the circuit used to reach the 
                next hop."
   ::= {usrIpxDestEntry 6}

usrIpxDestNextHopNICAddress OBJECT-TYPE
   SYNTAX      PhysAddress
   ACCESS      read-only
   STATUS      mandatory
   DESCRIPTION "The NIC address of the next hop."
   ::= {usrIpxDestEntry 7}

usrIpxDestNextHopNetNum OBJECT-TYPE
   SYNTAX      NetNumber
   ACCESS      read-only
   STATUS      mandatory
   DESCRIPTION "The IPX network number of the next hop."
   ::= {usrIpxDestEntry 8}

usrIpxDestExistState OBJECT-TYPE
   SYNTAX      INTEGER {
                      off(1),
                      on(2)
                       }
   ACCESS      read-write
   STATUS      mandatory
   DESCRIPTION "The validity of the route to this destination.  
                Valid row entry has this field set to on. 
                Learned routes with the value set to off will
                be removed from the routing table immediately, 
                static routes may be deleted from the table at the
                implementation's discretion."
   ::= {usrIpxDestEntry 9}

usrIpxDelRouteAll OBJECT-TYPE
   SYNTAX  INTEGER {
           disable(0),
           enable(1)
        }
   ACCESS  read-write
   STATUS  mandatory
   DESCRIPTION "This object is used to clear the hole routing table"
   ::= { usrIpx 20 }

	usrPPPIpxAddress OBJECT-TYPE
		SYNTAX   OCTET STRING (SIZE(4))
		ACCESS   read-write
		STATUS   mandatory 
		DESCRIPTION
				"The IPX ADDRESS assigned to all PPP user's if they are configured as such."
		--CONFIGURABLE
		::= { usrIpx 21 }

END         -- End IPX host MIB definitions
--
-- For the revision history to work correctly, after a new MIB file has been
-- added to the CVS repository the first time the CVS Admin person needs to
-- set the correct comment string delimiter for the file.
--
-- $Log: usr_ipx.mib,v $
-- Revision 1.14.8.4  1998/05/19 22:52:28  senthil
-- MR 6740: Re-arranged variables to maintain backwards compatibility with Pilgrim20
--
-- Revision 1.14.8.3  1998/03/18 14:35:26  dwartonick
-- Changes for Delete IPX Static or Non-Static Service and Delete All Non-Static
-- Services.
--
-- Revision 1.14.8.2  1998/03/13 00:05:31  olga
-- MR#5288 part 2: Add ability to clear out learned routes for IPX
--
-- Revision 1.14.8.1  1997/09/26 23:38:55  nkamrudd
-- Entered code for IPX UnNumbered Network
--
-- Revision 1.14  1996/09/18 21:44:46  jhalpin
-- Merge in LANLinker branch changes <sawdust city here I come..>
--
-- Revision 1.13  1996/08/28 19:04:04  hasmik
-- Fixed bug#1996082611435
--
-- Revision 1.12  1996/07/24 16:16:16  hasmik
-- Changed ConfigFileName access to read-only
--
-- Revision 1.11  1996/07/23 20:05:24  hasmik
-- Changed the DefaultGateway type from INTEGER to OCTET STRING of size 10
--
-- Revision 1.10.2.3  1996/08/28 19:05:39  hasmik
-- Fixed bug#19960826114355
--
-- Revision 1.10.2.2  1996/07/24 16:36:29  hasmik
-- Fixed bug#19960710145304
--
-- Revision 1.10.2.1  1996/07/23 23:18:27  hasmik
-- Fixed bug#1996072319354
--
-- Revision 1.10  1996/05/28 16:11:13  psd
-- Change objects to CONFIGURABLE.
--
-- Revision 1.9  1996/04/19 20:19:10  psd
-- Modified for one SAVE IPX command.
--
-- Revision 1.8  1996/04/16 23:33:55  ccb
-- updates following ppp testing
--
-- Revision 1.7  1996/04/16  19:38:23  psd
-- Fixed some typos in descriptions.
--
-- Revision 1.6  1996/03/29 12:20:17  psd
-- Added CFM save and load support.
--
-- Revision 1.5  1996/03/26 18:28:08  ccb
-- added CFM support
--
-- Revision 1.4  1996/02/16  22:03:55  jhalpin
-- fix disbale typo
--
-- Revision 1.3  1995/09/22 20:30:49  hasmik
-- Added usrIpxStaticServNextHopNetNum
--
-- Revision 1.2  1995/09/21 15:46:34  hasmik
-- Added usrIpxStaticRouteNextHopNetNum
--
-- Revision 1.1  1995/09/19 16:20:48  hasmik
-- Initial Version
--
-- Revision 1.1  1995/09/19 16:04:03  hasmik
-- Initial Version of IPX host mib
--
-- Revision 1.7  1995/08/31 14:29:01  jhalpin
-- Fixed up template.mib so that it actually compiles
--
-- Revision 1.6  1995/08/30 15:32:33  jhalpin
-- Add comment about revision history
--
-- Revision 1.5  1995/08/30 15:29:17  jhalpin
-- Fix case of Id and Log fields
--
--
--
--
-- Local Variables:
-- tab-width:5
-- tab-stop-list:( 5 10 15 20 25 30 35 40 45 50 55 60 65 70 75 80)
-- End:
--




















--
--	usr_ipx_cfg.mib
--
--
-- Author:         Peter Dobransky
--
-- $Id: usr_ipx_cfg.mib,v 1.3.8.1 1997/09/17 19:06:34 psd Exp $
--
--  | Copyright (c) 1996 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-IPX-CFG-MIB DEFINITIONS ::= BEGIN

	IMPORTS
          OBJECT-TYPE
                  FROM RFC-1212
          usrIpxCfg
                  FROM USR-DEFINITIONS-MIB;


   -- Begin managed object definitions here...

     usrIpxCfgNetworkTable OBJECT-TYPE
	     SYNTAX SEQUENCE OF UsrIpxCfgNetworkEntry
	     ACCESS not-accessible
	     STATUS mandatory
	     DESCRIPTION
		     "This table is the same as the usrIpxPortalTable,
		      with the exception that it is indexed by the Network Number
			 defined in the usrIpxStaticRouteTable. This table will be
                used only by the the Configuration File Manager process to
                load permament configuration file records for named networks
                at system boot time. Any attempt to set this table from
                either the CLI process or SNMP will fail."
     ::= { usrIpxCfg 1 }

     usrIpxCfgNetworkEntry OBJECT-TYPE
	     SYNTAX UsrIpxCfgNetworkEntry
	     ACCESS not-accessible
	     STATUS mandatory
	     DESCRIPTION
		     "A (conceptual) entry for one IPX Network."
	     INDEX { usrIpxCfgNetSysInstance,
                  usrIpxCfgNetNetNumber }
     ::= { usrIpxCfgNetworkTable 1 }

     UsrIpxCfgNetworkEntry ::= SEQUENCE {
               usrIpxCfgNetSysInstance
                    INTEGER,
               usrIpxCfgNetNetNumber
                    INTEGER,
               usrIpxCfgNetNetBiosState
                    INTEGER,
               usrIpxCfgNetNetworkDelay
                    INTEGER,
               usrIpxCfgNetRipBroadcastState
                    INTEGER,
               usrIpxCfgNetSapBroadcastState
                    INTEGER,
               usrIpxCfgNetRipPeriodicState
                    INTEGER,
               usrIpxCfgNetSapPeriodicState
                    INTEGER,
               usrIpxCfgNetNetBiosNameCachingState
                    INTEGER,
               usrIpxCfgNetNetBiosHops
                    INTEGER,
               usrIpxCfgNetDiagnosticState
                    INTEGER,
               usrIpxCfgNetNetBiosNameCachingTimer
                    INTEGER,
               usrIpxCfgNetMaxLearningRetries
                    INTEGER,
			usrIpxCfgNetRipCircState
				INTEGER,
			usrIpxCfgNetRipCircUpdate
				INTEGER,
			usrIpxCfgNetRipCircAgeMultiplier
				INTEGER,
			usrIpxCfgNetRipCircPacketSize
				INTEGER,
			usrIpxCfgNetSapCircState
				INTEGER,
			usrIpxCfgNetSapCircUpdate
				INTEGER,
			usrIpxCfgNetSapCircAgeMultiplier
				INTEGER,
			usrIpxCfgNetSapCircPacketSize
				INTEGER,
			usrIpxCfgNetSapCircGetNearestServerReply
				INTEGER,
			usrIpxCfgNetIpxCircExistState
				INTEGER,
			usrIpxCfgNetIpxCircOperState
				INTEGER,
			usrIpxCfgNetIpxCircType
				INTEGER,
			usrIpxCfgNetIpxCircLocalMaxPacketSize
				INTEGER
	}


     usrIpxCfgNetSysInstance OBJECT-TYPE
          SYNTAX      INTEGER
          ACCESS      not-accessible
          STATUS      mandatory
          DESCRIPTION 
               "The unique identifier of the instance of IPX to which this
               row corresponds."
     ::= {usrIpxCfgNetworkEntry 1}

     usrIpxCfgNetNetNumber OBJECT-TYPE
          SYNTAX      INTEGER
          ACCESS      not-accessible
          STATUS      mandatory
          DESCRIPTION
               "The unique identifier for this IPX network."
     ::= {usrIpxCfgNetworkEntry 2}

     usrIpxCfgNetNetBiosState OBJECT-TYPE
          SYNTAX      INTEGER {
                        disable(0),
                        enable(1)
                       }
          ACCESS      read-write
          STATUS      mandatory
          DESCRIPTION
               "The state of NetBios Processing. When enabled the router
               maintains a NetBios name table."
          --CONFIGURABLE
     ::= {usrIpxCfgNetworkEntry 3}

     usrIpxCfgNetNetworkDelay OBJECT-TYPE
          SYNTAX      INTEGER
          ACCESS      read-write
          STATUS      mandatory
          DESCRIPTION
               "The delay, in ticks, for this portal interface."
          --CONFIGURABLE
     ::= {usrIpxCfgNetworkEntry 4}

     usrIpxCfgNetRipBroadcastState OBJECT-TYPE
          SYNTAX      INTEGER {
                        disable(0),
                        enable(1)
                       }
          ACCESS      read-write 
          STATUS      mandatory
          DESCRIPTION
               "RIP broadcast packet state. When enabled IPX RIP will be
               enabled to send out RIP request packets transmitted over this
               portal. To totally disable RIP traffic
               usrIpxPortalRipPeriodicState must also be set to disable."
          --CONFIGURABLE
     ::= {usrIpxCfgNetworkEntry 5}

     usrIpxCfgNetSapBroadcastState OBJECT-TYPE
          SYNTAX      INTEGER {
                        disable(0),
                        enable(1)
                       }
          ACCESS      read-write
          STATUS      mandatory
          DESCRIPTION
               "SAP broadcast packet state. When enabled IPX SAP will be
               enabled to send out SAP request packets transmitted over this
               portal. To totally disable SAP traffic
               usrIpxPortalSapPeriodicState must also be set to disable."
          --CONFIGURABLE
     ::= {usrIpxCfgNetworkEntry 6}

     usrIpxCfgNetRipPeriodicState OBJECT-TYPE
          SYNTAX      INTEGER {
                        disable(0),
                        enable(1)
                       }
          ACCESS      read-write
          STATUS      mandatory
          DESCRIPTION
               "RIP periodic state."
          --CONFIGURABLE
     ::= {usrIpxCfgNetworkEntry 7}

     usrIpxCfgNetSapPeriodicState OBJECT-TYPE
          SYNTAX      INTEGER {
                        disable(0),
                        enable(1)
                       }
          ACCESS      read-write
          STATUS      mandatory
          DESCRIPTION
               "Controls sending periodic SAP broadcasts over this portal."
          --CONFIGURABLE
     ::= {usrIpxCfgNetworkEntry 8}

     usrIpxCfgNetNetBiosNameCachingState OBJECT-TYPE
          SYNTAX      INTEGER {
                        disable(0),
                        enable(1)
                       }
          ACCESS      read-write
          STATUS      mandatory
          DESCRIPTION
               "NetBios name caching state. When enabled IPX will maintain a
               table of NetBios names"
          --CONFIGURABLE
     ::= {usrIpxCfgNetworkEntry 9}

     usrIpxCfgNetNetBiosHops OBJECT-TYPE
          SYNTAX      INTEGER (0..65535)
          ACCESS      read-write
          STATUS      mandatory
          DESCRIPTION
               "NetBios maximum number of hops."
          --CONFIGURABLE
     ::= {usrIpxCfgNetworkEntry 10}

     usrIpxCfgNetDiagnosticState OBJECT-TYPE
          SYNTAX      INTEGER {
                        disable(0),
                        enable(1)
                       }
          ACCESS      read-write
          STATUS      mandatory
          DESCRIPTION
               "Diagnostic state."
          --CONFIGURABLE
     ::= {usrIpxCfgNetworkEntry 11}

     usrIpxCfgNetNetBiosNameCachingTimer OBJECT-TYPE
          SYNTAX      INTEGER
          ACCESS      read-write
          STATUS      mandatory
          DESCRIPTION
               "NetBios name caching timer."
          --CONFIGURABLE
     ::= {usrIpxCfgNetworkEntry 12}

     usrIpxCfgNetMaxLearningRetries OBJECT-TYPE
          SYNTAX      INTEGER
          ACCESS      read-write
          STATUS      mandatory
          DESCRIPTION
               "Maximum number of learning retries."
          --CONFIGURABLE
     ::= {usrIpxCfgNetworkEntry 13}

     usrIpxCfgNetRipCircState OBJECT-TYPE
   		SYNTAX      INTEGER {
                        off(1),
                        on(2),
                        auto-on(3),
                        auto-off(4)
                       }
   		ACCESS      read-write
   		STATUS      mandatory
   		DESCRIPTION "Indicates whether RIP information may be sent/received
          	       over this circuit."
   		DEFVAL      { auto-off }
		--CONFIGURABLE
     ::= {usrIpxCfgNetworkEntry 14}

     usrIpxCfgNetRipCircUpdate OBJECT-TYPE
   		SYNTAX      INTEGER
   		ACCESS      read-write
   		STATUS      mandatory
   		DESCRIPTION "The RIP periodic update interval, in seconds."
   		DEFVAL      { 60 }
		--CONFIGURABLE
     ::= {usrIpxCfgNetworkEntry 15}

	usrIpxCfgNetRipCircAgeMultiplier OBJECT-TYPE
		SYNTAX      INTEGER
		ACCESS      read-write
		STATUS      mandatory
		DESCRIPTION "The holding multiplier for information received in RIP
          	       periodic updates."
		DEFVAL      { 4 }
		--CONFIGURABLE
     ::= {usrIpxCfgNetworkEntry 16}

	usrIpxCfgNetRipCircPacketSize OBJECT-TYPE
   		SYNTAX      INTEGER
   		ACCESS      read-write
   		STATUS      mandatory
   		DESCRIPTION "The RIP packet size used on this circuit."
		--CONFIGURABLE
   	::= {usrIpxCfgNetworkEntry 17}

     usrIpxCfgNetSapCircState OBJECT-TYPE
		SYNTAX      INTEGER {
                        off(1),
                        on(2),
                        auto-on(3),
                        auto-off(4)
                       }
   		ACCESS      read-write
   		STATUS      mandatory
   		DESCRIPTION "Indicates whether SAP information may be sent/received
          	       over this circuit."
 		DEFVAL      { auto-off }
		--CONFIGURABLE
   	::= {usrIpxCfgNetworkEntry 18}

	usrIpxCfgNetSapCircUpdate OBJECT-TYPE
   		SYNTAX      INTEGER
   		ACCESS      read-write
   		STATUS      mandatory
   		DESCRIPTION "The SAP periodic update interval, in seconds."
   		DEFVAL      { 60 }
		--CONFIGURABLE
   	::= {usrIpxCfgNetworkEntry 19}

	usrIpxCfgNetSapCircAgeMultiplier OBJECT-TYPE
   		SYNTAX      INTEGER
   		ACCESS      read-write
   		STATUS      mandatory
   		DESCRIPTION "The holding multiplier for information received in SAP
	                 periodic updates."
   		DEFVAL      { 4 }
		--CONFIGURABLE
   	::= {usrIpxCfgNetworkEntry 20}

	usrIpxCfgNetSapCircPacketSize OBJECT-TYPE
   		SYNTAX      INTEGER
   		ACCESS      read-write
   		STATUS      mandatory
   		DESCRIPTION "The SAP packet size used on this circuit."
		--CONFIGURABLE
   	::= {usrIpxCfgNetworkEntry 21}

	usrIpxCfgNetSapCircGetNearestServerReply OBJECT-TYPE
   		SYNTAX      INTEGER {
                        no(1),
                        yes(2)
                       }
   		ACCESS      read-write
   		STATUS      mandatory
   		DESCRIPTION "Indicates whether to respond to SAP get nearest server
          	       requests received on this circuit."
   		DEFVAL      { yes }
		--CONFIGURABLE
   	::= {usrIpxCfgNetworkEntry 22}

	usrIpxCfgNetIpxCircExistState OBJECT-TYPE
   		SYNTAX      INTEGER {
                        off(1),
                        on(2)
                       }
   		ACCESS      read-write
   		STATUS      mandatory
   		DESCRIPTION "The validity of this circuit entry.  A circuit with this
          	       value set to off may be deleted from the table at the
                	  IPX implementation's discretion."
		--CONFIGURABLE
   	::= {usrIpxCfgNetworkEntry 23}

	usrIpxCfgNetIpxCircOperState OBJECT-TYPE
   		SYNTAX      INTEGER {
                        down(1),
                        up(2),
                        sleeping(3)
                       }
   		ACCESS      read-write
   		STATUS      mandatory
   		DESCRIPTION "The operational state of the circuit."
		--CONFIGURABLE
   	::= {usrIpxCfgNetworkEntry 24}

	usrIpxCfgNetIpxCircType OBJECT-TYPE
   		SYNTAX      INTEGER {
                        other(1),
                        broadcast(2),
                        ptToPt(3),
                        wanRIP(4),
                        unnumberedRIP(5),
                        dynamic(6),
                        wanWS(7)
                       }
   		ACCESS      read-write
   		STATUS      mandatory
   		DESCRIPTION "The type of the circuit."
		--CONFIGURABLE
   	::= {usrIpxCfgNetworkEntry 25}

	usrIpxCfgNetIpxCircLocalMaxPacketSize OBJECT-TYPE
   		SYNTAX      INTEGER
   		ACCESS      read-write
   		STATUS      mandatory
   		DESCRIPTION "The maximum size (including header), in bytes, that the
          	       system supports locally on this circuit."
		--CONFIGURABLE
   	::= {usrIpxCfgNetworkEntry 26}


END         -- End Template MIB definitions

--
--
-- $Log: usr_ipx_cfg.mib,v $
-- Revision 1.3.8.1  1997/09/17 19:06:34  psd
-- Merged 2.0 to 3.0
--
--Revision 1.3.14.1  1997/09/05  15:09:33  psd
--Changes to MIBs so that they compile using the SimpleTester.
--
--Revision 1.3  1996/09/18  21:44:48  jhalpin
--Merge in LANLinker branch changes <sawdust city here I come..>
--
-- Revision 1.2  1996/08/28 19:04:05  hasmik
-- Fixed bug#1996082611435
--
-- Revision 1.1.2.1  1996/08/28 19:05:40  hasmik
-- Fixed bug#19960826114355
--
-- Revision 1.1  1996/04/05 21:13:49  psd
-- Support for configuring IPX networks via the CFM.
--
--
--
--
-- Local Variables:
-- tab-width:5
-- tab-stop-list:( 5 10 15 20 25 30 35 40 45 50 55 60 65 70 75 80)
-- End:
--
--
--	usr_snmp.mib - The usr SNMP MIB module
--
--
-- Author:         Jim Halpin
--
-- $Id: usr_snmp.mib,v 1.8.10.4 1998/06/26 21:10:10 edjean Exp $
--
--  | Copyright (c) 1995 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-SNMP-MIB DEFINITIONS ::= BEGIN

	IMPORTS
		IpAddress
                  FROM RFC1155-SMI
          OBJECT-TYPE
                  FROM RFC-1212
          DisplayString, usrSnmp, UsrConfigStatus
                  FROM USR-DEFINITIONS-MIB;


   -- textual conventions
   -- 
   -- textual conventions are like pre-processor macro in 'C'
   --        (i.e. #define statements)
   -- Use them to define your own 'datatypes'

   -- memory size, expressed in units of 1024bytes


	-- A sample Table definiton.

	usrSnmpConfigFileName OBJECT-TYPE
		SYNTAX      DisplayString
		ACCESS      read-write
		STATUS      mandatory
		DESCRIPTION		
		  "The name of a ConfigFile to read/write permanent database records.
		   If the value of this object is an empty string, then the
		   SNMP process uses the default name `@file://SnmpProcess.cfg'. "
	::= { usrSnmp 1 }

	usrSnmpCFMStatusFlag  OBJECT-TYPE
	 	SYNTAX	  UsrConfigStatus
		ACCESS      read-write
		STATUS      mandatory
		DESCRIPTION
		  "Setting the value of this object to `save' causes the values
		   of the SNMP Group to be written out to the current config
		   file, which is stored in the usrSnmpConfigFileName object.
		   While the new ConfigFile is being written, the SNMP process
		   will set the value of this flag to `saving''. Any
		   attempts to set the value while it is not `normal'
		   (i.e. the file is currently being written to the
		   ConfigFile) while result in a badValue error being
		   returned. Setting the value to `normal' will result in no
		   action."
	::= { usrSnmp 2 }

	usrSnmpCommTable OBJECT-TYPE
		SYNTAX  SEQUENCE OF UsrSnmpCommEntry
         	ACCESS  not-accessible
         	STATUS  mandatory
         	DESCRIPTION
            "The SNMP Community Table"
	::= { usrSnmp 3 }

	usrSnmpCommEntry OBJECT-TYPE
         	SYNTAX  UsrSnmpCommEntry
         	ACCESS  not-accessible
         	STATUS  mandatory
         	DESCRIPTION
            ""
         INDEX   { usrSnmpCommName }
	::= { usrSnmpCommTable 1 }

	UsrSnmpCommEntry ::=
         	SEQUENCE {
         	usrSnmpCommName
            DisplayString,
         	usrSnmpCommIpAddr
            IpAddress,
         	usrSnmpCommAccess
            INTEGER,
         	usrSnmpCommStatus
            INTEGER,
         	usrSnmpCommLastError
            DisplayString,
         	usrSnmpCommLastErrorTicks
            INTEGER,
          usrSnmpCommPoolName
            DisplayString,
	  usrSnmpCommPoolValid
            INTEGER,
          usrSnmpCommValidateAddress
            INTEGER
         }

	usrSnmpCommName OBJECT-TYPE
         	SYNTAX  DisplayString (SIZE (0..255))
         	ACCESS  not-accessible
         	STATUS  mandatory
         	DESCRIPTION
            "The name of the SNMP Community."
	::= { usrSnmpCommEntry 1 }

	usrSnmpCommIpAddr OBJECT-TYPE
         	SYNTAX  IpAddress
         	ACCESS  read-write
         	STATUS  mandatory
         	DESCRIPTION
            "The IP Address of the remote community"
		--CONFIGURABLE
	::= { usrSnmpCommEntry 2 }

	usrSnmpCommAccess OBJECT-TYPE
	 	SYNTAX   INTEGER {
			readOnly(1),
			readWrite(2),
			administrator(4)
			}
         	ACCESS   read-write
         	STATUS   mandatory
         	DESCRIPTION
            "The allowed access for this community.
		   A value of readOnly(1) allows read-only access to user-level
		   objects.
		   A value of readWrite(2) allows read access to user-level
		   objects and write access to writable user-level objects.
		   A value of administrator(3) allows read access to all
		   objects and write access to all writable objects."
		--CONFIGURABLE
         ::= { usrSnmpCommEntry 3 }

	usrSnmpCommStatus OBJECT-TYPE
	 	SYNTAX   INTEGER {
			normal(1),
			delete(2)
			}
         	ACCESS   read-write
         	STATUS   mandatory
         	DESCRIPTION
            "The status of the entry for this community"
         ::= { usrSnmpCommEntry 4 }

	usrSnmpCommLastError OBJECT-TYPE
         	SYNTAX  DisplayString (SIZE (0..511))
         	ACCESS  read-only
         	STATUS  mandatory
         	DESCRIPTION
            "If there is an error on a request, this variable may
		   contain a message indicating the error."
	::= { usrSnmpCommEntry 5 }

	usrSnmpCommLastErrorTicks OBJECT-TYPE
	 	SYNTAX   INTEGER
         	ACCESS   read-only
         	STATUS   mandatory
         	DESCRIPTION
            "If the LastError variable is set, this is set to the
		   tick count of that error."
         ::= { usrSnmpCommEntry 6 }

	usrSnmpCommPoolName OBJECT-TYPE
	 	SYNTAX   DisplayString (SIZE (0..32))
         	ACCESS   read-write
         	STATUS   mandatory
         	DESCRIPTION
            "The name of the SNMP community address pool to use
             for this community."
         --CONFIGURABLE
         ::= { usrSnmpCommEntry 7 }

	usrSnmpCommPoolValid OBJECT-TYPE
	 	SYNTAX   INTEGER {
			valid(1),
			invalid(2)
			}
         	ACCESS   read-only
         	STATUS   mandatory
         	DESCRIPTION
            "A value of valid(1) means that the community pool
             assigned to this community exists. A value of
             invalid(2) means that the community pool assigned
             to this community does not exist."
         ::= { usrSnmpCommEntry 8 }

	usrSnmpCommValidateAddress OBJECT-TYPE
	 	SYNTAX   INTEGER {
			useAddress(1),
			usePool(2)
			}
         	ACCESS   read-write
         	STATUS   mandatory
         	DESCRIPTION
            "If this object is set to use_address(1), the value
             of usrSnmpCommIpAddr will be used to validate that the
             management station is allowed access. If this object
             is set to use_pool(2), the IP address of the
             management station will be validate using the list
             of IP addresses configured for the usrSnmpCommPoolName."
         DEFVAL { useAddress }
         --CONFIGURABLE
         ::= { usrSnmpCommEntry 9 }

	usrSnmpTrapCommTable OBJECT-TYPE
         	SYNTAX  SEQUENCE OF UsrSnmpTrapCommEntry
         	ACCESS  not-accessible
         	STATUS  mandatory
         	DESCRIPTION
            "The SNMP Trap Community Table"
	::= { usrSnmp 4 }

	usrSnmpTrapCommEntry OBJECT-TYPE
         	SYNTAX  UsrSnmpTrapCommEntry
         	ACCESS  not-accessible
         	STATUS  mandatory
         	DESCRIPTION
            ""
         INDEX   { usrSnmpTrapCommName }
	::= { usrSnmpTrapCommTable 1 }

	UsrSnmpTrapCommEntry ::=
         	SEQUENCE {
         	usrSnmpTrapCommName
            DisplayString,
         	usrSnmpTrapCommIpAddr
            IpAddress,
         	usrSnmpTrapCommStatus
            INTEGER,
                usrSnmpTrapCommPoolName
            DisplayString,
	        usrSnmpTrapCommPoolValid
            INTEGER,
                usrSnmpTrapCommValidateAddress
            INTEGER

         }

	usrSnmpTrapCommName OBJECT-TYPE
         	SYNTAX  DisplayString (SIZE (0..255))
         	ACCESS  not-accessible
         	STATUS  mandatory
         	DESCRIPTION
            "The name of the SNMP Trap Community."
	::= { usrSnmpTrapCommEntry 1 }

	usrSnmpTrapCommIpAddr OBJECT-TYPE
         	SYNTAX  IpAddress
         	ACCESS  read-write
         	STATUS  mandatory
         	DESCRIPTION
            "The IP Address of the remote community"
		--CONFIGURABLE
	::= { usrSnmpTrapCommEntry 2 }

	usrSnmpTrapCommStatus OBJECT-TYPE
		SYNTAX   INTEGER {
			normal(1),
			delete(2)
			}
         	ACCESS   read-write
         	STATUS   mandatory
         	DESCRIPTION
            "The status of the entry for this community"
         ::= { usrSnmpTrapCommEntry 3 }

	usrSnmpTrapCommPoolName OBJECT-TYPE
	 	SYNTAX   DisplayString (SIZE (0..32))
         	ACCESS   read-write
         	STATUS   mandatory
         	DESCRIPTION
            "The name of the SNMP community address pool to use
             for this community."
         --CONFIGURABLE
         ::= { usrSnmpTrapCommEntry 4 }

	usrSnmpTrapCommPoolValid OBJECT-TYPE
	 	SYNTAX   INTEGER {
			valid(1),
			invalid(2)
			}
         	ACCESS   read-only
         	STATUS   mandatory
         	DESCRIPTION
            "A value of valid(1) means that the community pool
             assigned to this community exists. A value of
             invalid(2) means that the community pool assigned
             to this community does not exist."
         ::= { usrSnmpTrapCommEntry 5 }

	usrSnmpTrapCommValidateAddress OBJECT-TYPE
	 	SYNTAX   INTEGER {
			useAddress(1),
			usePool(2)
			}
         	ACCESS   read-write
         	STATUS   mandatory
         	DESCRIPTION
            "If this object is set to use_address(1), the value
             of usrSnmpTrapCommIpAddr will be used to validate that the
             management station is allowed access. If this object
             is set to use_pool(2), the IP address of the
             management station will be validate using the list
             of IP addresses configured for the usrSnmpCommPoolName."
         DEFVAL { useAddress }
         --CONFIGURABLE
         ::= { usrSnmpTrapCommEntry 6 }


	usrSnmpCommAddrPoolTable OBJECT-TYPE
         	SYNTAX  SEQUENCE OF UsrSnmpCommAddrPoolEntry
         	ACCESS  not-accessible
         	STATUS  mandatory
         	DESCRIPTION
            "The SNMP Community Address Pool Table"
	::= { usrSnmp 5 }

	usrSnmpCommAddrPoolEntry OBJECT-TYPE
         	SYNTAX  UsrSnmpCommAddrPoolEntry
         	ACCESS  not-accessible
         	STATUS  mandatory
         	DESCRIPTION
            ""
         INDEX   { usrSnmpCommAddrPoolName,
                   usrSnmpCommAddrPoolIpAddr }
	::= { usrSnmpCommAddrPoolTable 1 }

	UsrSnmpCommAddrPoolEntry ::=
         	SEQUENCE {
         	usrSnmpCommAddrPoolName
            DisplayString,
         	usrSnmpCommAddrPoolIpAddr
            IpAddress,
         	usrSnmpCommAddrPoolStatus
            INTEGER,
	        usrSnmpCommAddrPoolGroupCount
            INTEGER

         }

	usrSnmpCommAddrPoolName OBJECT-TYPE
         	SYNTAX  DisplayString (SIZE (0..32))
         	ACCESS  not-accessible
         	STATUS  mandatory
         	DESCRIPTION
            "The name of the SNMP Community Address Pool."
	::= { usrSnmpCommAddrPoolEntry 1 }

	usrSnmpCommAddrPoolIpAddr OBJECT-TYPE
         	SYNTAX  IpAddress
         	ACCESS  not-accessible
         	STATUS  mandatory
         	DESCRIPTION
            "An IP Address in the SNMP community address pool."
	::= { usrSnmpCommAddrPoolEntry 2 }

	usrSnmpCommAddrPoolStatus OBJECT-TYPE
		SYNTAX   INTEGER {
			normal(1),
			delete(2)
			}
         	ACCESS   read-write
         	STATUS   mandatory
         	DESCRIPTION
            "The status of the entry in this SNMP community
             address pool."
         --CONFIGURABLE
         ::= { usrSnmpCommAddrPoolEntry 3 }

	usrSnmpCommAddrPoolGroupCount OBJECT-TYPE
		SYNTAX   INTEGER 
         	ACCESS   read-only
         	STATUS   mandatory
         	DESCRIPTION
            "The number of addresses per community."
         ::= { usrSnmpCommAddrPoolEntry 4 }


	usrSnmpTrapCommAddrPoolTable OBJECT-TYPE
         	SYNTAX  SEQUENCE OF UsrSnmpTrapCommAddrPoolEntry
         	ACCESS  not-accessible
         	STATUS  mandatory
         	DESCRIPTION
            "The SNMP Community Address Pool Table"
	::= { usrSnmp 6 }

	usrSnmpTrapCommAddrPoolEntry OBJECT-TYPE
         	SYNTAX  UsrSnmpTrapCommAddrPoolEntry
         	ACCESS  not-accessible
         	STATUS  mandatory
         	DESCRIPTION
            ""
         INDEX   { usrSnmpTrapCommAddrPoolName,
                   usrSnmpTrapCommAddrPoolIpAddr }
	::= { usrSnmpTrapCommAddrPoolTable 1 }

	UsrSnmpTrapCommAddrPoolEntry ::=
         	SEQUENCE {
         	usrSnmpTrapCommAddrPoolName
            DisplayString,
         	usrSnmpTrapCommAddrPoolIpAddr
            IpAddress,
         	usrSnmpTrapCommAddrPoolStatus
            INTEGER,
	        usrSnmpTrapCommAddrPoolGroupCount
            INTEGER
         }

	usrSnmpTrapCommAddrPoolName OBJECT-TYPE
         	SYNTAX  DisplayString (SIZE (0..32))
         	ACCESS  not-accessible
         	STATUS  mandatory
         	DESCRIPTION
            "The name of the SNMP Community Address Pool."
	::= { usrSnmpTrapCommAddrPoolEntry 1 }

	usrSnmpTrapCommAddrPoolIpAddr OBJECT-TYPE
         	SYNTAX  IpAddress
         	ACCESS  not-accessible
         	STATUS  mandatory
         	DESCRIPTION
            "An IP Address in the SNMP community address pool."
	::= { usrSnmpTrapCommAddrPoolEntry 2 }

	usrSnmpTrapCommAddrPoolStatus OBJECT-TYPE
		SYNTAX   INTEGER {
			normal(1),
			delete(2)
			}
         	ACCESS   read-write
         	STATUS   mandatory
         	DESCRIPTION
            "The status of the entry in this SNMP community
             address pool."
         --CONFIGURABLE
         ::= { usrSnmpTrapCommAddrPoolEntry 3 }

	usrSnmpTrapCommAddrPoolGroupCount OBJECT-TYPE
		SYNTAX   INTEGER 
         	ACCESS   read-only
         	STATUS   mandatory
         	DESCRIPTION
            "The number of addresses per community."
         ::= { usrSnmpTrapCommAddrPoolEntry 4 }

END         -- End usr SNMP MIB definitions

--
-- For the revision history to work correctly, after a new MIB file has been
-- added to the CVS repository the first time the CVS Admin person needs to
-- set the correct comment string delimter for the file.
--
-- $Log: usr_snmp.mib,v $
-- Revision 1.8.10.4  1998/06/26 21:10:10  edjean
-- merge 20 to 30, trap feature
--
-- Revision 1.8.10.3  1998/02/03 15:01:46  edjean
-- Add object for SNMP Community Pool support.
--
-- Revision 1.8.10.2  1998/01/27 13:59:44  edjean
-- Multiple IP Addresses per Community
--
--Revision 1.8.10.1  1997/09/17  19:06:40  psd
--Merged 2.0 to 3.0
--
--Revision 1.10.2.1  1997/09/05  15:09:38  psd
--Changes to MIBs so that they compile using the SimpleTester.
--
--Revision 1.10  1997/07/12  14:47:04  rsivan
--Removed 'RESTRICTED' tags until final design spec.
--
-- Revision 1.9  1997/07/10 15:29:04  rsivan
-- add access administrator(4), make some entries RESTRICTED
--
-- Revision 1.8  1996/05/08 20:18:19  pfc
-- Add error message to the community mib
--
-- Revision 1.7  1996/03/26 22:05:31  psd
-- Removed the CONFIGURABLE flag from the Config File object.
--
-- Revision 1.6  1996/03/11 14:46:26  psd
-- Changed usrSnmpSaveFlag to usrSnmpCFMStatusFlag.
--
-- Revision 1.5  1996/03/06 13:02:43  psd
-- Modified the description of usrSnmpSaveFlag.
--
-- Revision 1.4  1996/03/04 18:42:43  psd
-- Added CFM support for SNMP.
--
-- Revision 1.3  1995/12/22 18:31:55  jhalpin
-- community names are now nonaccessible
--
-- Revision 1.2  1995/09/26 16:28:47  patton
-- added status fields
--
-- Revision 1.1  1995/09/25 20:57:26  jhalpin
-- Add in usrSnmp definitions
--
--
--
--
--
-- Local Variables:
-- tab-width:5
-- tab-stop-list:( 5 10 15 20 25 30 35 40 45 50 55 60 65 70 75 80)
-- End:
--
--
--	usr_event.mib
--
--
-- Author:         Jim Halpin
--
-- $Id: usr_event.mib,v 1.5.4.1 1998/05/26 22:25:36 senthil Exp $
--
--  | Copyright (c) 1995 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

Event-MIB DEFINITIONS ::= BEGIN

	IMPORTS
	     Counter, IpAddress
                  FROM RFC1155-SMI
          OBJECT-TYPE
                  FROM RFC-1212
		  TruthValue				FROM SNMPv2-TC
          DisplayString, usrEventHandler,
		UsrConfigStatus
                  FROM USR-DEFINITIONS-MIB;


   -- textual conventions

   -- Begin managed object definitions here...

usrEhVersion OBJECT-TYPE
	SYNTAX		DisplayString
	ACCESS		read-only
	STATUS		mandatory
	DESCRIPTION
		"The current software version of the Event Handler process.."
::= { usrEventHandler 1 }

usrEhConfigFileName OBJECT-TYPE
	SYNTAX		DisplayString
	ACCESS		read-write
	STATUS		mandatory
	DESCRIPTION		
		  "The name of a ConfigFile to read/write permanent database records.
		   If the value of this object is an empty string, then the
		   Event process uses the default name `@file://EventProcess.cfg'."
	::= { usrEventHandler 2 }

usrEhCFMStatusFlag OBJECT-TYPE
	SYNTAX		UsrConfigStatus
	ACCESS		read-write
	STATUS		mandatory
	DESCRIPTION
		"This variable controls saving and loading of configuration
           information for the Event Handler process. The value can 
           be set to either save or load by a management station. The other
           values indicate if any configuration operation and what type
           is in progress."
::= { usrEventHandler 3 }

usrEhSyslogTable OBJECT-TYPE
	SYNTAX SEQUENCE OF UsrEhSyslogEntry
	ACCESS not-accessible
	STATUS mandatory
	DESCRIPTION
		"The (conceptual) table of SYSLOG sink nodes."
::= { usrEventHandler 4 }

usrEhSyslogEntry OBJECT-TYPE
	SYNTAX UsrEhSyslogEntry
	ACCESS not-accessible
	STATUS mandatory
	DESCRIPTION
		"A (conceptual) entry for one SYSLOG sink node."
	INDEX { usrEhSyslogSink }
::= { usrEhSyslogTable 1 }

UsrEhSyslogEntry ::= SEQUENCE {
	usrEhSyslogSink			IpAddress,
	usrEhSyslogLevel			INTEGER,
	usrEhSyslogMsgCount			Counter,
	usrEhSyslogStatus			INTEGER,
	usrEhSyslogFacility			INTEGER,
	usrEhSyslogAllowAllAuthLevels		TruthValue,
	usrEhSyslogBufferConfDepth		INTEGER,
	usrEhSyslogBufferReset			INTEGER
	}

usrEhSyslogSink OBJECT-TYPE
	SYNTAX		IpAddress
	ACCESS		not-accessible
	STATUS		mandatory
	DESCRIPTION
		"The IP Address of the SYSLOG sink system. Event messages for the
		 EVF_SYSLOG event sink will be sent to this address's UDP port
		 number 514."
::= { usrEhSyslogEntry 1 }

usrEhSyslogLevel OBJECT-TYPE
	SYNTAX		INTEGER { critical(0), unusual(1), common(2), verbose(3),
						debug(4) }
	ACCESS		read-write
	STATUS		mandatory
	DESCRIPTION
		"The log level associated with this SYSLOG sink node."
	--CONFIGURABLE
::= { usrEhSyslogEntry 2 }

usrEhSyslogMsgCount OBJECT-TYPE
	SYNTAX		Counter
	ACCESS		read-only
	STATUS		mandatory
	DESCRIPTION
		"The number of event messages sent to this syslog sink."
::= { usrEhSyslogEntry 3 }

usrEhSyslogStatus OBJECT-TYPE
	SYNTAX		INTEGER { normal(1), delete(2) }
	ACCESS		read-write
	STATUS		mandatory
	DESCRIPTION
		"Status flag for the SYSLOG sink. The value returned by the
		 Event process will always be normal. Setting the value to
		 delete will cause the entry to removed from the table."
::= { usrEhSyslogEntry 4 }

usrEhSyslogFacility OBJECT-TYPE
	SYNTAX		INTEGER { auth(1), local0(2), local1(3),
						local2(4), local3(5), local4(6),
						local5(7), local6(8), local7(9) }
	ACCESS		read-write
	STATUS		mandatory
	DESCRIPTION
		"The SYSLOG sink node facility to which the SYSLOG message is
		 is sent."
	--CONFIGURABLE
::= { usrEhSyslogEntry 5 }

usrEhSyslogAllowAllAuthLevels OBJECT-TYPE
	SYNTAX		TruthValue
	ACCESS		read-write
	STATUS		mandatory
	DESCRIPTION
		"Whether Pilgrim Auth facility messages get sent irrespective of
		 their loglevels.  Default is Yes(2).  No is (1)."
	--CONFIGURABLE
::= { usrEhSyslogEntry 6 }

usrEhSyslogBufferConfDepth OBJECT-TYPE
	SYNTAX		INTEGER (1..256)
	ACCESS		read-write
	STATUS		mandatory
	DESCRIPTION
		"Maximum number of syslogs that are buffered for a particular server"
	--CONFIGURABLE
 ::= { usrEhSyslogEntry 7 }

usrEhSyslogBufferReset OBJECT-TYPE
	SYNTAX		INTEGER (1..2)
	ACCESS		read-write
	STATUS		mandatory
	DESCRIPTION
		"Indicator to reset the syslogs"
	--CONFIGURABLE
 ::= { usrEhSyslogEntry 8 }

usrEhSyslogBufferState OBJECT-TYPE
	SYNTAX		INTEGER {
                       enabled(1),
                      disabled(2)
                     }
	ACCESS		read-write
	STATUS		mandatory
	DESCRIPTION
		"This flag states whether syslog buffering is enabled/disabled/reset."
 ::= { usrEventHandler 5 }

usrEhResetSyslogBuffer OBJECT-TYPE
	SYNTAX		INTEGER
	ACCESS		write-only
	STATUS		mandatory
	DESCRIPTION
		"This flag states whether syslog buffering is to be reset"
 ::= { usrEventHandler 6 }


END         -- End Template MIB definitions

--
--
-- $Log: usr_event.mib,v $
-- Revision 1.5.4.1  1998/05/26 22:25:36  senthil
-- MR 6652: All Pilgrim Auth facility msgs sent even if syslog is at level CRITICAL
--
-- Revision 1.5  1997/02/28 18:25:46  psd
-- Use better values for SYSLOG facility.
--
-- Revision 1.4  1997/02/26 17:24:31  psd
-- Added a SYSLOG facility object.
--
-- Revision 1.3  1996/03/27 13:54:09  psd
-- Added CFM support.
--
-- Revision 1.2  1995/12/20 22:56:10  jhalpin
-- Updated event MIB
--
-- Revision 1.1  1995/12/12 02:44:04  jhalpin
-- event handler mib
--
--
--
-- Local Variables:
-- tab-width:5
-- tab-stop-list:( 5 10 15 20 25 30 35 40 45 50 55 60 65 70 75 80)
-- End:
--
--
--     usr_cip.mib -  A template MIB file for Pilgrim MIB modules
--		
--
--	Description:	This module contains MIB definitions for the 
--      		Call-Initiation Process. 
--
--	Author:	Hasmik Sarkezians
--
--	$Id: usr_cip.mib,v 1.33.2.20 1998/06/30 23:50:47 senthil Exp $
--
--  ----------------------------------------------------------------------
-- | Copyright (c) 1995 U.S. Robotics Access Corp., Skokie, IL 60076      |
-- |                                                                      |
-- | The information in this software is subject to change without notice |
-- | and should not be construed as a commitment by U.S. Robotics Access  |
-- | Corp.                                                                |
-- |                                                                      |
-- | U.S. Robotics Access Corp. assumes no responsibility for the use or  |
-- | reliability of its software on equipment which is not supplied by    |
-- | U.S. Robotics Access Corp.                                           |
-- |                                                                      |
-- | This software is furnished under a license and may be copied only    |
-- | with the inclusion of the above copyright notice. This software, or  |
-- | any other copies thereof, may not be provided or otherwise made      |
-- | available to any other person except to one who agrees to these      |
-- | license terms. Title to and ownership of the software shall at all   |
-- | times remain in U.S. Robotics Access Corp.                           |
--  ----------------------------------------------------------------------
--

Cip-MIB DEFINITIONS ::= BEGIN

	IMPORTS
          IpAddress, Counter
                FROM RFC1155-SMI
	  Counter32 
                FROM SNMPv2-SMI
          OBJECT-TYPE
               FROM RFC-1212
          usrCip, DisplayString FROM USR-DEFINITIONS-MIB;

   -- textual conventions
   -- 
   -- textual conventions are like pre-processor macro in 'C'
   --        (i.e. #define statements)
   -- Use them to define your own 'datatypes'

   NetNumber ::= OCTET STRING (SIZE(4))

   -- Begin managed object definitions here...


	usrCipPortParamTable OBJECT-TYPE
         SYNTAX  SEQUENCE OF USRCIPPortParamEntry
         ACCESS  not-accessible
         STATUS  mandatory
         DESCRIPTION
            "This table contains the serial port parameters."
	::= { usrCip 1 }

     usrCipPortParamEntry OBJECT-TYPE
        SYNTAX      USRCIPPortParamEntry
        ACCESS      not-accessible
        STATUS      mandatory
        DESCRIPTION "Each entry corresponds to a serial interface."
        INDEX   {
                usrCipPortIndex
               }
     ::= {usrCipPortParamTable 1}

     USRCIPPortParamEntry ::= 
          SEQUENCE {
               usrCipPortIndex
                    INTEGER,
               usrCipPortType
                    INTEGER,
               usrCipPortAccess
                    INTEGER,
               usrCipPortHostType
                    INTEGER,
               usrCipPortLoginService
                    INTEGER,
               usrCipPortTcpPortNumber
                    INTEGER,
               usrCipPortLoginMsg
                    OCTET STRING,
               usrCipPortLoginPrompt
                    OCTET STRING,
               usrCipPortIpAddress
                    IpAddress,
               usrCipPortHostIpAddress
                    IpAddress,
               usrCipPortNetMask
                    INTEGER,
               usrCipPortProtocol
                    INTEGER,
               usrCipPortMtu
                    INTEGER,
               usrCipPortIdleTimeOut
                    INTEGER,
               usrCipPortState
                    INTEGER,
               usrCipPortNumConns
                    Counter,
               usrCipPortConnType
                    INTEGER,
               usrCipUserName
                    OCTET STRING,
               usrCipConnStartTime
                    INTEGER,
               usrCipDataLinkConn
                    INTEGER,
               usrCipInitScriptName
                    DisplayString,
               usrCipIfConnType
                    INTEGER,
               usrCipPromptUserName
                    OCTET STRING,
               usrCipUserPasswd
                    OCTET STRING,
               usrCipPortIfName
                    OCTET STRING,
               usrCipPortDialPrefix
                    OCTET STRING,
               usrCipPortCfgScript
                    DisplayString,
               usrCipPortCfgScriptResult
                    DisplayString,
               usrCipPortPromptingStyle
                    INTEGER,
               usrCipPortLoginProcessing
                    INTEGER,
               usrCipPortCallType
                   INTEGER,
	       usrCipPortDNISAuthentication
		   INTEGER,
	       usrCipPortDNISAuthTime
		   INTEGER,
	       usrCipPortDNISAuthType
		   INTEGER,
	       usrCipPortDNISPassword
		   OCTET STRING, 
	       usrCipPortDNISTimeout
		   INTEGER,
	       usrCipPortParity
		   INTEGER,
               usrCipPortDomainName
                    OCTET STRING,
               usrCipPortDelimiter 
                    OCTET STRING,
               usrCipPromptDelay 
                   INTEGER,
	       usrCipPromptTimeout
		   INTEGER,
	       usrCipSpecialXonXoffFlow
                   INTEGER,
			   usrCipCalledPhoneNumber
                   OCTET STRING,
			   usrCipCallingPhoneNumber
                   OCTET STRING,
			   usrCipPortGlobalConnId
				   INTEGER,
			   usrCipPortUseDnisPool
				   INTEGER,
				usrCipPortLoginTable
				   OCTET STRING,
               usrCipPortMobileType    
                  INTEGER,
               usrCipPortInputFilter   
                  OCTET STRING,
               usrCipPortLCPKeepAlive
                  INTEGER,
               usrCipPortPasswordPrompt
                  OCTET STRING
               }

     usrCipPortIndex OBJECT-TYPE
          SYNTAX      INTEGER
          ACCESS      read-write
          STATUS      mandatory
          DESCRIPTION "The identifier of the physical interface."
     ::= {usrCipPortParamEntry 1}

     usrCipPortType OBJECT-TYPE
          SYNTAX      INTEGER {
                         login (1),
                         network (2),
                         login-network (3)
                         }
          ACCESS      read-write
          STATUS      mandatory
          DESCRIPTION "The type of the physical port."
        --CONFIGURABLE
     ::= {usrCipPortParamEntry 2}

     usrCipPortAccess OBJECT-TYPE
          SYNTAX      INTEGER {
                         dial-in(1),
                         dial-out(2),
                         two-way(3)
                       }
          ACCESS      read-write
          STATUS      mandatory
          DESCRIPTION "This field specifies the direction of the calls
                         that could be made on a specific interface. 
                         Ports could be configured to be dial-in, dial-out
                         or two-way ports."
       --CONFIGURABLE
     ::= {usrCipPortParamEntry 3}

     usrCipPortHostType OBJECT-TYPE
          SYNTAX      INTEGER {
                         default (1),
                         prompt (2),
                         specified (3)
                         }
          ACCESS      read-write
          STATUS      mandatory
          DESCRIPTION "The host type that the dial-in user 
                       will be connected to."
        --CONFIGURABLE
     ::= {usrCipPortParamEntry 4}

     usrCipPortLoginService OBJECT-TYPE
          SYNTAX      INTEGER {
                         telnet (1),
                         rlogin (2),
                         cleartcp (3),
                         ping (4)
                         }
          ACCESS      read-write
          STATUS      mandatory
          DESCRIPTION "The Service type that the dial-in user will 
                       be connected to."
        --CONFIGURABLE
     ::= {usrCipPortParamEntry 5}

     usrCipPortTcpPortNumber OBJECT-TYPE
          SYNTAX      INTEGER
          ACCESS      read-write
          STATUS      mandatory
          DESCRIPTION "The tcp port number associated with the service type."
        --CONFIGURABLE
     ::= {usrCipPortParamEntry 6}

     usrCipPortLoginMsg OBJECT-TYPE
          SYNTAX      OCTET STRING (SIZE(0..800))
          ACCESS      read-write
          STATUS      mandatory
          DESCRIPTION "The salutation message associated with a specific port."
        --CONFIGURABLE
     ::= {usrCipPortParamEntry 7}

     usrCipPortLoginPrompt OBJECT-TYPE
   	  SYNTAX      OCTET STRING (SIZE(0..64))
   	  ACCESS      read-write
   	  STATUS      mandatory
   	  DESCRIPTION "The login prompt associated with a specific port."
        --CONFIGURABLE
     ::= {usrCipPortParamEntry 8}

     usrCipPortIpAddress OBJECT-TYPE
   	  SYNTAX      IpAddress
   	  ACCESS      read-write
   	  STATUS      mandatory
	  DESCRIPTION "The IP address for a specific serial port."
        --CONFIGURABLE
      ::= {usrCipPortParamEntry 9}

     usrCipPortHostIpAddress OBJECT-TYPE
   	  SYNTAX      IpAddress
   	  ACCESS      read-write
   	  STATUS      mandatory
	  DESCRIPTION "A host IP address specified for this interface."
        --CONFIGURABLE
   	::= {usrCipPortParamEntry 10}

     usrCipPortNetMask OBJECT-TYPE
   	  SYNTAX      INTEGER
   	  ACCESS      read-write
   	  STATUS      mandatory
   	  DESCRIPTION "The netmask associated with a specific 
                       serial interface."
        --CONFIGURABLE
     ::= {usrCipPortParamEntry 11}

     usrCipPortProtocol OBJECT-TYPE
   	  SYNTAX      INTEGER {
                         ppp (1),
                         slip (2),
                         arap (3)
                    	   }
   	  ACCESS      read-write
   	  STATUS      mandatory
   	  DESCRIPTION "The protocol type configured for a specific interface."
        --CONFIGURABLE
     ::= {usrCipPortParamEntry 12}

     usrCipPortMtu OBJECT-TYPE
   	  SYNTAX      INTEGER
   	  ACCESS      read-write
   	  STATUS      mandatory
   	  DESCRIPTION "The mtu value associated with a specific interface."
        --CONFIGURABLE
     ::= {usrCipPortParamEntry 13}

     usrCipPortIdleTimeOut OBJECT-TYPE
   	  SYNTAX      INTEGER
   	  ACCESS      read-write
   	  STATUS      mandatory
   	  DESCRIPTION "The maximum idle time specified for an interface."
        --CONFIGURABLE
     ::= {usrCipPortParamEntry 14}

     usrCipPortState OBJECT-TYPE
          SYNTAX        INTEGER {
                          port-disabled (0),
                          port-initializing(1),
                          port-available(2),
                          port-connecting(3),
                          port-connected(4),
                          port-disconnecting(5),
                          port-disconnected(6)
                           }
          ACCESS        read-only
          STATUS        mandatory
          DESCRIPTION  "The state of the serial line."
     ::= {usrCipPortParamEntry 15}

     usrCipPortNumConns OBJECT-TYPE
   	  SYNTAX      Counter
   	  ACCESS      read-only
   	  STATUS      mandatory
   	  DESCRIPTION "The total number of connections made on this if."
     ::= {usrCipPortParamEntry 16}

     usrCipPortConnType OBJECT-TYPE
          SYNTAX        INTEGER {
                          undefined-conn(0),
                          on-demand-conn(1),
                          dial-back-conn(2),
                          continuous-conn(3),
                          manual-conn(4),
                          timed-conn(5),
                          shared-modem-conn(6),
                          dial-in-conn(7),
                          bond-conn(8),
                          dedicated-conn (9)
                           }
          ACCESS        read-only
          STATUS        mandatory
          DESCRIPTION  "The connection type on this interface."
     ::= {usrCipPortParamEntry 17}

     usrCipUserName OBJECT-TYPE
          SYNTAX      OCTET STRING (SIZE(0..32))
   	  ACCESS      read-only
   	  STATUS      mandatory
   	  DESCRIPTION "The name user connected to this interface. "
     ::= {usrCipPortParamEntry 18}

     usrCipConnStartTime OBJECT-TYPE
          SYNTAX      INTEGER
          ACCESS      read-only
          STATUS      mandatory
          DESCRIPTION "The start time of a connection specified 
                       on an interface."
     ::= {usrCipPortParamEntry 19}

     usrCipDataLinkConn OBJECT-TYPE
          SYNTAX        INTEGER {
                           telnet (1),
                           rlogin (2),
                           clear-tcp (3),
                           ppp (4),
                           arap (5),
                           slip (6),
                           admin(7),
                           ping(8),
                           none(9),
                           lt2p(10),
                           pptp(11),
                           tap(12),
                           shell(13)
                           }
          ACCESS        read-only
          STATUS        mandatory
          DESCRIPTION  "The data link layer that a specific dial-in session is
                        connected to."
     ::= {usrCipPortParamEntry 20}

     usrCipInitScriptName OBJECT-TYPE
          SYNTAX      DisplayString  (SIZE(0..7))
          ACCESS      read-write
          STATUS      mandatory
          DESCRIPTION "The name of the script"
        --CONFIGURABLE
     ::= { usrCipPortParamEntry 21 }

     usrCipIfConnType OBJECT-TYPE
          SYNTAX      INTEGER {
                        if-direct-conn (1),
                        if-direct-network-conn (2),
                        if-normal-conn (3),
                        if-prompt-passwd (4),
                        if-prompt-none (5),
						if-ppp-only(6)
                        }
          ACCESS      read-write
          STATUS      mandatory
          DESCRIPTION "The type of the connection that i/f is configured for."
        --CONFIGURABLE
     ::= { usrCipPortParamEntry 22 }

     usrCipPromptUserName OBJECT-TYPE
          SYNTAX        OCTET STRING (SIZE(0..32))
          ACCESS        read-write
          STATUS        mandatory
          DESCRIPTION   "This could only be set if the port is
                        configured not to prompt for username."
     --CONFIGURABLE
     ::= {usrCipPortParamEntry 23}

     usrCipUserPasswd OBJECT-TYPE
          SYNTAX      OCTET STRING (SIZE(0..15))
   	  ACCESS      write-only
   	  STATUS      mandatory
   	  DESCRIPTION "This could only be set if the port is 
                       configured to not prompt for password."
        --CONFIGURABLE
     ::= { usrCipPortParamEntry 24 }

     usrCipPortIfName OBJECT-TYPE
          SYNTAX      OCTET STRING (SIZE(0..32))
   	  ACCESS      read-only
   	  STATUS      mandatory
   	  DESCRIPTION "The name of the serial line interface."
     ::= { usrCipPortParamEntry 25 }

     usrCipPortDialPrefix OBJECT-TYPE
         SYNTAX         OCTET STRING (SIZE(0..64))
         ACCESS         read-write
         STATUS         mandatory
         DESCRIPTION    "This string defines the prefix to the phone number."
         
       --CONFIGURABLE
    ::= {usrCipPortParamEntry 26}

    usrCipPortCfgScript OBJECT-TYPE
         SYNTAX         DisplayString (SIZE(1..32))
         ACCESS         read-write
         STATUS         mandatory
         DESCRIPTION    "This string defines an I-modem or V.34 AT command
			 a value of RESET will cause the modem to be reset 
                         and reinitialized with the string found in 
                         usrInitScriptCommands."
        
    ::= { usrCipPortParamEntry 27 }

    usrCipPortCfgScriptResult OBJECT-TYPE
         SYNTAX         DisplayString (SIZE(0..1350))
         ACCESS         read-only
         STATUS         mandatory
         DESCRIPTION    "This string defines the result of the AT command."
        
    ::= { usrCipPortParamEntry 28 }

    usrCipPortPromptingStyle OBJECT-TYPE
         SYNTAX        INTEGER {
                           local-prompting(1),
                           remote-prompting(2)
                       }                                                  
         ACCESS        read-write
         STATUS        mandatory 
         DESCRIPTION   "This value specifies whether the NAS will provide
                       username and password prompting locally or if the  
                       prompting will be handled by a remote security server."
       --CONFIGURABLE 
    ::= { usrCipPortParamEntry 29 }


    usrCipPortLoginProcessing OBJECT-TYPE
        SYNTAX INTEGER {
                       disable-auth-for-none (1),
                       disable-auth-for-async-ppp (2),
                       disable-auth-for-sync-ppp (3),
                       disable-auth-for-ppp (4)
                       }
        ACCESS read-write
        STATUS mandatory
        DESCRIPTION
            "This variable controls login processing.  This value can be set
			for controlling user authentication for different types of 
			autodetected PPP calls. Default is authentication is done for 
			all types of PPP calls.."
        --CONFIGURABLE
        ::= {usrCipPortParamEntry 30}

     usrCipPortDomainName OBJECT-TYPE
          SYNTAX      OCTET STRING (SIZE(0..240))
          ACCESS      read-write
          STATUS      mandatory
          DESCRIPTION "The Domain Name associated with this port "
       --CONFIGURABLE
     ::= { usrCipPortParamEntry 31 }
                   
     usrCipPortDelimiter  OBJECT-TYPE
          SYNTAX  OCTET STRING    (SIZE (1..6))
          ACCESS  read-write
          STATUS  mandatory
          DESCRIPTION      
              "The delimiter string port domain configuration"
          --CONFIGURABLE   
          ::= { usrCipPortParamEntry 32 } 


usrCipPortCallType OBJECT-TYPE
        SYNTAX INTEGER {
                       call-type-pptp(1),
                       call-type-l2tp(2),
                       call-type-none(3)
                       }
        ACCESS read-write
        STATUS mandatory
        DESCRIPTION
            "This variable call type associated with the interface."
        --CONFIGURABLE
        ::= {usrCipPortParamEntry 33}
 
	usrCipPortDNISAuthentication  OBJECT-TYPE
         SYNTAX INTEGER 
		 {
             dnis-auth-disabled (1),
             dnis-auth-preferred (2),
             dnis-auth-required (3)
         }
         ACCESS  read-write
         STATUS  mandatory
         DESCRIPTION
             "DNIS Authentication type"
         --CONFIGURABLE
         ::= { usrCipPortParamEntry 34 }

	usrCipPortDNISAuthTime  OBJECT-TYPE
         SYNTAX INTEGER 
		 {
             before-answer (1),
             after-answer (2)
         }
         ACCESS  read-write
         STATUS  mandatory
         DESCRIPTION
             "DNIS Authentication Time"
         --CONFIGURABLE
         ::= { usrCipPortParamEntry 35 }

	usrCipPortDNISAuthType  OBJECT-TYPE
         SYNTAX INTEGER 
		 {
             dnis (1),
             ani (2)
         }
         ACCESS  read-write
         STATUS  mandatory
         DESCRIPTION
             "DNIS Authentication type"
         --CONFIGURABLE
         ::= { usrCipPortParamEntry 36 }

     usrCipPortDNISPassword OBJECT-TYPE
          SYNTAX      OCTET STRING (SIZE(0..15))
   	  ACCESS      read-write
   	  STATUS      mandatory
   	  DESCRIPTION "The DNIS  password."
        --CONFIGURABLE
     ::= { usrCipPortParamEntry 37 }

     usrCipPortDNISTimeout OBJECT-TYPE
          SYNTAX      INTEGER
          ACCESS      read-write
          STATUS      mandatory
          DESCRIPTION "Timeout if no auth within this time"
        --CONFIGURABLE
     ::= {usrCipPortParamEntry 38}

    usrCipPortParity  OBJECT-TYPE
         SYNTAX INTEGER   
         {
             no-parity-eight-bit (1),
             even-seven-bit (2),
             odd-seven-bit (3),
             no-parity-seven-bit (4)
         }
         ACCESS  read-write      
         STATUS  mandatory     
         DESCRIPTION
             "Port Parity"
         --CONFIGURABLE
         ::= { usrCipPortParamEntry 39 }

    usrCipPromptDelay  OBJECT-TYPE
         SYNTAX INTEGER (0..100)
         ACCESS  read-write
         STATUS  mandatory
         DESCRIPTION
             "If user does not enter any key after banner mesg, authenticate
              user based on interface user name after this delay"
         --CONFIGURABLE
         ::= { usrCipPortParamEntry 40 }
 

    usrCipPromptTimeout  OBJECT-TYPE
         SYNTAX INTEGER (5..600)
         ACCESS  read-write
         STATUS  mandatory
         DESCRIPTION
             " This is the maximum timeout while prompting for 
				username password. If nothing is typed, the session will
				be terminated. Default is 300 secs"
         --CONFIGURABLE
         ::= { usrCipPortParamEntry 41 }

 
                  
    usrCipSpecialXonXoffFlow  OBJECT-TYPE
         SYNTAX INTEGER   
         {
             disabled (0),
             enabled (1)
         }
         ACCESS  read-write      
         STATUS  mandatory     
         DESCRIPTION
             "Specail Xon Xoff flow control in modem control receive side"
         --CONFIGURABLE
         ::= { usrCipPortParamEntry 42 }
     
	 usrCipCallingPhoneNumber OBJECT-TYPE
      SYNTAX      OCTET STRING (SIZE(0..64))
   	  ACCESS      read-only
   	  STATUS      mandatory
   	  DESCRIPTION "Calling phone number"
     ::= { usrCipPortParamEntry 43 }
	 
	 
	 usrCipCalledPhoneNumber OBJECT-TYPE
      SYNTAX      OCTET STRING (SIZE(0..64))
   	  ACCESS      read-only
   	  STATUS      mandatory
   	  DESCRIPTION "Called phone number"
     ::= { usrCipPortParamEntry 44 }

	usrCipPortGlobalConnId OBJECT-TYPE
      SYNTAX      INTEGER
      ACCESS      read-only
      STATUS      mandatory
      DESCRIPTION "Global Connection Id"
     ::= { usrCipPortParamEntry 45 }

	 usrCipPortUseDnisPool OBJECT-TYPE
         SYNTAX INTEGER 
		 {
             dnis-pool-disabled (1),
             dnis-pool-preferred (2),
             dnis-pool-required (3)
         }
         ACCESS  read-write
         STATUS  mandatory
         DESCRIPTION
             "User DNIS pool"
         --CONFIGURABLE
     ::= { usrCipPortParamEntry 46 }

     usrCipPortLoginTable OBJECT-TYPE
         SYNTAX OCTET STRING    
         ACCESS  read-write
         STATUS  mandatory
         DESCRIPTION
             "Login Host Table "
         --CONFIGURABLE 
     ::= { usrCipPortParamEntry 47 }

     usrCipPortMobileType OBJECT-TYPE
          SYNTAX        INTEGER {
                          undefined-conn(0),
                          mobile-ip(1),
                          simple-ip(2)
                           } 
          ACCESS        read-only
          STATUS        mandatory
          DESCRIPTION  "The Mobile Node connected"
     ::= {usrCipPortParamEntry 48}

        usrCipPortInputFilter OBJECT-TYPE
         SYNTAX OCTET STRING
         ACCESS  read-write
         STATUS  mandatory   
         DESCRIPTION
             "Input Filter"
         --CONFIGURABLE
     ::= { usrCipPortParamEntry 49 }
 
        usrCipPortLCPKeepAlive  OBJECT-TYPE
         SYNTAX INTEGER (0..5000)
         ACCESS read-write
         STATUS  mandatory
         DESCRIPTION
             " This is the LCP keep alive timer interval for PPP" 
         --CONFIGURABLE
         ::= { usrCipPortParamEntry 50 }

     usrCipPortPasswordPrompt OBJECT-TYPE
          SYNTAX      OCTET STRING (SIZE(0..64))
          ACCESS      read-write
          STATUS      mandatory
          DESCRIPTION "The login Password prompt associated with a specific port."
        --CONFIGURABLE
     ::= {usrCipPortParamEntry 51}


-- Modem Group Table 

      usrCipModemGroupTable OBJECT-TYPE
         SYNTAX  SEQUENCE OF USRCIPModemGroupEntry 
         ACCESS  not-accessible
         STATUS  mandatory
         DESCRIPTION
            "This table contains the serial port parameters."
      ::= { usrCip 2 }

     usrCipModemGroupEntry OBJECT-TYPE
        SYNTAX      USRCIPModemGroupEntry
        ACCESS      not-accessible
        STATUS      mandatory
        DESCRIPTION "Each entry corresponds to a serial interface."
        INDEX   {
                usrCipModemGroupName
               }
     ::= {usrCipModemGroupTable 1}

     USRCIPModemGroupEntry ::= 
          SEQUENCE {
               usrCipModemGroupName
                    DisplayString,
               usrCipModemGroupStatus
                    INTEGER,
               usrCipModemGroupCount
                    INTEGER
          }

     usrCipModemGroupName OBJECT-TYPE
          SYNTAX        DisplayString (SIZE (0..32))
          ACCESS        not-accessible
          STATUS        mandatory
          DESCRIPTION   "The identifier of a modem group."
     ::= { usrCipModemGroupEntry 1 }

     usrCipModemGroupStatus  OBJECT-TYPE
        SYNTAX          INTEGER {
                                add(0),
                                delete(1)
                                }
        ACCESS         	read-write
        STATUS          mandatory
        DESCRIPTION     "The status could be add or delete the group member
                         specified in the usrCipGroupMembers MIB."
      --CONFIGURABLE
    ::= { usrCipModemGroupEntry 2 }

     usrCipModemGroupCount OBJECT-TYPE
          SYNTAX      INTEGER
          ACCESS      read-only
          STATUS      mandatory
          DESCRIPTION "The number of modem ports in a specific group."
     ::= { usrCipModemGroupEntry 3 }



-- The Global Host Table

      usrCipGlblHostTable OBJECT-TYPE
         SYNTAX  SEQUENCE OF USRCIPGlblHostEntry
         ACCESS  not-accessible
         STATUS  mandatory
         DESCRIPTION
            "This table contains the global host addresses."
      ::= { usrCip 3 }

     usrCipGlblHostEntry OBJECT-TYPE
        SYNTAX      USRCIPGlblHostEntry
        ACCESS      not-accessible
        STATUS      mandatory
        DESCRIPTION "Each entry contains a host address with tcp port numbers."
        INDEX   {
                usrCipGlblHostIndex
                }
     ::= {usrCipGlblHostTable 1}

     USRCIPGlblHostEntry ::= 
         SEQUENCE {
               usrCipGlblHostIndex
                    INTEGER,
               usrCipGlblHostAddress
                    IpAddress,
               usrCipGlblHostRloginPort
                    INTEGER,
               usrCipGlblHostTelnetPort
                    INTEGER,
               usrCipGlblHostTcpClearPort
                    INTEGER,
               usrCipGlblHostName
                    OCTET STRING,
               usrCipGlblHostState 
                    INTEGER
          }

     usrCipGlblHostIndex OBJECT-TYPE
          SYNTAX      INTEGER
          ACCESS      read-write
          STATUS      mandatory
          DESCRIPTION "The identifier of a default host table."
     ::= { usrCipGlblHostEntry 1 }
     
     usrCipGlblHostAddress OBJECT-TYPE
        SYNTAX  IpAddress
        ACCESS  read-write
        STATUS  mandatory
        DESCRIPTION     
                "The global host IP address."
        --CONFIGURABLE                
     ::= { usrCipGlblHostEntry 2 }

     usrCipGlblHostRloginPort   OBJECT-TYPE
        SYNTAX  INTEGER
        ACCESS  read-write
        STATUS  mandatory
        DESCRIPTION
                "The host rlogin tcp port number."
        --CONFIGURABLE        
     ::= { usrCipGlblHostEntry 3 }        

     usrCipGlblHostTelnetPort   OBJECT-TYPE
        SYNTAX  INTEGER
        ACCESS  read-write
        STATUS  mandatory
        DESCRIPTION
                "The host telnet port number."
        --CONFIGURABLE
     ::= { usrCipGlblHostEntry 4 }

     usrCipGlblHostTcpClearPort OBJECT-TYPE
        SYNTAX  INTEGER
        ACCESS  read-write
        STATUS  mandatory
        DESCRIPTION     
                "The host tcp clear port number."
        --CONFIGURABLE
     ::= { usrCipGlblHostEntry 5 }

     usrCipGlblHostName OBJECT-TYPE
        SYNTAX  OCTET STRING (SIZE(0..32))
        ACCESS  read-write
        STATUS  mandatory
        DESCRIPTION
                "The global host name."
        --CONFIGURABLE
     ::= { usrCipGlblHostEntry 6 }

     usrCipGlblHostState OBJECT-TYPE
        SYNTAX  INTEGER {
                        host-undefined (0),
                        host-valid (1),
                        host-invalid (2),
                        host-pending (3)
                        }
        ACCESS  read-write
        STATUS  mandatory
        DESCRIPTION     
                "The state of a default host entry."
     ::= { usrCipGlblHostEntry 7 }

-- The Global Parameters

     usrCipGlblHostSelectionMethod      OBJECT-TYPE
        SYNTAX  INTEGER {
                        round-robin(0),
                        random(1)
                        }

        ACCESS  read-write
        STATUS  mandatory
        DESCRIPTION
                "The method that will be used to select the 
                 default host."
        --CONFIGURABLE
        ::= {usrCip 4}	     

     usrCipGlblHostType OBJECT-TYPE
        SYNTAX  INTEGER {
                        undefined-host(0),
                        default-host(1),
                        prompt(2)
                        }
        ACCESS  read-write
        STATUS  mandatory
        DESCRIPTION
            "The default host type."
        --CONFIGURABLE
        ::= { usrCip 5 }
                                              
     usrCipGlblLoginMsg OBJECT-TYPE
        SYNTAX  OCTET STRING (SIZE(0..255))
        ACCESS  read-write
        STATUS  mandatory
        DESCRIPTION
                "The user login message"
        --CONFIGURABLE
        ::= { usrCip 6 }
                                              
     usrCipGlblUsrCommandPrompt OBJECT-TYPE
        SYNTAX  OCTET STRING (SIZE(0..64))
        ACCESS  read-write
        STATUS  mandatory
        DESCRIPTION
                "The user command prompt."
        --CONFIGURABLE
        ::= { usrCip 7 }

      usrCipGlblLogNetUserPrompt OBJECT-TYPE
        SYNTAX  OCTET STRING (SIZE(0..64))
        ACCESS  read-write
        STATUS  mandatory
        DESCRIPTION
                "The login/network command prompt."
        --CONFIGURABLE
        ::= { usrCip 8 }

     usrCipGlblMgPrompt OBJECT-TYPE
        SYNTAX  OCTET STRING (SIZE(0..64))
        ACCESS  read-write
        STATUS  mandatory
        DESCRIPTION
                "The manage prompt."
        --CONFIGURABLE
        ::= { usrCip 9 }

     usrCipGlblUserName OBJECT-TYPE
        SYNTAX  OCTET STRING (SIZE(0..32))
        ACCESS  read-write
        STATUS  mandatory
        DESCRIPTION
                "The default user name used in case the dial-in users don't
                 get prompted for the user name and no user name is configured
                 for the i/f."
        --CONFIGURABLE
        ::= { usrCip 10 }

     usrCipGlblNumCalls OBJECT-TYPE
        SYNTAX  Counter
        ACCESS  read-only
        STATUS  mandatory
        DESCRIPTION
                "The total number of calls received since the boot up time."
        ::= { usrCip 11 }

     usrCipAllowManageOnDialups OBJECT-TYPE
        SYNTAX  INTEGER {
                        manage-off(0),
                        manage-on (1)
                        }
        ACCESS  read-write
        STATUS  mandatory
        DESCRIPTION
                "This variable turns on/off the ability to manage the system
                 through the dialup ports."
        --CONFIGURABLE
        ::= { usrCip 12 }

     usrCipHangUp OBJECT-TYPE
        SYNTAX  INTEGER
        ACCESS  write-only
        STATUS  mandatory
        DESCRIPTION
                "This variable is set only if a hangup message is sent out.
                 The value of this variable is the interface index."
        ::= {usrCip 13 }

     usrCipDialOut OBJECT-TYPE
        SYNTAX  OCTET STRING (SIZE(0..32))
        ACCESS  write-only
        STATUS  mandatory
        DESCRIPTION
                "This variable is set through the CLI when the user
                 manually issues a dial-out."
        ::= { usrCip 14 }

     usrCipBusyOut   OBJECT-TYPE
        SYNTAX  INTEGER
        ACCESS  write-only
        STATUS  mandatory
        DESCRIPTION     
                "This variable is set only in case the user wants to 
                take the phone off hook."
        ::= {usrCip 15}

     usrInitScriptTable OBJECT-TYPE
         SYNTAX  SEQUENCE OF USRInitScriptEntry
         ACCESS  not-accessible
         STATUS  mandatory
         DESCRIPTION
            "This table contains the global host addresses."
      ::= { usrCip 16}

     usrInitScriptEntry OBJECT-TYPE
        SYNTAX      USRInitScriptEntry
        ACCESS      not-accessible
        STATUS      mandatory
        DESCRIPTION "Each entry contains a host address with tcp port numbers."
        INDEX   {
                usrInitScriptName
                }
     ::= {usrInitScriptTable 1}

     USRInitScriptEntry ::= 
         SEQUENCE {
               usrInitScriptName
                    DisplayString,
               usrInitScriptCommands
                    DisplayString,
	       usrInitScriptStatus
		    INTEGER
                }

     usrInitScriptName OBJECT-TYPE
          SYNTAX      DisplayString  (SIZE(0..7))
          ACCESS      not-accessible
          STATUS      mandatory
          DESCRIPTION "The name of the script"
     ::= { usrInitScriptEntry 1 }

     usrInitScriptCommands OBJECT-TYPE
          SYNTAX        DisplayString (SIZE(0..56))
          ACCESS        read-write
          STATUS        mandatory
          DESCRIPTION   "The AT commands that will be sent to the serial line
                         driver every time a connection goes away."
        --CONFIGURABLE
     ::= { usrInitScriptEntry 2 }

     usrInitScriptStatus  OBJECT-TYPE
        SYNTAX          INTEGER {
                                normal-status(0),
                                delete-script(1)
                                }
        ACCESS         	read-write
        STATUS          mandatory
        DESCRIPTION     "This variable is used to delete a script from the init
                         script list."
    ::= { usrInitScriptEntry 3 }


-- MIB Variables defined for CFM purposes

     usrCipCfmPortIndexTable OBJECT-TYPE
         SYNTAX  SEQUENCE OF USRCIPCfmPortIndexEntry
         ACCESS  not-accessible
         STATUS  mandatory
         DESCRIPTION
            "This table contains CIP port indices. It is defined 
             so that CFM process would be able to save a specific
             row of portal table."
	::= { usrCip 17 }

     usrCipCfmPortIndexEntry OBJECT-TYPE
        SYNTAX      USRCIPCfmPortIndexEntry
        ACCESS      not-accessible
        STATUS      mandatory
        DESCRIPTION "Each entry corresponds to a serial interface."
        INDEX   {
                usrCipCfmPortIndex
               }
     ::= {usrCipCfmPortIndexTable 1}

     USRCIPCfmPortIndexEntry ::= 
          SEQUENCE {
               usrCipCfmPortIndex
                    INTEGER,
               usrCipCfmPortFlag
                    INTEGER
                }

     usrCipCfmPortIndex OBJECT-TYPE
          SYNTAX      INTEGER
          ACCESS      read-only
          STATUS      mandatory
          DESCRIPTION "The identifier of the physical interface."
     ::= {usrCipCfmPortIndexEntry 1}

     usrCipCfmPortFlag OBJECT-TYPE
          SYNTAX       INTEGER
          ACCESS       read-write
          STATUS       mandatory
          DESCRIPTION   "The flag that triggers a cfm operation on each
                         interface."
     ::= {usrCipCfmPortIndexEntry 2 }

-- Scalar Flags

    usrCipCfmAllPortsFlag  OBJECT-TYPE
         SYNTAX         INTEGER
         ACCESS         read-write
         STATUS         mandatory
         DESCRIPTION    "This flag triggers a CFM action."
    ::= { usrCip 18 }

    usrCipCfmModemGroupFlag OBJECT-TYPE
        SYNTAX          INTEGER
        ACCESS          read-write
        STATUS          mandatory
        DESCRIPTION     "This flag triggers a save of modem group table."
    ::= { usrCip 19 }

    usrCipCfmGlblHostTableFlag OBJECT-TYPE
        SYNTAX          INTEGER
        ACCESS          read-write
        STATUS          mandatory
        DESCRIPTION     "This flag triggers a save of global host table."
    ::= { usrCip 20 }        

    usrCipCfmInitScriptFlag OBJECT-TYPE
        SYNTAX          INTEGER
        ACCESS          read-write
        STATUS          mandatory
        DESCRIPTION     "This flag triggers a save of init script table."
    ::= { usrCip 21 }

    usrCipCfmGlblVarFlag OBJECT-TYPE
        SYNTAX          INTEGER
        ACCESS          read-write
        STATUS          mandatory
        DESCRIPTION     "This flag triggers a save of global variables."
    ::= { usrCip 22 }

   usrCipCfmSaveAllFlag OBJECT-TYPE
        SYNTAX          INTEGER
        ACCESS          read-write
        STATUS          mandatory
        DESCRIPTION     "This flag triggers a save for all of CIP tables."
        
    ::= { usrCip 23 }

-- Port Parameters Grouped in a Modem Group 

    usrCipModemPortParamTable OBJECT-TYPE
         SYNTAX  SEQUENCE OF USRCIPModemPortParamEntry
         ACCESS  not-accessible
         STATUS  mandatory
         DESCRIPTION
            "This table contains the serial port parameters."
	::= { usrCip 24 }

    usrCipModemPortParamEntry OBJECT-TYPE
        SYNTAX      USRCIPModemPortParamEntry
        ACCESS      not-accessible
        STATUS      mandatory
        DESCRIPTION "Each entry corresponds to a serial interface."
        INDEX   {
                usrCipModemPortName
               }
     ::= {usrCipModemPortParamTable 1}

     USRCIPModemPortParamEntry ::= 
          SEQUENCE {
               usrCipModemPortName
                    OCTET STRING,
               usrCipModemPortType
                    INTEGER,
               usrCipModemPortAccess
                    INTEGER,
               usrCipModemPortHostType
                    INTEGER,
               usrCipModemPortLoginService
                    INTEGER,
               usrCipModemPortTcpPortNumber
                    INTEGER,
               usrCipModemPortLoginMsg
                    OCTET STRING,
               usrCipModemPortLoginPrompt
                    OCTET STRING,
               usrCipModemPortIpAddress
                    IpAddress,
               usrCipModemPortHostIpAddress
                    IpAddress,
               usrCipModemPortNetMask
                    INTEGER,
               usrCipModemPortProtocol
                    INTEGER,
               usrCipModemPortMtu
                    INTEGER,
               usrCipModemPortIdleTimeOut
                    INTEGER,
               usrCipModemInitScriptName
                    DisplayString,
               usrCipModemIfConnType
                    INTEGER,
               usrCipModemPromptUserName
                    OCTET STRING,
               usrCipModemUserPasswd
                    OCTET STRING,
               usrCipModemDialPrefix
                    OCTET STRING,
               usrCipModemPortPromptingStyle
                    INTEGER,
               usrCipModemPortLoginProcessing
                    INTEGER,
               usrCipModemPortDNISAuthentication
                   INTEGER,
               usrCipModemPortDNISAuthTime
                   INTEGER,
               usrCipModemPortDNISAuthType 
                   INTEGER,
               usrCipModemPortDNISPassword
                   OCTET STRING,
               usrCipModemPortDNISTimeout
                   INTEGER,
              usrCipModemPortParity
                    INTEGER,
               usrCipModemPromptDelay
                   INTEGER,
			   usrCipModemPromptTimeout
				   INTEGER,
  				usrCipModemSpecialXonXoffFlow 
					INTEGER,
  				usrCipModemUseDnisPool 
					INTEGER,
				usrCipModemLoginTable
					OCTET STRING,
                usrCipModemLCPKeepAlive 
                    INTEGER,
               usrCipModemPortPasswordPrompt
                    OCTET STRING
               }

     usrCipModemPortName OBJECT-TYPE
          SYNTAX        OCTET STRING (SIZE (0..32))
          ACCESS        not-accessible
          STATUS        mandatory
          DESCRIPTION   "The identifier of a modem group."
     ::= {usrCipModemPortParamEntry 1}

     usrCipModemPortType OBJECT-TYPE
          SYNTAX      INTEGER {
                         login (1),
                         network (2),
                         login-network (3)
                         }
          ACCESS      write-only
          STATUS      mandatory
          DESCRIPTION "The type of the physical port."
     ::= {usrCipModemPortParamEntry 2}

     usrCipModemPortAccess OBJECT-TYPE
          SYNTAX      INTEGER {
                         dial-in(1),
                         dial-out(2),
                         two-way(3)
                       }
          ACCESS      write-only
          STATUS      mandatory
          DESCRIPTION "This field specifies the direction of the calls
                         that could be made on a specific interface. 
                         Ports could be configured to be dial-in, dial-out
                         or two-way ports."
     ::= {usrCipModemPortParamEntry 3}

     usrCipModemPortHostType OBJECT-TYPE
          SYNTAX      INTEGER {
                         default (1),
                         prompt (2),
                         specified (3)
                         }
          ACCESS      write-only
          STATUS      mandatory
          DESCRIPTION "The host type that the dial-in user 
                       will be connected to."
     ::= {usrCipModemPortParamEntry 4}

     usrCipModemPortLoginService OBJECT-TYPE
          SYNTAX      INTEGER {
                         telnet (1),
                         rlogin (2),
                         netdata (3)
                         }
          ACCESS      write-only
          STATUS      mandatory
          DESCRIPTION "The Service type that the dial-in user will 
                       be connected to."
     ::= {usrCipModemPortParamEntry 5}

     usrCipModemPortTcpPortNumber OBJECT-TYPE
          SYNTAX      INTEGER
          ACCESS      write-only
          STATUS      mandatory
          DESCRIPTION "The tcp port number associated with the service type."
     ::= {usrCipModemPortParamEntry 6}

     usrCipModemPortLoginMsg OBJECT-TYPE
          SYNTAX      OCTET STRING (SIZE(0..255))
          ACCESS      write-only
          STATUS      mandatory
          DESCRIPTION "The salutation message associated with a specific port."
     ::= {usrCipModemPortParamEntry 7}

     usrCipModemPortLoginPrompt OBJECT-TYPE
   	  SYNTAX      OCTET STRING (SIZE(0..64))
   	  ACCESS      write-only
   	  STATUS      mandatory
   	  DESCRIPTION "The login prompt associated with a specific port."
     ::= {usrCipModemPortParamEntry 8}

     usrCipModemPortIpAddress OBJECT-TYPE
   	  SYNTAX      IpAddress
   	  ACCESS      write-only
   	  STATUS      mandatory
	  DESCRIPTION "The IP address for a specific serial port."
      ::= {usrCipModemPortParamEntry 9}

     usrCipModemPortHostIpAddress OBJECT-TYPE
   	  SYNTAX      IpAddress
   	  ACCESS      write-only
   	  STATUS      mandatory
	  DESCRIPTION "A host IP address specified for this interface."
   	::= {usrCipModemPortParamEntry 10}

     usrCipModemPortNetMask OBJECT-TYPE
   	  SYNTAX      INTEGER
   	  ACCESS      write-only
   	  STATUS      mandatory
   	  DESCRIPTION "The netmask associated with a specific 
                       serial interface."
     ::= {usrCipModemPortParamEntry 11}

     usrCipModemPortProtocol OBJECT-TYPE
   	  SYNTAX      INTEGER {
                         ppp (1),
                         slip (2),
                         arap (3)
                    	   }
   	  ACCESS      write-only
   	  STATUS      mandatory
   	  DESCRIPTION "The protocol type configured for a specific interface."
     ::= {usrCipModemPortParamEntry 12}

     usrCipModemPortMtu OBJECT-TYPE
   	  SYNTAX      INTEGER
   	  ACCESS      write-only
   	  STATUS      mandatory
   	  DESCRIPTION "The mtu value associated with a specific interface."
     ::= {usrCipModemPortParamEntry 13}

     usrCipModemPortIdleTimeOut OBJECT-TYPE
   	  SYNTAX      INTEGER
   	  ACCESS      write-only
   	  STATUS      mandatory
   	  DESCRIPTION "The maximum idle time specified for an interface."
     ::= {usrCipModemPortParamEntry 14}

     usrCipModemInitScriptName OBJECT-TYPE
          SYNTAX      DisplayString  (SIZE(0..7))
          ACCESS      write-only
          STATUS      mandatory
          DESCRIPTION "The name of the script"
     ::= { usrCipModemPortParamEntry 15 }

     usrCipModemIfConnType OBJECT-TYPE
          SYNTAX      INTEGER {
                        if-direct-conn (1),
                        if-direct-network-conn (2),
                        if-normal-conn (3),
                        if-prompt-passwd (4),
                        if-prompt-none (5),
						if-ppp-only(6)
                        }
          ACCESS      write-only
          STATUS      mandatory
          DESCRIPTION "The type of the connection that i/f is configured for."
     ::= { usrCipModemPortParamEntry 16 }

     usrCipModemPromptUserName OBJECT-TYPE
          SYNTAX        OCTET STRING (SIZE(0..32))
          ACCESS        write-only
          STATUS        mandatory
          DESCRIPTION   "This could only be set if the port is
                        configured not to prompt for username."
     ::= { usrCipModemPortParamEntry 17 }

     usrCipModemUserPasswd OBJECT-TYPE
          SYNTAX      OCTET STRING (SIZE(0..15))
   	  ACCESS      write-only
   	  STATUS      mandatory
   	  DESCRIPTION "This could only be set if the port is 
                       configured to not prompt for password."
     ::= { usrCipModemPortParamEntry 18 }

     usrCipModemDialPrefix OBJECT-TYPE
         SYNTAX         OCTET STRING (SIZE(0..64))
         ACCESS         write-only
         STATUS         mandatory
         DESCRIPTION    "This string defines the prefix to the phone number."
        
    ::= { usrCipModemPortParamEntry 19 }

    usrCipModemPortPromptingStyle OBJECT-TYPE
         SYNTAX        INTEGER {
                           local-prompting(1),
                           remote-prompting(2)
                       }
         ACCESS        write-only
         STATUS        mandatory
         DESCRIPTION   "This value specifies whether the NAS will provide
                       username and password prompting locally or if the
                       prompting will be handled by a remote security server."
       --CONFIGURABLE
    ::= { usrCipModemPortParamEntry 20 }

    usrCipModemPortLoginProcessing OBJECT-TYPE
        SYNTAX INTEGER {
                       enable (1),
                       disable (2)
                       }
        ACCESS write-only
        STATUS mandatory
        DESCRIPTION
            "This variable controls login processing.  Setting the value to disable
             will cause the box to not prompt a user for login name or password.  Enabling
             this value will cause the box to perform normal login name and password prompting."
        --CONFIGURABLE
        ::= {usrCipModemPortParamEntry 21}
    

    usrCipModemPortDNISAuthentication  OBJECT-TYPE
         SYNTAX INTEGER    
         {     
             dnis-auth-disabled (1),
             dnis-auth-preferred (2), 
             dnis-auth-required (3)
         }      
         ACCESS  write-only
         STATUS  mandatory       
         DESCRIPTION  
             "DNIS Authentication type"
         --CONFIGURABLE
         ::= { usrCipModemPortParamEntry 22 }

    usrCipModemPortDNISAuthTime  OBJECT-TYPE
         SYNTAX INTEGER
         {
             before-answer (1),
             after-answer (2)
         }
         ACCESS write-only
         STATUS  mandatory
         DESCRIPTION
             "DNIS Authentication Time"
         --CONFIGURABLE
         ::= { usrCipModemPortParamEntry 23 }
 
    usrCipModemPortDNISAuthType  OBJECT-TYPE
         SYNTAX INTEGER
         {
             dnis (1),
             ani (2)
         }
         ACCESS write-only
         STATUS  mandatory
         DESCRIPTION
             "DNIS Authentication type"
         --CONFIGURABLE
         ::= { usrCipModemPortParamEntry 24 }

     usrCipModemPortDNISPassword OBJECT-TYPE
          SYNTAX      OCTET STRING (SIZE(0..15))
   	  ACCESS    write-only
   	  STATUS      mandatory
   	  DESCRIPTION "The DNIS  password."
        --CONFIGURABLE
         ::= { usrCipModemPortParamEntry 25 }


     usrCipModemPortDNISTimeout OBJECT-TYPE
          SYNTAX      INTEGER
          ACCESS      write-only
          STATUS      mandatory
          DESCRIPTION "Timeout if no auth within this time"
        --CONFIGURABLE
     ::= {usrCipModemPortParamEntry 26}

    usrCipModemPortParity  OBJECT-TYPE
         SYNTAX INTEGER       
         {      
			no-parity-eight-bit (1),
			even-seven-bit (2),  
			odd-seven-bit (3),  
			no-parity-seven-bit (4)
         }
         ACCESS  write-only
         STATUS  mandatory
         DESCRIPTION
             "Port Parity"
         --CONFIGURABLE
         ::= { usrCipModemPortParamEntry 27 }

    usrCipModemPromptDelay  OBJECT-TYPE
         SYNTAX INTEGER (0..100)
         ACCESS   write-only
         STATUS  mandatory
         DESCRIPTION
             "If user does not enter any key after banner mesg, authenticate
              user based on interface user name after this delay"
         --CONFIGURABLE 
         ::= { usrCipModemPortParamEntry 28 }


    usrCipModemPromptTimeout  OBJECT-TYPE
         SYNTAX INTEGER (5..600)
         ACCESS write-only
         STATUS  mandatory
         DESCRIPTION
             " This is the maximum timeout while prompting for 
				username password. If nothing is typed, the session will
				be terminated. Default is 300 secs"
         --CONFIGURABLE
         ::= { usrCipModemPortParamEntry 29 }


      usrCipModemSpecialXonXoffFlow  OBJECT-TYPE
         SYNTAX INTEGER       
         {      
             disbaled (0),
             enabled (1)
         }
         ACCESS write-only
         STATUS  mandatory
         DESCRIPTION
             "Specail Xon Xoff flow control in modem control receive side"
         --CONFIGURABLE
         ::= { usrCipModemPortParamEntry 30 }

	 usrCipModemUseDnisPool OBJECT-TYPE
         SYNTAX INTEGER 
		 {
             dnis-pool-disabled (1),
             dnis-pool-preferred (2),
             dnis-pool-required (3)
         }
         ACCESS write-only
         STATUS  mandatory
         DESCRIPTION
             "User DNIS pool"
         --CONFIGURABLE
     ::= { usrCipModemPortParamEntry 31 }

	 usrCipModemLoginTable OBJECT-TYPE
         SYNTAX OCTET STRING
         ACCESS  read-write
         STATUS  mandatory
         DESCRIPTION
             "Login Host Table "
         --CONFIGURABLE
     ::= { usrCipModemPortParamEntry 32 }

    usrCipModemLCPKeepAlive  OBJECT-TYPE
         SYNTAX INTEGER (0..5000)
         ACCESS      write-only
         STATUS  mandatory
         DESCRIPTION
             " This is the LCP keep alive timer interval for PPP" 
         --CONFIGURABLE
         ::= { usrCipModemPortParamEntry 33 }

     usrCipModemPortPasswordPrompt OBJECT-TYPE
          SYNTAX      OCTET STRING (SIZE(0..64))
          ACCESS      write-only
          STATUS      mandatory
          DESCRIPTION "The login Password prompt associated with a specific port."
     ::= {usrCipModemPortParamEntry 34}

     usrCipConfigFileName OBJECT-TYPE
         SYNTAX OCTET STRING (SIZE(0..64))
         ACCESS read-only
         STATUS mandatory
         DESCRIPTION
           "The name of a ConfigFile to read/write permanent database
            records. If the value of this object is an empty string,
            then the default name `@file://CallInitProcess.cfg' is
            used."
     ::= { usrCip 25 }

-- Modem Group Interface Table

      usrCipModemGroupInterfaceTable OBJECT-TYPE
         SYNTAX  SEQUENCE OF USRCIPModemGroupInterfaceEntry 
         ACCESS  not-accessible
         STATUS  mandatory
         DESCRIPTION
            "This table contains the list of interfaces that belong to 
             a particular modem group."
      ::= { usrCip 26 }

     usrCipModemGroupInterfaceEntry OBJECT-TYPE
        SYNTAX      USRCIPModemGroupInterfaceEntry
        ACCESS      not-accessible
        STATUS      mandatory
        DESCRIPTION "Each entry corresponds to a serial interface."
        INDEX   {
                usrCipModemGroupInterfaceGroupName,
                usrCipModemGroupInterfaceName
               }
     ::= {usrCipModemGroupInterfaceTable 1}

     USRCIPModemGroupInterfaceEntry ::= 
          SEQUENCE {
               usrCipModemGroupInterfaceName
                    DisplayString,
               usrCipModemGroupInterfaceStatus
                    INTEGER,
               usrCipModemGroupInterfaceGroupName
                    DisplayString
          }

     usrCipModemGroupInterfaceGroupName OBJECT-TYPE
          SYNTAX        DisplayString
          ACCESS        not-accessible
          STATUS        mandatory
          DESCRIPTION   "Group name that this interface belongs to."
     ::= { usrCipModemGroupInterfaceEntry 1 }

     usrCipModemGroupInterfaceName OBJECT-TYPE
          SYNTAX        DisplayString 
          ACCESS        not-accessible
          STATUS        mandatory
          DESCRIPTION   "The identifier of a modem group."
     --CONFIGURABLE
     ::= { usrCipModemGroupInterfaceEntry 2 }

     usrCipModemGroupInterfaceStatus  OBJECT-TYPE
        SYNTAX          INTEGER {
                                add(0),
                                delete(1),
                                active(2),
                                inactive(3)
                                }
        ACCESS         	read-write
        STATUS          mandatory
        DESCRIPTION     "The status could be add or delete the group member
                         specified in the usrCipGroupMembers MIB."
      --CONFIGURABLE
     ::= { usrCipModemGroupInterfaceEntry 3 }


     usrCipGlobalCallType  OBJECT-TYPE
           SYNTAX          INTEGER { pptp(1),l2tp(3),none(2) }
           ACCESS          read-write
           STATUS          mandatory
           DESCRIPTION
              " Global Call Type determiner . "
           --CONFIGURABLE
           ::= { usrCip 27 }

     usrCipSingleLevelPrompting OBJECT-TYPE
        SYNTAX  INTEGER {
            disabled(0),
            enabled(1)
        }
        ACCESS  read-write
        STATUS mandatory
        DESCRIPTION
           "If enabled, Login/Network users are presented with the HiPer
           prompt, by-passing the initial Login/Network prompt (def: disabled)."
        --CONFIGURABLE
     ::= { usrCip 28 }

   usrCipCfmChatScriptFlag OBJECT-TYPE
        SYNTAX          INTEGER
        ACCESS          read-write
        STATUS          mandatory
        DESCRIPTION     "This flag triggers a save of chat script table."
    ::= { usrCip 29 }
 
    usrCipChatScriptTable OBJECT-TYPE
         SYNTAX  SEQUENCE OF USRCIPChatScriptEntry
         ACCESS  not-accessible
         STATUS  mandatory
         DESCRIPTION
            "This table contains the chatscript names."
    ::= { usrCip 30 }
 
    usrCIPChatScriptEntry OBJECT-TYPE
        SYNTAX      USRCIPChatScriptEntry
        ACCESS      not-accessible
        STATUS      mandatory
        DESCRIPTION "Each entry corresponds to a chat script."
        INDEX   { usrCipChatScriptName }
     ::= {usrCipChatScriptTable 1}
 
    USRCIPChatScriptEntry ::=
          SEQUENCE {
               usrCipChatScriptName
                    OCTET STRING,
               usrCipChatScriptStatus
                    INTEGER,
               usrCipChatScriptString
                    OCTET STRING
    }
 
   usrCipChatScriptName OBJECT-TYPE
         SYNTAX  OCTET STRING
         ACCESS  not-accessible
         STATUS  mandatory
         DESCRIPTION
            "The character name for this chatscript."
    ::= { usrCIPChatScriptEntry 1 }
 
    usrCipChatScriptStatus OBJECT-TYPE
         SYNTAX  INTEGER {
                         add(1),
                         delete(2),
                         verify(3),
                         normal(4),       -- Chat Script reading in progress
                         reading(5),     -- Chat Script reading in progress
                         verifyFailed(6),  -- Chat Script verification failed
                         starting(7),       -- Chat Script operation starting
                         verifying(8)       -- Chat script verification in progress
                         }
         ACCESS  read-write
         STATUS  mandatory
         DESCRIPTION
            "The status of this chatscript entry. Valid row entries in this
             table have the status field set to normal. The settable values
             are normal and delete. If the instance is in the table and the
             status is starting/reading, this will be an add operation."
         --CONFIGURABLE
     ::= { usrCIPChatScriptEntry 2 }
 
    usrCipChatScriptString OBJECT-TYPE
         SYNTAX  OCTET STRING
         ACCESS  read-only
         STATUS  mandatory
         DESCRIPTION
            "Chat script buffer"
    ::= { usrCIPChatScriptEntry 3 }
 
    usrCipDNISAuthFlag  OBJECT-TYPE
         SYNTAX  INTEGER {
                 disabled(0),
                 enabled(1)
             }
         ACCESS  read-write
         STATUS  mandatory
         DESCRIPTION
             "This is the switch to enable/disable DNIS based
              call-authorization"
         --CONFIGURABLE
         ::= { usrCip 31 }

    usrCipDNISAuthPassword  OBJECT-TYPE
         SYNTAX  OCTET STRING
         ACCESS  read-write
         STATUS  mandatory
         DESCRIPTION
             "This is the Password for the DNIS authorization request being sent out"
         --CONFIGURABLE
         ::= { usrCip 32 }

 
    usrCipBannerFileName  OBJECT-TYPE
         SYNTAX  OCTET STRING
         ACCESS  read-write
         STATUS  mandatory
         DESCRIPTION
             "This is file name for port banner file"
         --CONFIGURABLE
         ::= { usrCip 33 }
    
    usrCipAutoAnswerFlag  OBJECT-TYPE
         SYNTAX  INTEGER {
                 disabled(0),
                 enabled(1)
             }
         ACCESS  read-write
         STATUS  mandatory
         DESCRIPTION
             "This is the switch to enable/disable the Auto Answering of
              Modem-Sharing-Dialout Calls"
         --CONFIGURABLE
         ::= { usrCip 34 }

    usrSlotUtilizationTable OBJECT-TYPE
         SYNTAX  SEQUENCE OF USRSlotUtilizationEntry
         ACCESS  not-accessible
         STATUS  mandatory
         DESCRIPTION
            "This table contains the chatscript names."
    ::= { usrCip 35 }
 
    usrSlotUtilizationEntry OBJECT-TYPE
        SYNTAX      USRSlotUtilizationEntry
        ACCESS      not-accessible
        STATUS      mandatory
        DESCRIPTION "Each entry corresponds to a chat script."
        INDEX   { usrSlotIndex }
     ::= {usrSlotUtilizationTable 1}
 
    USRSlotUtilizationEntry ::=
          SEQUENCE {
               usrSlotIndex
                    INTEGER,
               usrSlotId
                    INTEGER,
               usrSlotActiveCalls
                    INTEGER,
               usrSlotNumberOfPorts
                    INTEGER,
               usrSlotUtilization
                    INTEGER
    }
 
   usrSlotIndex OBJECT-TYPE
         SYNTAX  INTEGER
         ACCESS  not-accessible
         STATUS  mandatory
         DESCRIPTION
            "The slot index."
    ::= { usrSlotUtilizationEntry 1 }
 
   usrSlotId OBJECT-TYPE
         SYNTAX  INTEGER
         ACCESS  read-only
         STATUS  mandatory
         DESCRIPTION
            "The slot number in human readable format where proper offset is computed." 
    ::= { usrSlotUtilizationEntry 2 }
 
   usrSlotActiveCalls OBJECT-TYPE
         SYNTAX  INTEGER
         ACCESS  read-only
         STATUS  mandatory
         DESCRIPTION
            "The number of active calls on that slot at that instant." 
    ::= { usrSlotUtilizationEntry 3 }
 
   usrSlotNumberOfPorts OBJECT-TYPE
         SYNTAX  INTEGER
         ACCESS  read-only
         STATUS  mandatory
         DESCRIPTION
            "The number of ports on that slot."
    ::= { usrSlotUtilizationEntry 4 }
 
   usrSlotUtilization OBJECT-TYPE
         SYNTAX  INTEGER
         ACCESS  read-only
         STATUS  mandatory
         DESCRIPTION
            "The percent utilization of that slot. This is computed as number of active calls on that slot divided by the number of ports on that slot."
    ::= { usrSlotUtilizationEntry 5 }
 
    usrCipTotalCalls  OBJECT-TYPE
         SYNTAX  INTEGER 
         ACCESS  read-only
         STATUS  mandatory
         DESCRIPTION
             "Total number of calls on the chassis."
         ::= { usrCip 36 }

    usrCipTotalAvailablePorts  OBJECT-TYPE
         SYNTAX  INTEGER 
         ACCESS  read-only
         STATUS  mandatory
         DESCRIPTION
             "Total number of ports on the chassis."
         ::= { usrCip 37 }

    usrCipTotalChassisUtilization  OBJECT-TYPE
         SYNTAX  INTEGER 
         ACCESS  read-only
         STATUS  mandatory
         DESCRIPTION
             "Percent utilization of all ports on the chassis."
         ::= { usrCip 38 }

    usrCipCallsInLast24Hours  OBJECT-TYPE
         SYNTAX  INTEGER 
         ACCESS  read-only
         STATUS  mandatory
         DESCRIPTION
             "The number of calls in last 24 hours."
         ::= { usrCip 39 }


    usrCipDialinAccessManageUser  OBJECT-TYPE
         SYNTAX  INTEGER {
            disabled(2),
            enabled(1)
         }
         ACCESS  read-write
         STATUS  mandatory
         DESCRIPTION
             "No Manage user dialin access"
		--CONFIGURABLE
         ::= { usrCip 40 }

-- CIP login table definition. An interface pointing to this table
-- use the login host ip address and login port from the table.

   usrCipCfmLoginTableFlag OBJECT-TYPE
        SYNTAX          INTEGER
        ACCESS          read-write
        STATUS          mandatory
        DESCRIPTION     "This flag triggers a save of cip login table."  
    ::= { usrCip 69 }
 
    usrCipLoginTable OBJECT-TYPE
    SYNTAX SEQUENCE OF UsrCipLoginEntry
    ACCESS  not-accessible
    STATUS  mandatory
    DESCRIPTION
        ""
    ::= { usrCip 70 }

    usrCipLoginEntry    OBJECT-TYPE
    SYNTAX  UsrCipLoginEntry
    ACCESS  not-accessible
    STATUS  mandatory
    DESCRIPTION
        ""
   INDEX  { usrCipLoginListName, usrCipLoginPref }
	   ::= { usrCipLoginTable 1 }

	UsrCipLoginEntry ::=
	SEQUENCE {
		usrCipLoginListName
		OCTET STRING,
		usrCipLoginPref
		INTEGER,
		usrCipLoginIpAddress	
		IpAddress,
		usrCipLoginPort
		INTEGER,
		usrCipLoginListNameForPrint
		OCTET STRING,
		usrCipLoginEntryDelete
        INTEGER
	} 
	usrCipLoginListName  OBJECT-TYPE
         SYNTAX  OCTET STRING (SIZE(0..9))
         ACCESS  not-accessible
         STATUS  mandatory
         DESCRIPTION
             "This is the cip login list name"
         ::= { usrCipLoginEntry 1 }

    usrCipLoginPref  OBJECT-TYPE
    SYNTAX  INTEGER
    ACCESS  not-accessible 
    STATUS  mandatory
    DESCRIPTION
        "login preference index"
    ::= { usrCipLoginEntry 2 }

	usrCipLoginIpAddress  OBJECT-TYPE
         SYNTAX  IpAddress
         ACCESS  read-write
         STATUS  mandatory
         DESCRIPTION
             "This is the cip login host ip address"
     --CONFIGURABLE
         ::= { usrCipLoginEntry 3 }

	usrCipLoginPort  OBJECT-TYPE
         SYNTAX  INTEGER
         ACCESS  read-write
         STATUS  mandatory
         DESCRIPTION
             "This is the cip login host port"
     --CONFIGURABLE
         ::= { usrCipLoginEntry 4 }
	
	usrCipLoginListNameForPrint  OBJECT-TYPE
         SYNTAX  OCTET STRING (SIZE(0..9))
         ACCESS  read-write
         STATUS  mandatory
         DESCRIPTION
             "This is the cip login list name. Added the second mib to print
			 the login table name. The first mib is an index to table"
     --CONFIGURABLE
         ::= { usrCipLoginEntry 5 }

	usrCipLoginEntryDelete  OBJECT-TYPE
         SYNTAX  INTEGER
         ACCESS  write-only
         STATUS  mandatory
         DESCRIPTION
             "Setting this entry will delete the particular table"
         ::= { usrCipLoginEntry 6 }
	

	usrCipModemUtilizationStatisticsTable OBJECT-TYPE  
           SYNTAX     SEQUENCE OF USRCIPModemUtilizationStatisticsEntry
           ACCESS not-accessible
           STATUS     mandatory
           DESCRIPTION
             "The active calls during every hour gives 24 samples."
           ::= { usrCip 41 }

    usrCipModemUtilizationStatisticsEntry OBJECT-TYPE  
           SYNTAX     USRCIPModemUtilizationStatisticsEntry
           ACCESS not-accessible
           STATUS     mandatory
           DESCRIPTION
                "CIP PPP Modem Utilizationstatistics"
           INDEX      { usrCipModemUtilizationStatisticsIndex }
           ::= { usrCipModemUtilizationStatisticsTable 1 }

    USRCIPModemUtilizationStatisticsEntry ::= SEQUENCE {
           usrCipModemUtilizationStatisticsIndex            INTEGER,
           usrCipModemUtilization                          Counter32,
           usrCipCallsPerHour                              Counter32,
           usrCipPacketsForwadedPerHour                    Counter32
        }

    usrCipModemUtilizationStatisticsIndex OBJECT-TYPE
           SYNTAX     INTEGER
           ACCESS not-accessible
           STATUS     mandatory
           DESCRIPTION
                 "The index for the call duration samples."
           ::= { usrCipModemUtilizationStatisticsEntry 1 }

    usrCipModemUtilization OBJECT-TYPE
           SYNTAX     Counter32   
           ACCESS read-only
           STATUS     mandatory 
           DESCRIPTION
                 "The  percentage utilization of the modems per hour."
           ::= { usrCipModemUtilizationStatisticsEntry 2 }

    usrCipCallsPerHour OBJECT-TYPE
           SYNTAX     Counter32   
           ACCESS read-only
           STATUS     mandatory 
           DESCRIPTION
                 "The  number of calls per hour."
           ::= { usrCipModemUtilizationStatisticsEntry 3 }

    usrCipPacketsForwadedPerHour OBJECT-TYPE
           SYNTAX     Counter32   
           ACCESS read-only
           STATUS     mandatory 
           DESCRIPTION
                 "The  number of packets forwarded per hour."
           ::= { usrCipModemUtilizationStatisticsEntry 4 }

	usrCipCallStatisticsTable OBJECT-TYPE
           SYNTAX     SEQUENCE OF USRCIPCallStatisticsEntry
           ACCESS  not-accessible
           STATUS     mandatory
           DESCRIPTION
                 "The  table listing the Cip Call statistics
                  for all the calls coming in."
           ::= { usrCip 42 }

    usrCipCallStatisticsEntry OBJECT-TYPE
           SYNTAX     USRCIPCallStatisticsEntry
           ACCESS not-accessible
           STATUS     mandatory
           DESCRIPTION
				"CIP Call statistics"
           INDEX      { usrCipCallStatisticsIndex }
           ::= { usrCipCallStatisticsTable 1 }

    USRCIPCallStatisticsEntry ::= SEQUENCE {
           usrCipCallStatisticsIndex                        INTEGER,
           usrCipCallStatisticsOnDemandConns                Counter32,
           usrCipCallStatisticsContinuousConns              Counter32,
           usrCipCallStatisticsDialBackConns                Counter32,
           usrCipCallStatisticsManualConns                  Counter32,
           usrCipCallStatisticsTimedConns                   Counter32,
           usrCipCallStatisticsSharedConns                  Counter32,
           usrCipCallStatisticsDialInConns                  Counter32,
           usrCipCallStatisticsBondConns                    Counter32,
           usrCipCallStatisticsDedicatedConns               Counter32,
           usrCipCallStatisticsAnalogCalls                  Counter32,
           usrCipCallStatisticsIsdnCalls                    Counter32,
           usrCipCallStatisticsDialInUsers                  Counter32,
           usrCipCallStatisticsNetworkUsers                 Counter32,
           usrCipCallStatisticsCounterResetTime             OCTET STRING 
     }


    usrCipCallStatisticsIndex OBJECT-TYPE
           SYNTAX     INTEGER
           ACCESS not-accessible
           STATUS     mandatory
           DESCRIPTION
                 "The index for the call statistics display.
                  they are 0-now, 1-max, 2-today & 3-total."
           ::= { usrCipCallStatisticsEntry 1 }

	usrCipCallStatisticsOnDemandConns OBJECT-TYPE
           SYNTAX     Counter32
           ACCESS read-only
           STATUS     mandatory
           DESCRIPTION
                 "The number of On Demand connections."
           ::= { usrCipCallStatisticsEntry 2 }

	usrCipCallStatisticsContinuousConns OBJECT-TYPE
           SYNTAX     Counter32
           ACCESS read-only
           STATUS     mandatory
           DESCRIPTION
                 "The number of Continuous  connections."
           ::= { usrCipCallStatisticsEntry 3 }

	usrCipCallStatisticsDialBackConns OBJECT-TYPE
           SYNTAX     Counter32
           ACCESS read-only
           STATUS     mandatory
           DESCRIPTION
                 "The number of Dial back connections."
           ::= { usrCipCallStatisticsEntry 4 }

	usrCipCallStatisticsManualConns OBJECT-TYPE
           SYNTAX     Counter32
           ACCESS read-only
           STATUS     mandatory
           DESCRIPTION
                 "The number of manual connections."
           ::= { usrCipCallStatisticsEntry 5 }

	usrCipCallStatisticsTimedConns OBJECT-TYPE
           SYNTAX     Counter32
           ACCESS read-only
           STATUS     mandatory
           DESCRIPTION
                 "The number of Timed connections."
           ::= { usrCipCallStatisticsEntry 6 }

	usrCipCallStatisticsSharedConns OBJECT-TYPE
           SYNTAX     Counter32
           ACCESS read-only
           STATUS     mandatory
           DESCRIPTION
                 "The number of Shared connections."
           ::= { usrCipCallStatisticsEntry 7 }

	usrCipCallStatisticsDialInConns OBJECT-TYPE
           SYNTAX     Counter32
           ACCESS read-only
           STATUS     mandatory
           DESCRIPTION
                 "The number of Dial-In connections."
           ::= { usrCipCallStatisticsEntry 8 }

	usrCipCallStatisticsBondConns OBJECT-TYPE
           SYNTAX     Counter32
           ACCESS read-only
           STATUS     mandatory
           DESCRIPTION
                 "The number of Bond connections."
           ::= { usrCipCallStatisticsEntry 9 }

	usrCipCallStatisticsDedicatedConns OBJECT-TYPE
           SYNTAX     Counter32
           ACCESS read-only
           STATUS     mandatory
           DESCRIPTION
                 "The number of Dedicated connections."
           ::= { usrCipCallStatisticsEntry 10 }

	usrCipCallStatisticsAnalogCalls OBJECT-TYPE
           SYNTAX     Counter32
           ACCESS read-only
           STATUS     mandatory
           DESCRIPTION
                 "The number of analog calls."
           ::= { usrCipCallStatisticsEntry 11 }

	usrCipCallStatisticsIsdnCalls OBJECT-TYPE
           SYNTAX     Counter32
           ACCESS read-only
           STATUS     mandatory
           DESCRIPTION
                 "The number of digital calls."
           ::= { usrCipCallStatisticsEntry 12 }

	usrCipCallStatisticsDialInUsers OBJECT-TYPE
           SYNTAX     Counter32
           ACCESS read-only
           STATUS     mandatory
           DESCRIPTION
                 "The number of login users."
           ::= { usrCipCallStatisticsEntry 13 }

	 usrCipCallStatisticsNetworkUsers OBJECT-TYPE
           SYNTAX     Counter32
           ACCESS read-only
           STATUS     mandatory
           DESCRIPTION
                 "The number of  Network users."
           ::= { usrCipCallStatisticsEntry 14 }

    usrCipCallStatisticsCounterResetTime	OBJECT-TYPE
			SYNTAX	OCTET STRING (SIZE (12))
			ACCESS	read-write
			STATUS	mandatory
			DESCRIPTION
				"Time the call statistics counters were last reset to value zero."
    ::= { usrCipCallStatisticsEntry 15 }

	usrCipCallDurationStatisticsTable OBJECT-TYPE
           SYNTAX     SEQUENCE OF USRCIPCallDurationStatisticsEntry
           ACCESS not-accessible
           STATUS     mandatory
           DESCRIPTION
			 "Number of calls which lasted 1, 2, 5, 10, 20, 60, 
			  120, 360, 720, 1440, 2160 and 3600 minutes & over. 
			  This gives 12 samples."
           ::= { usrCip 43 }

    usrCipCallDurationStatisticsEntry OBJECT-TYPE
           SYNTAX     USRCIPCallDurationStatisticsEntry
           ACCESS not-accessible
           STATUS     mandatory
           DESCRIPTION
                "CIP Call Duration statistics"
           INDEX      { usrCipCallDurationStatisticsIndex }
           ::= { usrCipCallDurationStatisticsTable 1 }

    USRCIPCallDurationStatisticsEntry ::= SEQUENCE {
           usrCipCallDurationStatisticsIndex            INTEGER,
           usrCipCallDurations                          Counter32
        }

    usrCipCallDurationStatisticsIndex OBJECT-TYPE
           SYNTAX     INTEGER
           ACCESS not-accessible
           STATUS     mandatory
           DESCRIPTION
                 "The index for the call duration samples."
           ::= { usrCipCallDurationStatisticsEntry 1 }


    usrCipCallDurations OBJECT-TYPE
           SYNTAX     Counter32 
           ACCESS read-only
           STATUS     mandatory 
           DESCRIPTION
                 "The  number of calls for each samples."
           ::= { usrCipCallDurationStatisticsEntry 2 }

	usrCipPPPCompressionStatisticsTable OBJECT-TYPE
           SYNTAX     SEQUENCE OF USRCIPPPPCompressionStatisticsEntry
           ACCESS not-accessible
           STATUS     mandatory
           DESCRIPTION
                 "The  table listing the Cip PPP Compression statistics
                  for all the calls coming in."
           ::= { usrCip 44 }

    usrCipPPPCompressionStatisticsEntry OBJECT-TYPE
           SYNTAX     USRCIPPPPCompressionStatisticsEntry
           ACCESS not-accessible
           STATUS     mandatory
           DESCRIPTION
                "CIP PPPCompression statistics"
           INDEX      { usrCipPPPCompressionStatisticsIndex }
           ::= { usrCipPPPCompressionStatisticsTable 1 }

    USRCIPPPPCompressionStatisticsEntry ::= SEQUENCE {
           usrCipPPPCompressionStatisticsIndex                        INTEGER,
           usrCipPPPCompressionStatisticsMicrosoftComp                Counter32,
           usrCipPPPCompressionStatisticsAscendComp                   Counter32,
           usrCipPPPCompressionStatisticsStackComp                    Counter32,
           usrCipPPPCompressionStatisticsPPPUsers                     Counter32,
           usrCipPPPCompressionStatisticsPPPBundlesFormed             Counter32,
           usrCipPPPCompressionStatisticsMrruNegotiated               Counter32,
           usrCipPPPCompressionStatisticsIPXNegotiated                Counter32,
           usrCipPPPCompressionStatisticsIPNegotiated                 Counter32,
           usrCipPPPCompressionStatisticsVJCompression                Counter32,
           usrCipPPPCompressionStatisticsBACPNegotiated               Counter32,
           usrCipPPPCompressionStatisticsCHAPAuthenticated            Counter32,
           usrCipPPPCompressionStatisticsPAPAuthenticated             Counter32,
           usrCipPPPCompressionStatisticsMSCHAPAuthenticated          Counter32,
           usrCipPPPCompressionStatisticsEAPAuthenticated             Counter32,
           usrCipPPPCompressionStatisticsResetTime                 OCTET STRING, 
           usrCipPPPCompressionStatisticsDeflateComp                  Counter32
	}

	usrCipPPPCompressionStatisticsIndex OBJECT-TYPE
           SYNTAX     INTEGER
           ACCESS not-accessible
           STATUS     mandatory
           DESCRIPTION
                 "The index for the PPPCompression statistics display."
           ::= { usrCipPPPCompressionStatisticsEntry 1 }

    usrCipPPPCompressionStatisticsMicrosoftComp OBJECT-TYPE
           SYNTAX     Counter32
           ACCESS read-only
           STATUS     mandatory
           DESCRIPTION
                 "The number of calls uses microsoft compression."
           ::= { usrCipPPPCompressionStatisticsEntry 2 }

    usrCipPPPCompressionStatisticsAscendComp OBJECT-TYPE
           SYNTAX     Counter32
           ACCESS read-only
           STATUS     mandatory
           DESCRIPTION
                 "The number of calls uses ascend compression.."
           ::= { usrCipPPPCompressionStatisticsEntry 3 }

    usrCipPPPCompressionStatisticsStackComp OBJECT-TYPE
           SYNTAX     Counter32
           ACCESS read-only
           STATUS     mandatory
           DESCRIPTION
                 "The number of calls uses stack compression.."
           ::= { usrCipPPPCompressionStatisticsEntry 4 }

    usrCipPPPCompressionStatisticsPPPUsers OBJECT-TYPE
           SYNTAX     Counter32
           ACCESS read-only
           STATUS     mandatory
           DESCRIPTION
                 "The number of PPP users.."
           ::= { usrCipPPPCompressionStatisticsEntry 5 }

    usrCipPPPCompressionStatisticsPPPBundlesFormed OBJECT-TYPE
           SYNTAX     Counter32
           ACCESS read-only
           STATUS     mandatory
           DESCRIPTION
                 "The number of PPP Bundles formed.."
           ::= { usrCipPPPCompressionStatisticsEntry 6 }
		   
    usrCipPPPCompressionStatisticsMrruNegotiated OBJECT-TYPE
           SYNTAX     Counter32
           ACCESS read-only
           STATUS     mandatory
           DESCRIPTION
                 "The number of calls negotiated MRRU for making a multi-link.."
           ::= { usrCipPPPCompressionStatisticsEntry 7 }
		   
    usrCipPPPCompressionStatisticsIPXNegotiated OBJECT-TYPE
           SYNTAX     Counter32
           ACCESS read-only
           STATUS     mandatory
           DESCRIPTION
                 "The number of calls negotiated IPX."
           ::= { usrCipPPPCompressionStatisticsEntry 8 }
		   
    usrCipPPPCompressionStatisticsIPNegotiated OBJECT-TYPE
           SYNTAX     Counter32
           ACCESS read-only
           STATUS     mandatory
           DESCRIPTION
                 "The number of calls negotiated IP."
           ::= { usrCipPPPCompressionStatisticsEntry 9 }
		   
    usrCipPPPCompressionStatisticsVJCompression OBJECT-TYPE
           SYNTAX     Counter32
           ACCESS read-only
           STATUS     mandatory
           DESCRIPTION
                 "The number of calls negotiated VJ Compression"
           ::= { usrCipPPPCompressionStatisticsEntry 10 }
		   
    usrCipPPPCompressionStatisticsBACPNegotiated OBJECT-TYPE
           SYNTAX     Counter32
           ACCESS read-only
           STATUS     mandatory
           DESCRIPTION
                 "The number of calls negotiated BAP."
           ::= { usrCipPPPCompressionStatisticsEntry 11 }
		   
    usrCipPPPCompressionStatisticsCHAPAuthenticated OBJECT-TYPE
           SYNTAX     Counter32
           ACCESS read-only
           STATUS     mandatory
           DESCRIPTION
                 "The number of calls authenticated using CHAP."
           ::= { usrCipPPPCompressionStatisticsEntry 12 }
		   
    usrCipPPPCompressionStatisticsPAPAuthenticated OBJECT-TYPE
           SYNTAX     Counter32
           ACCESS read-only
           STATUS     mandatory
           DESCRIPTION
                 "The number of calls authenticated using PAP."
           ::= { usrCipPPPCompressionStatisticsEntry 13 }
		   
    usrCipPPPCompressionStatisticsMSCHAPAuthenticated OBJECT-TYPE
           SYNTAX     Counter32
           ACCESS read-only
           STATUS     mandatory
           DESCRIPTION
                 "The number of calls authenticated using MSCHAP."
           ::= { usrCipPPPCompressionStatisticsEntry 14 }

    usrCipPPPCompressionStatisticsEAPAuthenticated OBJECT-TYPE
           SYNTAX     Counter32
           ACCESS read-only
           STATUS     mandatory
           DESCRIPTION
                 "The number of calls authenticated using EAP."
           ::= { usrCipPPPCompressionStatisticsEntry 15 }

    usrCipPPPCompressionStatisticsResetTime	OBJECT-TYPE
			SYNTAX	OCTET STRING (SIZE (12))
			ACCESS	read-write
			STATUS	mandatory
			DESCRIPTION
				"Time the PPP statistics counters were last reset to value zero."
    ::= { usrCipPPPCompressionStatisticsEntry 16 }

    usrCipPPPCompressionStatisticsDeflateComp OBJECT-TYPE
           SYNTAX     Counter32
           ACCESS read-only
           STATUS     mandatory
           DESCRIPTION
                 "The number of calls uses Deflate compression.."
           ::= { usrCipPPPCompressionStatisticsEntry 17 }

		
	usrCipSpeedStatisticsTable OBJECT-TYPE
           SYNTAX     SEQUENCE OF USRCIPSpeedStatisticsEntry
           ACCESS not-accessible
           STATUS     mandatory
           DESCRIPTION
                 "The  table listing the CIP Speed statistics
                  for all the calls coming in."
           ::= { usrCip 45 }
   
    usrCipSpeedStatisticsEntry OBJECT-TYPE
           SYNTAX     USRCIPSpeedStatisticsEntry
           ACCESS not-accessible
           STATUS     mandatory
           DESCRIPTION
                "CIP Speed statistics of the incoming calls."
           INDEX      { usrCipSpeedStatisticsIndex }
           ::= { usrCipSpeedStatisticsTable 1 }
   
    USRCIPSpeedStatisticsEntry ::= SEQUENCE {
           usrCipSpeedStatisticsIndex                       INTEGER,
           usrCipSpeedStatisticsSpeed300                   Counter32,
           usrCipSpeedStatisticsSpeed1200                  Counter32,
           usrCipSpeedStatisticsSpeed2400                  Counter32,
           usrCipSpeedStatisticsSpeed4800                   Counter32,
           usrCipSpeedStatisticsSpeed7200                   Counter32,
           usrCipSpeedStatisticsSpeed9600                   Counter32,
           usrCipSpeedStatisticsSpeed12000                   Counter32,
           usrCipSpeedStatisticsSpeed14400                   Counter32,
           usrCipSpeedStatisticsSpeed16800                   Counter32,
           usrCipSpeedStatisticsSpeed19200                   Counter32,
           usrCipSpeedStatisticsSpeed21600                   Counter32,
           usrCipSpeedStatisticsSpeed28800                   Counter32,
           usrCipSpeedStatisticsSpeed38400                   Counter32,
           usrCipSpeedStatisticsSpeed57600                   Counter32,
           usrCipSpeedStatisticsSpeed115200                  Counter32,
           usrCipSpeedStatisticsSpeed288000                  Counter32,
           usrCipSpeedStatisticsSpeed751200                  Counter32,
           usrCipSpeedStatisticsSpeed120075                  Counter32,
           usrCipSpeedStatisticsSpeed24000                  Counter32,
           usrCipSpeedStatisticsSpeed26400                  Counter32,
           usrCipSpeedStatisticsSpeed31200                  Counter32,
           usrCipSpeedStatisticsSpeed33600                  Counter32,
           usrCipSpeedStatisticsSpeed32000                  Counter32,
           usrCipSpeedStatisticsSpeed36000                  Counter32,
           usrCipSpeedStatisticsSpeed40000                  Counter32,
           usrCipSpeedStatisticsSpeed44000                  Counter32,
           usrCipSpeedStatisticsSpeed48000                  Counter32,
           usrCipSpeedStatisticsSpeed49333                  Counter32,
           usrCipSpeedStatisticsSpeed50666                  Counter32,
           usrCipSpeedStatisticsSpeed52000                  Counter32,
           usrCipSpeedStatisticsSpeed53333                  Counter32,
           usrCipSpeedStatisticsSpeed54666                  Counter32,
           usrCipSpeedStatisticsSpeed56000                  Counter32,
           usrCipSpeedStatisticsSpeed57333                  Counter32,
           usrCipSpeedStatisticsSpeed58666                  Counter32,
           usrCipSpeedStatisticsSpeed60000                  Counter32,
           usrCipSpeedStatisticsSpeed61333                  Counter32,
           usrCipSpeedStatisticsSpeed64000                  Counter32,
           usrCipSpeedStatisticsResetTime                 OCTET STRING 
    }
   
    usrCipSpeedStatisticsIndex OBJECT-TYPE
           SYNTAX     INTEGER
           ACCESS not-accessible
           STATUS     mandatory
           DESCRIPTION
                 "The index for the speed statistics display.
                  they are 0-now & 1--total."
           ::= { usrCipSpeedStatisticsEntry 1 }

   
    usrCipSpeedStatisticsSpeed300 OBJECT-TYPE
           SYNTAX     Counter32
           ACCESS read-only
           STATUS     mandatory
           DESCRIPTION
                 "The number of calls with speed of 300."
           ::= { usrCipSpeedStatisticsEntry 2 }
   
    usrCipSpeedStatisticsSpeed1200 OBJECT-TYPE
           SYNTAX     Counter32
           ACCESS read-only
           STATUS     mandatory
           DESCRIPTION
                 "The number of calls with speed of 1200."
           ::= { usrCipSpeedStatisticsEntry 3 }
   
    usrCipSpeedStatisticsSpeed2400 OBJECT-TYPE
           SYNTAX     Counter32
           ACCESS read-only
           STATUS     mandatory
           DESCRIPTION
                 "The number of calls with speed of 2400."
           ::= { usrCipSpeedStatisticsEntry 4 }
   
    usrCipSpeedStatisticsSpeed4800 OBJECT-TYPE
           SYNTAX     Counter32
           ACCESS read-only
           STATUS     mandatory
           DESCRIPTION
                 "The number of calls with speed of 4800."
           ::= { usrCipSpeedStatisticsEntry 5 }
   
    usrCipSpeedStatisticsSpeed7200 OBJECT-TYPE
           SYNTAX     Counter32
           ACCESS read-only
           STATUS     mandatory
           DESCRIPTION
                 "The number of calls with speed of 7200."
           ::= { usrCipSpeedStatisticsEntry 6 }
   
    usrCipSpeedStatisticsSpeed9600 OBJECT-TYPE
           SYNTAX     Counter32
           ACCESS read-only
           STATUS     mandatory
           DESCRIPTION
                 "The number of calls with speed of 9600."
           ::= { usrCipSpeedStatisticsEntry 7 }
   
    usrCipSpeedStatisticsSpeed12000 OBJECT-TYPE
           SYNTAX     Counter32
           ACCESS read-only
           STATUS     mandatory
           DESCRIPTION
                 "The number of calls with speed of 12000."
           ::= { usrCipSpeedStatisticsEntry 8 }
   
    usrCipSpeedStatisticsSpeed14400 OBJECT-TYPE
           SYNTAX     Counter32
           ACCESS read-only
           STATUS     mandatory
           DESCRIPTION
                 "The number of calls with speed of 14400."
           ::= { usrCipSpeedStatisticsEntry 9 }
   
    usrCipSpeedStatisticsSpeed16800 OBJECT-TYPE
           SYNTAX     Counter32
           ACCESS read-only
           STATUS     mandatory
           DESCRIPTION
                 "The number of calls with speed of 16800."
           ::= { usrCipSpeedStatisticsEntry 10 }
   
    usrCipSpeedStatisticsSpeed19200 OBJECT-TYPE
           SYNTAX     Counter32
           ACCESS read-only
           STATUS     mandatory
           DESCRIPTION
                 "The number of calls with speed of 19200."
           ::= { usrCipSpeedStatisticsEntry 11 }
   
    usrCipSpeedStatisticsSpeed21600 OBJECT-TYPE
           SYNTAX     Counter32
           ACCESS read-only
           STATUS     mandatory
           DESCRIPTION
                 "The number of calls with speed of 21600."
           ::= { usrCipSpeedStatisticsEntry 12 }
   
    usrCipSpeedStatisticsSpeed28800 OBJECT-TYPE
           SYNTAX     Counter32
           ACCESS read-only
           STATUS     mandatory
           DESCRIPTION
                 "The number of calls with speed of 28800."
           ::= { usrCipSpeedStatisticsEntry 13 }
   
    usrCipSpeedStatisticsSpeed38400 OBJECT-TYPE
           SYNTAX     Counter32
           ACCESS read-only
           STATUS     mandatory
           DESCRIPTION
                 "The number of calls with speed of 38400."
           ::= { usrCipSpeedStatisticsEntry 14 }
   
    usrCipSpeedStatisticsSpeed57600 OBJECT-TYPE
           SYNTAX     Counter32
           ACCESS read-only
           STATUS     mandatory
           DESCRIPTION
                 "The number of calls with speed of 57600."
           ::= { usrCipSpeedStatisticsEntry 15 }
   
    usrCipSpeedStatisticsSpeed115200 OBJECT-TYPE
           SYNTAX     Counter32
           ACCESS read-only
           STATUS     mandatory
           DESCRIPTION
                 "The number of calls with speed of 115200."
           ::= { usrCipSpeedStatisticsEntry 16 }
   
    usrCipSpeedStatisticsSpeed288000 OBJECT-TYPE
           SYNTAX     Counter32
           ACCESS read-only
           STATUS     mandatory
           DESCRIPTION
                 "The number of calls with speed of 288000."
           ::= { usrCipSpeedStatisticsEntry 17 }
   
    usrCipSpeedStatisticsSpeed751200 OBJECT-TYPE
           SYNTAX     Counter32
           ACCESS read-only
           STATUS     mandatory
           DESCRIPTION
                 "The number of calls with speed of 75_1200."
           ::= { usrCipSpeedStatisticsEntry 18 }
   
    usrCipSpeedStatisticsSpeed120075 OBJECT-TYPE
           SYNTAX     Counter32
           ACCESS read-only
           STATUS     mandatory
           DESCRIPTION
                 "The number of calls with speed of 1200_75."
           ::= { usrCipSpeedStatisticsEntry 19 }
   
    usrCipSpeedStatisticsSpeed24000 OBJECT-TYPE
           SYNTAX     Counter32
           ACCESS read-only
           STATUS     mandatory
           DESCRIPTION
                 "The number of calls with speed of 24000."
           ::= { usrCipSpeedStatisticsEntry 20 }
   
    usrCipSpeedStatisticsSpeed26400 OBJECT-TYPE
           SYNTAX     Counter32
           ACCESS read-only
           STATUS     mandatory
           DESCRIPTION
                 "The number of calls with a speed of 26400."
           ::= { usrCipSpeedStatisticsEntry 21 }
   
    usrCipSpeedStatisticsSpeed31200 OBJECT-TYPE
           SYNTAX     Counter32
           ACCESS read-only
           STATUS     mandatory
           DESCRIPTION
                 "The number of calls with a speed of 31200."
           ::= { usrCipSpeedStatisticsEntry 22 }
   
    usrCipSpeedStatisticsSpeed33600 OBJECT-TYPE
           SYNTAX     Counter32
           ACCESS read-only
           STATUS     mandatory
           DESCRIPTION
                 "The number of calls with a speed of 33600."
           ::= { usrCipSpeedStatisticsEntry 23 }
   
    usrCipSpeedStatisticsSpeed32000 OBJECT-TYPE
           SYNTAX     Counter32
           ACCESS read-only
           STATUS     mandatory
           DESCRIPTION
                 "The number of calls with a speed of 32000."
           ::= { usrCipSpeedStatisticsEntry 24 }
   
    usrCipSpeedStatisticsSpeed36000 OBJECT-TYPE
           SYNTAX     Counter32
           ACCESS read-only
           STATUS     mandatory
           DESCRIPTION
                 "The number of calls with a speed of 36000."
           ::= { usrCipSpeedStatisticsEntry 25 }
   
    usrCipSpeedStatisticsSpeed40000 OBJECT-TYPE
           SYNTAX     Counter32
           ACCESS read-only
           STATUS     mandatory
           DESCRIPTION
                 "The number of calls with a speed of 40000."
           ::= { usrCipSpeedStatisticsEntry 26 }
   
    usrCipSpeedStatisticsSpeed44000 OBJECT-TYPE
           SYNTAX     Counter32
           ACCESS read-only
           STATUS     mandatory
           DESCRIPTION
                 "The number of calls with a speed of 44000."
           ::= { usrCipSpeedStatisticsEntry 27 }
   
    usrCipSpeedStatisticsSpeed48000 OBJECT-TYPE
           SYNTAX     Counter32
           ACCESS read-only
           STATUS     mandatory
           DESCRIPTION
                 "The number of calls with a speed of 48000."
           ::= { usrCipSpeedStatisticsEntry 28 }
   
    usrCipSpeedStatisticsSpeed49333 OBJECT-TYPE
           SYNTAX     Counter32
           ACCESS read-only
           STATUS     mandatory
           DESCRIPTION
                 "The number of calls with a speed of 49333."
           ::= { usrCipSpeedStatisticsEntry 29 }
   
    usrCipSpeedStatisticsSpeed50666 OBJECT-TYPE
           SYNTAX     Counter32
           ACCESS read-only
           STATUS     mandatory
           DESCRIPTION
                 "The number of calls with a speed of 50666."
           ::= { usrCipSpeedStatisticsEntry 30 }
   
    usrCipSpeedStatisticsSpeed52000 OBJECT-TYPE
           SYNTAX     Counter32
           ACCESS read-only
           STATUS     mandatory
           DESCRIPTION
                 "The number of calls with a speed of 52000."
           ::= { usrCipSpeedStatisticsEntry 31 }
   
    usrCipSpeedStatisticsSpeed53333 OBJECT-TYPE
           SYNTAX     Counter32
           ACCESS read-only
           STATUS     mandatory
           DESCRIPTION
                 "The number of calls with a speed of 53333."
           ::= { usrCipSpeedStatisticsEntry 32 }
   
    usrCipSpeedStatisticsSpeed54666 OBJECT-TYPE
           SYNTAX     Counter32
           ACCESS read-only
           STATUS     mandatory
           DESCRIPTION
                 "The number of calls with a speed of 54666."
           ::= { usrCipSpeedStatisticsEntry 33 }
   
    usrCipSpeedStatisticsSpeed56000 OBJECT-TYPE
           SYNTAX     Counter32
           ACCESS read-only
           STATUS     mandatory
           DESCRIPTION
                 "The number of calls with a speed of 56000."
           ::= { usrCipSpeedStatisticsEntry 34 }
   
    usrCipSpeedStatisticsSpeed57333 OBJECT-TYPE
           SYNTAX     Counter32
           ACCESS read-only
           STATUS     mandatory
           DESCRIPTION
                 "The number of calls with a speed of 57333."
           ::= { usrCipSpeedStatisticsEntry 35 }
   
    usrCipSpeedStatisticsSpeed58666 OBJECT-TYPE
           SYNTAX     Counter32
           ACCESS read-only
           STATUS     mandatory
           DESCRIPTION
                 "The number of calls with a speed of 58666."
           ::= { usrCipSpeedStatisticsEntry 36 }
   
    usrCipSpeedStatisticsSpeed60000 OBJECT-TYPE
           SYNTAX     Counter32
           ACCESS read-only
           STATUS     mandatory
           DESCRIPTION
                 "The number of calls with a speed of 60000."
           ::= { usrCipSpeedStatisticsEntry 37 }
   
    usrCipSpeedStatisticsSpeed61333 OBJECT-TYPE
           SYNTAX     Counter32
           ACCESS read-only
           STATUS     mandatory
           DESCRIPTION
                 "The number of calls with a speed of 61333."
           ::= { usrCipSpeedStatisticsEntry 38 }
   
    usrCipSpeedStatisticsSpeed64000 OBJECT-TYPE
           SYNTAX     Counter32
           ACCESS read-only
           STATUS     mandatory
           DESCRIPTION
                 "The number of calls with speed of 64000."
           ::= { usrCipSpeedStatisticsEntry 39 }

    usrCipSpeedStatisticsResetTime	OBJECT-TYPE
			SYNTAX	OCTET STRING (SIZE (12))
			ACCESS	read-write
			STATUS	mandatory
			DESCRIPTION
				"Time the Speed statistics counters were last reset to value zero."
    ::= { usrCipSpeedStatisticsEntry 40 }

	usrCipPacketSizeStatisticsTable OBJECT-TYPE
           SYNTAX     SEQUENCE OF USRCIPPacketSizeStatisticsEntry
           ACCESS not-accessible
           STATUS     mandatory
           DESCRIPTION
				"Size of the PPP packets in each direction.
				 packet size of every 64 bytes. ie 0-64, 64-128,
 				 128-192,, 2048. Which gives 32 samples."
           ::= { usrCip 46 }

    usrCipPacketSizeStatisticsEntry OBJECT-TYPE
           SYNTAX     USRCIPPacketSizeStatisticsEntry
           ACCESS not-accessible
           STATUS     mandatory
           DESCRIPTION
                "CIP PPP packet size statistics"
           INDEX      { usrCipPacketSizeStatisticsIndex }
           ::= { usrCipPacketSizeStatisticsTable 1 }

    USRCIPPacketSizeStatisticsEntry ::= SEQUENCE {
           usrCipPacketSizeStatisticsIndex      INTEGER,
           usrCipPacketUpLoadSizes              Counter32,
           usrCipPacketDownLoadSizes            Counter32
		}

	usrCipPacketSizeStatisticsIndex OBJECT-TYPE
           SYNTAX     INTEGER
           ACCESS not-accessible
           STATUS     mandatory
           DESCRIPTION
                 "The index for the PPP packet size samples."
           ::= { usrCipPacketSizeStatisticsEntry 1 }

    usrCipPacketUpLoadSizes OBJECT-TYPE
           SYNTAX     Counter32
           ACCESS read-only
           STATUS     mandatory
           DESCRIPTION
                 "The PPP Upload packet size samples."
           ::= { usrCipPacketSizeStatisticsEntry 2 }

    usrCipPacketDownLoadSizes OBJECT-TYPE
           SYNTAX     Counter32
           ACCESS read-only
           STATUS     mandatory
           DESCRIPTION
                 "The PPP Download packet size samples."
           ::= { usrCipPacketSizeStatisticsEntry 3 }


	usrCipModemDisconectReasonNoError  OBJECT-TYPE
         SYNTAX  Counter32
         ACCESS  read-only
         STATUS  mandatory
         DESCRIPTION
             "Number of calls with disconnect reason no_error."
         ::= { usrCip 47 }
	
	usrCipModemDisconectReasonNoCarrier  OBJECT-TYPE
         SYNTAX  Counter32
         ACCESS  read-only
         STATUS  mandatory
         DESCRIPTION
             "Number of calls with disconnect reason no_carrier."
         ::= { usrCip 48 }

	usrCipModemDisconectReasonNoDsr  OBJECT-TYPE
         SYNTAX  Counter32
         ACCESS  read-only
         STATUS  mandatory
         DESCRIPTION
             "Number of calls with disconnect reason no_dsr."
         ::= { usrCip 49 }

	usrCipModemDisconectReasonTimeout  OBJECT-TYPE
         SYNTAX  Counter32
         ACCESS  read-only
         STATUS  mandatory
         DESCRIPTION
             "Number of calls with disconnect reason timeout."
         ::= { usrCip 50 }

	usrCipModemDisconectReasonReset  OBJECT-TYPE
         SYNTAX  Counter32
         ACCESS  read-only
         STATUS  mandatory
         DESCRIPTION
             "Number of calls with disconnect reason reset."
         ::= { usrCip 51 }

	usrCipModemDisconectReasonCallDropReq  OBJECT-TYPE
         SYNTAX  Counter32
         ACCESS  read-only
         STATUS  mandatory
         DESCRIPTION
             "Number of calls with disconnect reason call_drop_req."
         ::= { usrCip 52 }

	usrCipModemDisconectReasonIdleTimeout  OBJECT-TYPE
         SYNTAX  Counter32
         ACCESS  read-only
         STATUS  mandatory
         DESCRIPTION
             "Number of calls with disconnect reason idle_timeout."
         ::= { usrCip 53 }

	usrCipModemDisconectReasonSessionTimeout  OBJECT-TYPE
         SYNTAX  Counter32
         ACCESS  read-only
         STATUS  mandatory
         DESCRIPTION
             "Number of calls with disconnect reason session_timeout."
         ::= { usrCip 54 }

	usrCipModemDisconectReasonUserReqDrop  OBJECT-TYPE
         SYNTAX  Counter32
         ACCESS  read-only
         STATUS  mandatory
         DESCRIPTION
             "Number of calls with disconnect reason user_req_drop."
         ::= { usrCip 55 }

	usrCipModemDisconectReasonHostReqDrop  OBJECT-TYPE
         SYNTAX  Counter32
         ACCESS  read-only
         STATUS  mandatory
         DESCRIPTION
             "Number of calls with disconnect reason host_req_drop."
         ::= { usrCip 56 }

	usrCipModemDisconectReasonServiceInterruption  OBJECT-TYPE
         SYNTAX  Counter32
         ACCESS  read-only
         STATUS  mandatory
         DESCRIPTION
             "Number of calls with disconnect reason service_interruption."
         ::= { usrCip 57 }

	usrCipModemDisconectReasonServiceUnavailable  OBJECT-TYPE
         SYNTAX  Counter32
         ACCESS  read-only
         STATUS  mandatory
         DESCRIPTION
             "Number of calls with disconnect reason service_unavailable."
         ::= { usrCip 58 }

	usrCipModemDisconectReasonUserInputError  OBJECT-TYPE
         SYNTAX  Counter32
         ACCESS  read-only
         STATUS  mandatory
         DESCRIPTION
             "Number of calls with disconnect reason user_input_error."
         ::= { usrCip 59 }

	usrCipModemDisconectReasonNasDropForCallback  OBJECT-TYPE
         SYNTAX  Counter32
         ACCESS  read-only
         STATUS  mandatory
         DESCRIPTION
             "Number of calls with disconnect reason nas_drop_for_callback."
         ::= { usrCip 60 }

	usrCipModemDisconectReasonnasDropMiscNonError  OBJECT-TYPE
         SYNTAX  Counter32
         ACCESS  read-only
         STATUS  mandatory
         DESCRIPTION
             "Number of calls with disconnect reason nas_drop_misc_non_error."
         ::= { usrCip 61 }

	usrCipModemDisconectReasonNasInternalError  OBJECT-TYPE
         SYNTAX  Counter32
         ACCESS  read-only
         STATUS  mandatory
         DESCRIPTION
             "Number of calls with disconnect reason nas_internal_error."
         ::= { usrCip 62 }

	usrCipStatisticsResetCallDuration    OBJECT-TYPE
			SYNTAX  OCTET STRING (SIZE (12))
			ACCESS  read-write
			STATUS  mandatory
			DESCRIPTION
				"Daily time we reset all the call statistics counters."
         ::= { usrCip 63 }

	usrCipStatisticsResetPPPUploadPackets    OBJECT-TYPE
			SYNTAX  OCTET STRING (SIZE (12))
			ACCESS  read-write
			STATUS  mandatory
			DESCRIPTION
				"Daily time we reset all the ppp upload packets counters."
         ::= { usrCip 64 }

	usrCipStatisticsResetPPPDownloadPackets    OBJECT-TYPE
			SYNTAX  OCTET STRING (SIZE (12))
			ACCESS  read-write
			STATUS  mandatory
			DESCRIPTION
				"Daily time we reset all the PPP download packets counters."
         ::= { usrCip 65 }

	usrCipStatisticsResetCallDisconnectReasons    OBJECT-TYPE
			SYNTAX  OCTET STRING (SIZE (12))
			ACCESS  read-write
			STATUS  mandatory
			DESCRIPTION
				"Daily time we reset all the call disconnect reason counters."
         ::= { usrCip 66 }

	usrCipStatistics100PercentModemUtilization    OBJECT-TYPE
			SYNTAX  Counter32
			ACCESS  read-write
			STATUS  mandatory
			DESCRIPTION
				" Number of minutes at modems 100 % utilization."
         ::= { usrCip 67 }

	usrCipModemCompressionStatisticsTable OBJECT-TYPE
           SYNTAX     SEQUENCE OF USRCIPModemCompressionStatisticsEntry
           ACCESS not-accessible
           STATUS     mandatory
           DESCRIPTION
                 "The  table listing the Modem Compression statistics
                  for all the calls coming in."
           ::= { usrCip 68 }

    usrCipModemCompressionStatisticsEntry OBJECT-TYPE
           SYNTAX     USRCIPModemCompressionStatisticsEntry
           ACCESS not-accessible
           STATUS     mandatory
           DESCRIPTION
                "CIP Modem Compression statistics"
           INDEX      { usrCipModemCompressionStatisticsIndex }
           ::= { usrCipModemCompressionStatisticsTable 1 }

    USRCIPModemCompressionStatisticsEntry ::= SEQUENCE {
           usrCipModemCompressionStatisticsIndex                        INTEGER,
           usrCipModemCompressionStatisticsModemCompNone               Counter32,
           usrCipModemCompressionStatisticsModemCompV42Bis              Counter32,
           usrCipModemCompressionStatisticsModemCompMnp5           Counter32,
		usrCipModemCompressionStatisticsResetTime  OCTET STRING
		}

	 usrCipModemCompressionStatisticsIndex OBJECT-TYPE
           SYNTAX     INTEGER
           ACCESS not-accessible
           STATUS     mandatory
           DESCRIPTION
                 "The index for the Modem Compression statistics display.
                  they are 0-now& 1-total."
           ::= { usrCipModemCompressionStatisticsEntry 1 }
	

	usrCipModemCompressionStatisticsModemCompNone OBJECT-TYPE
           SYNTAX     Counter32
           ACCESS read-only
           STATUS     mandatory
           DESCRIPTION
                 "The number of calls that has No Modem Compression."
           ::= { usrCipModemCompressionStatisticsEntry 2 }

	usrCipModemCompressionStatisticsModemCompV42Bis OBJECT-TYPE
           SYNTAX     Counter32
           ACCESS read-only
           STATUS     mandatory
           DESCRIPTION
                 "The number of calls that has V_42Bis modem compression."
           ::= { usrCipModemCompressionStatisticsEntry 3 }

	usrCipModemCompressionStatisticsModemCompMnp5 OBJECT-TYPE
           SYNTAX     Counter32
           ACCESS read-only
           STATUS     mandatory
           DESCRIPTION
                 "The number of calls that has mnp5 modem compression."
           ::= { usrCipModemCompressionStatisticsEntry 4 }

    usrCipModemCompressionStatisticsResetTime	OBJECT-TYPE
			SYNTAX	OCTET STRING (SIZE (12))
			ACCESS	read-write
			STATUS	mandatory
			DESCRIPTION
				"Time the Speed statistics counters were last reset to value zero."
    ::= { usrCipModemCompressionStatisticsEntry 5 }

	usrCipTelnetConnectionTimeout  OBJECT-TYPE
         SYNTAX  INTEGER
         ACCESS  read-write
         STATUS  mandatory
         DESCRIPTION
             "For host rotation a configurable connection timeout"
     --CONFIGURABLE
         ::= { usrCip 71 }

    usrCipTelnetBuffering  OBJECT-TYPE
         SYNTAX  INTEGER
         ACCESS  read-write
         STATUS  mandatory
         DESCRIPTION
             "For a login user, whether CIP to TELNET buffering           
             should be turned on or off flag"
     --CONFIGURABLE
         ::= { usrCip 72 }

-- ifdef VIRT_DYN
-- Modem Group Template Table
--
      usrCipModemGroupTemplateTable OBJECT-TYPE
         SYNTAX  SEQUENCE OF USRCIPModemGroupTemplateEntry 
         ACCESS  not-accessible
         STATUS  mandatory
         DESCRIPTION
            "This is the table of all modem group templates"
      ::= { usrCip 93 }

     usrCipModemGroupTemplateEntry OBJECT-TYPE
        SYNTAX      USRCIPModemGroupTemplateEntry
        ACCESS      not-accessible
        STATUS      mandatory
        DESCRIPTION "Each entry corresponds to a virtual dynamic modem group."
        INDEX   {
                usrCipModemGroupTemplateGroupName
               }
     ::= {usrCipModemGroupTemplateTable 1}

     USRCIPModemGroupTemplateEntry ::= 
          SEQUENCE {
                usrCipModemGroupTemplateGroupName
                   DisplayString,
--
-- The following are per-interface entries from the configurator 
--
		usrCipModemGroupTemplateCfgIfInFilter 
			DisplayString,
		usrCipModemGroupTemplateCfgIfOutFilter 
			DisplayString,
		usrCipModemGroupTemplateCfgIfFilterAccess 
			INTEGER,
		usrCipModemGroupTemplateCfgIfPolicy 
			DisplayString,
		usrCipModemGroupTemplateCfgIfPolicyAccess 
			INTEGER,
		usrCipModemGroupTemplateCfgIfType  
			INTEGER,
--
-- The following are per port parameters(SPP)
--
               usrCipModemGroupTemplatePortType
                    INTEGER,
               usrCipModemGroupTemplatePortAccess
                    INTEGER,
               usrCipModemGroupTemplatePortHostType
                    INTEGER,
               usrCipModemGroupTemplatePortLoginService
                    INTEGER,
               usrCipModemGroupTemplatePortTcpPortNumber
                    INTEGER,
               usrCipModemGroupTemplatePortLoginMsg
                    OCTET STRING,
               usrCipModemGroupTemplatePortLoginPrompt
                    OCTET STRING,
               usrCipModemGroupTemplatePortIpAddress
                    IpAddress,
               usrCipModemGroupTemplatePortHostIpAddress
                    IpAddress,
               usrCipModemGroupTemplatePortNetMask
                    INTEGER,
               usrCipModemGroupTemplatePortProtocol
                    INTEGER,
               usrCipModemGroupTemplatePortMtu
                    INTEGER,
               usrCipModemGroupTemplatePortIdleTimeOut
                    INTEGER,
               usrCipModemGroupTemplateInitScriptName
                    DisplayString,
               usrCipModemGroupTemplateIfConnType
                    INTEGER,
               usrCipModemGroupTemplatePromptUserName
                    OCTET STRING,
               usrCipModemGroupTemplateUserPasswd
                    OCTET STRING,
               usrCipModemGroupTemplateDialPrefix
                    OCTET STRING,
               usrCipModemGroupTemplatePortPromptingStyle
                    INTEGER,
               usrCipModemGroupTemplatePortLoginProcessing
                    INTEGER,
               usrCipModemGroupTemplatePortDNISAuthentication
                   INTEGER,
               usrCipModemGroupTemplatePortDNISAuthTime
                   INTEGER,
               usrCipModemGroupTemplatePortDNISAuthType 
                   INTEGER,
               usrCipModemGroupTemplatePortDNISPassword
                   OCTET STRING,
               usrCipModemGroupTemplatePortDNISTimeout
                   INTEGER,
               usrCipModemGroupTemplatePortParity
                    INTEGER,
               usrCipModemGroupTemplatePromptDelay
                   INTEGER,
               usrCipModemGroupTemplatePromptTimeout
                   INTEGER,
               usrCipModemGroupTemplateSpecialXonXoffFlow 
                   INTEGER,
               usrCipModemGroupTemplateUseDnisPool 
                    INTEGER,
               usrCipModemGroupTemplateLoginTable
                    OCTET STRING
               }

     usrCipModemGroupTemplateGroupName OBJECT-TYPE
          SYNTAX        DisplayString 
          ACCESS        not-accessible
          STATUS        mandatory
          DESCRIPTION   "The identifier of a modem group."
     ::= { usrCipModemGroupTemplateEntry 1 }

     
     usrCipModemGroupTemplateCfgIfInFilter OBJECT-TYPE
     	SYNTAX      DisplayString (SIZE(0..20))
     	ACCESS      read-write
     	STATUS      mandatory
     	DESCRIPTION "The name of the input filter for a specific interface."
           --CONFIGURABLE
     ::= {  usrCipModemGroupTemplateEntry 2 }
     
     usrCipModemGroupTemplateCfgIfOutFilter OBJECT-TYPE
     	SYNTAX      DisplayString (SIZE(0..20))
     	ACCESS      read-write
     	STATUS      mandatory
     	DESCRIPTION "The name of the output filter for a specific interface."
            --CONFIGURABLE
     ::= {  usrCipModemGroupTemplateEntry 3 }
     
     usrCipModemGroupTemplateCfgIfFilterAccess OBJECT-TYPE
            SYNTAX      INTEGER {
     	                        off (0),
                                  on (1)
                                }
            ACCESS      read-write
            STATUS      mandatory
            DESCRIPTION "This switch will allow user filters to override the
                         interface filters. If set to 'off', user filters do not
     				override the interface filters. If set to 'on' user
     				filters can override the interface filters."
            --CONFIGURABLE
     ::= { usrCipModemGroupTemplateEntry 4 }
     
     usrCipModemGroupTemplateCfgIfPolicy OBJECT-TYPE
     	SYNTAX      DisplayString (SIZE(0..20))
     	ACCESS      read-write
     	STATUS      mandatory
     	DESCRIPTION "The name of the  policy for a specific interface."
           --CONFIGURABLE
     ::= {  usrCipModemGroupTemplateEntry 5 }
     
     usrCipModemGroupTemplateCfgIfPolicyAccess OBJECT-TYPE
            SYNTAX      INTEGER {
     	                        off (0),
                                  on (1)
                                }
            ACCESS      read-write
            STATUS      mandatory
            DESCRIPTION "This switch will allow user policy to override the
                         interface policy. If set to 'off', user policies do not
     				override the interface policy. If set to 'on' user
     				policy can override the interface policy."
            --CONFIGURABLE
     ::= { usrCipModemGroupTemplateEntry 6 }
     
     usrCipModemGroupTemplateCfgIfType OBJECT-TYPE  
         SYNTAX INTEGER
         ACCESS not-accessible
         STATUS mandatory    
         DESCRIPTION 
             "The type of interface, distinguished according to
             the physical/link protocol(s) immediately below
             the network layer in the protocol stack."
     ::= {  usrCipModemGroupTemplateEntry 7 } 

     usrCipModemGroupTemplatePortType OBJECT-TYPE
          SYNTAX      INTEGER {
                         login (1),
                         network (2),
                         login-network (3)
                         }
          ACCESS      read-write
          STATUS      mandatory
          DESCRIPTION "The type of the physical port."
            --CONFIGURABLE
     ::= { usrCipModemGroupTemplateEntry 8}

     usrCipModemGroupTemplatePortAccess OBJECT-TYPE
          SYNTAX      INTEGER {
                         dial-in(1),
                         dial-out(2),
                         two-way(3)
                       }
          ACCESS      read-write
          STATUS      mandatory
          DESCRIPTION "This field specifies the direction of the calls
                         that could be made on a specific interface. 
                         Ports could be configured to be dial-in, dial-out
                         or two-way ports."
            --CONFIGURABLE
     ::= { usrCipModemGroupTemplateEntry 9}

     usrCipModemGroupTemplatePortHostType OBJECT-TYPE
          SYNTAX      INTEGER {
                         default (1),
                         prompt (2),
                         specified (3)
                         }
          ACCESS      read-write
          STATUS      mandatory
          DESCRIPTION "The host type that the dial-in user 
                       will be connected to."
            --CONFIGURABLE
     ::= { usrCipModemGroupTemplateEntry 10}

     usrCipModemGroupTemplatePortLoginService OBJECT-TYPE
          SYNTAX      INTEGER {
                         telnet (1),
                         rlogin (2),
                         netdata (3)
                         }
          ACCESS      read-write 
          STATUS      mandatory
          DESCRIPTION "The Service type that the dial-in user will 
                       be connected to."
            --CONFIGURABLE
     ::= { usrCipModemGroupTemplateEntry 11}

     usrCipModemGroupTemplatePortTcpPortNumber OBJECT-TYPE
          SYNTAX      INTEGER
          ACCESS      read-write
          STATUS      mandatory
          DESCRIPTION "The tcp port number associated with the service type."
            --CONFIGURABLE
     ::= { usrCipModemGroupTemplateEntry 12}

     usrCipModemGroupTemplatePortLoginMsg OBJECT-TYPE
          SYNTAX      OCTET STRING (SIZE(0..255))
          ACCESS      read-write
          STATUS      mandatory
          DESCRIPTION "The salutation message associated with a specific port."
            --CONFIGURABLE
     ::= { usrCipModemGroupTemplateEntry 13}

     usrCipModemGroupTemplatePortLoginPrompt OBJECT-TYPE
   	  SYNTAX      OCTET STRING (SIZE(0..64))
   	  ACCESS      read-write
   	  STATUS      mandatory
   	  DESCRIPTION "The login prompt associated with a specific port."
            --CONFIGURABLE
     ::= { usrCipModemGroupTemplateEntry 14}

     usrCipModemGroupTemplatePortIpAddress OBJECT-TYPE
   	  SYNTAX      IpAddress
   	  ACCESS      read-write
   	  STATUS      mandatory
	  DESCRIPTION "The IP address for a specific serial port."
            --CONFIGURABLE
      ::= { usrCipModemGroupTemplateEntry 15}

     usrCipModemGroupTemplatePortHostIpAddress OBJECT-TYPE
   	  SYNTAX      IpAddress
   	  ACCESS      read-write
   	  STATUS      mandatory
	  DESCRIPTION "A host IP address specified for this interface."
            --CONFIGURABLE
   	::= { usrCipModemGroupTemplateEntry 16}

     usrCipModemGroupTemplatePortNetMask OBJECT-TYPE
   	  SYNTAX      INTEGER
   	  ACCESS      read-write
   	  STATUS      mandatory
   	  DESCRIPTION "The netmask associated with a specific 
                       serial interface."
            --CONFIGURABLE
     ::= { usrCipModemGroupTemplateEntry 17}

     usrCipModemGroupTemplatePortProtocol OBJECT-TYPE
   	  SYNTAX      INTEGER {
                         ppp (1),
                         slip (2),
                         arap (3)
                    	   }
   	  ACCESS      read-write
   	  STATUS      mandatory
   	  DESCRIPTION "The protocol type configured for a specific interface."
            --CONFIGURABLE
     ::= { usrCipModemGroupTemplateEntry 18}

     usrCipModemGroupTemplatePortMtu OBJECT-TYPE
   	  SYNTAX      INTEGER
   	  ACCESS      read-write
   	  STATUS      mandatory
   	  DESCRIPTION "The mtu value associated with a specific interface."
            --CONFIGURABLE
     ::= { usrCipModemGroupTemplateEntry 19}

     usrCipModemGroupTemplatePortIdleTimeOut OBJECT-TYPE
   	  SYNTAX      INTEGER
   	  ACCESS      read-write
   	  STATUS      mandatory
   	  DESCRIPTION "The maximum idle time specified for an interface."
            --CONFIGURABLE
     ::= { usrCipModemGroupTemplateEntry 20}

     usrCipModemGroupTemplateInitScriptName OBJECT-TYPE
          SYNTAX      DisplayString  (SIZE(0..7))
          ACCESS      read-write
          STATUS      mandatory
          DESCRIPTION "The name of the script"
            --CONFIGURABLE
     ::= {  usrCipModemGroupTemplateEntry 21 }

     usrCipModemGroupTemplateIfConnType OBJECT-TYPE
          SYNTAX      INTEGER {
                        if-direct-conn (1),
                        if-direct-network-conn (2),
                        if-normal-conn (3),
                        if-prompt-passwd (4),
                        if-prompt-none (5),
						if-ppp-only(6)
                        }
          ACCESS      read-write
          STATUS      mandatory
          DESCRIPTION "The type of the connection that i/f is configured for."
            --CONFIGURABLE
     ::= {  usrCipModemGroupTemplateEntry 22 }

     usrCipModemGroupTemplatePromptUserName OBJECT-TYPE
          SYNTAX        OCTET STRING (SIZE(0..32))
          ACCESS        read-write
          STATUS        mandatory
          DESCRIPTION   "This could only be set if the port is
                        configured not to prompt for username."
            --CONFIGURABLE
     ::= {  usrCipModemGroupTemplateEntry 23 }

     usrCipModemGroupTemplateUserPasswd OBJECT-TYPE
          SYNTAX      OCTET STRING (SIZE(0..15))
   	  ACCESS      read-write
   	  STATUS      mandatory
   	  DESCRIPTION "This could only be set if the port is 
                       configured to not prompt for password."
            --CONFIGURABLE
     ::= {  usrCipModemGroupTemplateEntry 24 }

     usrCipModemGroupTemplateDialPrefix OBJECT-TYPE
         SYNTAX         OCTET STRING (SIZE(0..64))
         ACCESS         read-write
         STATUS         mandatory
         DESCRIPTION    "This string defines the prefix to the phone number."
            --CONFIGURABLE
    ::= {  usrCipModemGroupTemplateEntry 25 }

    usrCipModemGroupTemplatePortPromptingStyle OBJECT-TYPE
         SYNTAX        INTEGER {
                           local-prompting(1),
                           remote-prompting(2)
                       }
         ACCESS        read-write
         STATUS        mandatory
         DESCRIPTION   "This value specifies whether the NAS will provide
                       username and password prompting locally or if the
                       prompting will be handled by a remote security server."
        --CONFIGURABLE
    ::= {  usrCipModemGroupTemplateEntry 26 }

    usrCipModemGroupTemplatePortLoginProcessing OBJECT-TYPE
        SYNTAX INTEGER {
                       enable (1),
                       disable (2)
                       }
        ACCESS read-write
        STATUS mandatory
        DESCRIPTION
            "This variable controls login processing.  Setting the value to disable
             will cause the box to not prompt a user for login name or password.  Enabling
             this value will cause the box to perform normal login name and password prompting."
        --CONFIGURABLE
        ::= { usrCipModemGroupTemplateEntry 27}
    

    usrCipModemGroupTemplatePortDNISAuthentication  OBJECT-TYPE
         SYNTAX INTEGER    
         {     
             dnis-auth-disabled (1),
             dnis-auth-preferred (2), 
             dnis-auth-required (3)
         }      
         ACCESS  read-write
         STATUS  mandatory       
         DESCRIPTION  
             "DNIS Authentication type"
         --CONFIGURABLE
         ::= {  usrCipModemGroupTemplateEntry 28 }

    usrCipModemGroupTemplatePortDNISAuthTime  OBJECT-TYPE
         SYNTAX INTEGER
         {
             before-answer (1),
             after-answer (2)
         }
         ACCESS read-write
         STATUS  mandatory
         DESCRIPTION
             "DNIS Authentication Time"
         --CONFIGURABLE
         ::= {  usrCipModemGroupTemplateEntry 29 }
 
    usrCipModemGroupTemplatePortDNISAuthType  OBJECT-TYPE
         SYNTAX INTEGER
         {
             dnis (1),
             ani (2)
         }
         ACCESS read-write
         STATUS  mandatory
         DESCRIPTION
             "DNIS Authentication type"
         --CONFIGURABLE
         ::= {  usrCipModemGroupTemplateEntry 30 }


     usrCipModemGroupTemplatePortDNISPassword OBJECT-TYPE
          SYNTAX      OCTET STRING (SIZE(0..15))
   	  ACCESS    read-write
   	  STATUS      mandatory
   	  DESCRIPTION "The DNIS  password."
         --CONFIGURABLE
         ::= {  usrCipModemGroupTemplateEntry 31 }


     usrCipModemGroupTemplatePortDNISTimeout OBJECT-TYPE
          SYNTAX      INTEGER
          ACCESS      read-write  
          STATUS      mandatory
          DESCRIPTION "Timeout if no auth within this time"
         --CONFIGURABLE
     ::= { usrCipModemGroupTemplateEntry 32}

    usrCipModemGroupTemplatePortParity  OBJECT-TYPE
         SYNTAX INTEGER       
         {      
			no-parity-eight-bit (1),
			even-seven-bit (2),  
			odd-seven-bit (3),  
			no-parity-seven-bit (4)
         }
         ACCESS  read-write 
         STATUS  mandatory
         DESCRIPTION
             "Port Parity"
         --CONFIGURABLE
         ::= {  usrCipModemGroupTemplateEntry 33 }

    usrCipModemGroupTemplatePromptDelay  OBJECT-TYPE
         SYNTAX INTEGER (0..100)
         ACCESS   read-write
         STATUS  mandatory
         DESCRIPTION
             "If user does not enter any key after banner mesg, authenticate
              user based on interface user name after this delay"
         --CONFIGURABLE
         ::= {  usrCipModemGroupTemplateEntry 34 }


    usrCipModemGroupTemplatePromptTimeout  OBJECT-TYPE
         SYNTAX INTEGER (5..600)
         ACCESS  read-write
         STATUS  mandatory
         DESCRIPTION
             " This is the maximum timeout while prompting for 
				username password. If nothing is typed, the session will
				be terminated. Default is 300 secs"
         --CONFIGURABLE
         ::= {  usrCipModemGroupTemplateEntry 35 }


      usrCipModemGroupTemplateSpecialXonXoffFlow  OBJECT-TYPE
         SYNTAX INTEGER       
         {      
             disbaled (0),
             enabled (1)
         }
         ACCESS read-write
         STATUS  mandatory
         DESCRIPTION
             "Specail Xon Xoff flow control in modem control receive side"
         --CONFIGURABLE
         ::= {  usrCipModemGroupTemplateEntry 36 }

	 usrCipModemGroupTemplateUseDnisPool OBJECT-TYPE
         SYNTAX INTEGER 
		 {
             dnis-pool-disabled (1),
             dnis-pool-preferred (2),
             dnis-pool-required (3)
         }
         ACCESS read-write
         STATUS  mandatory
         DESCRIPTION
             "User DNIS pool"
         --CONFIGURABLE
     ::= {  usrCipModemGroupTemplateEntry 37 }

	 usrCipModemGroupTemplateLoginTable OBJECT-TYPE
         SYNTAX OCTET STRING
         ACCESS  read-write
         STATUS  mandatory
         DESCRIPTION
             "Login Host Table "
         --CONFIGURABLE
     ::= {  usrCipModemGroupTemplateEntry 38 }

-- Scalar Flag
    usrCipCfmModemGroupTemplateFlag OBJECT-TYPE
        SYNTAX          INTEGER
        ACCESS          read-write
        STATUS          mandatory
        DESCRIPTION    "This flag triggers a save of 
                         modem group template table."
    ::= { usrCip 94 } --Conflict CHAITANYA has to be resolved

--
-- endif VIRT_DYN
--

	usrCipOndemandConnectionRetries  OBJECT-TYPE
         SYNTAX  INTEGER(1..500)
         ACCESS  read-write
         STATUS  mandatory
         DESCRIPTION
             ""
     --CONFIGURABLE
         ::= { usrCip 74 }

	usrCipOndemandConnectionRetryInterval  OBJECT-TYPE
         SYNTAX  INTEGER(1..600)
         ACCESS  read-write
         STATUS  mandatory
         DESCRIPTION
             ""
     --CONFIGURABLE
         ::= { usrCip 75 }


END         -- End CIP-MIB definitions


--
-- File Footer 
--
-- Revisions:
-- 
-- $Log: usr_cip.mib,v $
-- Revision 1.33.2.20  1998/06/30 23:50:47  senthil
-- Support for chat scripting
--
-- Revision 1.33.2.19  1998/06/29 19:26:01  snatu
-- Have to change to accomodate sprint feature
--
-- Revision 1.33.2.18  1998/06/08 22:28:53  sanil
-- Fixed MR6930 ( calltype & auth disable)
--
-- Revision 1.33.2.17  1998/05/27 19:01:26  rajr
-- Merging UUNET changes to Pilgrim30
--
-- Revision 1.33.2.16  1998/05/20 16:22:15  rverma
-- changd the values for l2tp and none to avoid mib erase.
--
-- Revision 1.33.2.15  1998/05/15 21:14:48  rverma
-- Fix for MR 6497 added a new enumeration of l2tp to global call type
--
-- Revision 1.33.2.14  1998/05/14 20:37:42  senthil
-- MR 6289: Eliminating the Login/Network prompt by means of a CLI command
--
-- Revision 1.33.2.13  1998/05/11 21:48:56  joes
-- Undid the previous commit.
--
-- Revision 1.33.2.12  1998/04/15 13:12:06  joes
-- Modified usrCipModemGroupInterfaceEntry objects to be in same order as listed
-- in the sequence statement.
--
-- Revision 1.33.2.11  1998/04/07 21:04:29  asingh
-- Added mib for MR6220 
--
-- Revision 1.33.2.10  1998/04/03 20:50:09  joes
-- Merged Samsung ER changes into 3.0
--
-- Revision 1.33.2.9  1998/03/17 23:41:57  joes
-- Fixed cut and paste error.
--
-- Revision 1.33.2.8  1998/03/17 22:15:47  joes
-- Moved USRCIPModemGroupInterfaceGroupName to end of USRCIPModemGroupInterfaceEntry
-- > to preserve oids.
--
-- Revision 1.33.2.7  1998/03/16 18:17:06  psd
-- MR 5759 fix. Sync up MBOX ids and dlls.
--
-- Revision 1.33.2.6  1998/01/10 01:38:49  merge
-- Tacacs+ merge
--
-- Revision 1.33.2.5  1997/12/22 01:02:44  joes
-- MR4197: Changed some OCTET STRING fields to DisplayString so SNMP
-- managers will display the information correctly.
--
-- Revision 1.33.2.3  1997/12/18 20:14:07  joes
-- Second merge of 2.0 -> 3.0
--
-- Revision 1.33.2.2  1997/09/17 19:06:24  psd
-- Merged 2.0 to 3.0
--
--Revision 1.37.2.3  1997/09/10  14:30:43  psd
--Changed string range of usrCipPortCfgScript from 0-32 to 1-32.
--
--Revision 1.37.2.2  1997/08/29  19:39:35  psd
--Added the ping service to usrCipPortLoginService.
--
--Revision 1.37.2.1  1997/08/27  14:19:08  psd
--Part of MR 2566 fix. Added ping and none to usrCipDataLinkConn enum.
--
--Revision 1.37  1997/08/05  12:40:54  naga
--Bug fix for #1707 - telnet misspelled in usrCipDataLinkConn
--
-- Revision 1.36  1997/07/18 20:49:19  joes
-- PR1933: Reordered mib to prevent NM application from needing to be recompiled.  Moved Modem group interface table to end of mib.
--
-- Revision 1.35  1997/06/23 21:40:27  joes
-- Modifications to support modem group rewrite.
--
-- Revision 1.34  1997/05/29 15:29:42  tonyw
-- Changed usrCipPortCfgScriptResult to a display string and added RESET magic string for usrCipPortCfgScript
--
--Revision 1.33.2.1  1997/07/01  13:27:11  pfc
--Merge in changes from mainline branch
--
-- Revision 1.33  1997/05/16 16:33:21  lmg
-- MR 977: Added Mib object for config file name
--
-- Revision 1.32  1997/03/14 19:15:22  patton
-- made modem_group interface parameters write only, now that NMI is fixed to handle write-only parameters
--
-- Revision 1.31  1997/02/26 22:13:20  joes
-- Increases usrCipPortLoginMsg to 800 form 255
--
-- Revision 1.30  1997/02/26 21:14:09  joes
-- Previous change was meant for netserver branch not mainline.
--
-- Revision 1.29  1997/02/26 21:11:31  joes
-- Increased usrCipPortLoginMsg from 255 to 800.
--
-- Revision 1.28  1996/11/08 20:05:10  edjean
-- Add mib objects to support AT cmds
--
-- Revision 1.26  1996/09/18 21:44:39  jhalpin
-- Merge in LANLinker branch changes <sawdust city here I come..>
--
-- Revision 1.25  1996/07/10 20:13:42  hasmik
-- Added usrCipGlblHostState
--
-- Revision 1.24.2.1  1996/07/10 22:01:26  hasmik
-- Added GlobalHostState to the table
--
-- Revision 1.24  1996/06/04 20:01:17  hasmik
-- Added usrCipSaveAllFlag
--
-- Revision 1.23  1996/05/30 16:54:03  hasmik
-- Added DialPrefix MIB entry and removed Filter MIBS
--
-- Revision 1.22  1996/05/17 20:24:49  hasmik
-- Added normal-status to the init_script status
--
-- Revision 1.21  1996/05/14 19:54:37  hasmik
-- Added CIPBusyOutIf MIB variable
--
-- Revision 1.20  1996/04/30 00:35:57  hasmik
-- Changed the UserPass to read-write
--
-- Revision 1.19  1996/04/26 21:49:46  hasmik
-- Added configurable username and userpassword
--
-- Revision 1.18  1996/04/26 20:06:21  hasmik
-- Added port modem_group
--
-- Revision 1.17  1996/04/19 22:30:46  hasmik
-- Duplicated ModemGroup table based on modem_group name
--
-- Revision 1.16  1996/04/16 16:06:30  hasmik
-- Added dedicated-conn to the ConnType
--
-- Revision 1.15  1996/04/15 23:02:23  patton
-- fixed type Falg to Flag
--
-- Revision 1.14  1996/04/12 18:04:19  hasmik
-- Added CFM flags for the tables
--
-- Revision 1.13  1996/04/08 20:49:33  hasmik
-- Changed definition of HostState
--
-- Revision 1.12  1996/04/03 23:05:02  hasmik
-- Added AllowManageOnDialups MIB variable
--
-- Revision 1.11  1996/04/01 19:28:41  hasmik
-- Added DefaultPassword to port structure. Removed GlblServiceType and GlblProtoType
--
-- Revision 1.10  1996/03/19 20:58:49  hasmik
-- Added support for init script
--
-- Revision 1.9  1996/03/11 17:12:03  hasmik
-- Added CipDataLinkConn Variable
--
-- Revision 1.8  1996/03/11 14:45:28  hasmik
-- Added CIPGroupCount MIB variable
--
-- Revision 1.7  1996/03/08 23:08:44  hasmik
-- Added CipConnStartTime to the Port Table.
--
-- Revision 1.6  1996/03/08 22:51:59  hasmik
-- Added HangUp and DialOut MIB variables
--
-- Revision 1.5  1996/02/29 20:01:22  hasmik
-- Added CipGroupStatus
--
-- Revision 1.4  1996/02/28 21:28:29  hasmik
-- Changed the length of octet strings
--
-- Revision 1.3  1996/02/27 23:57:24  hasmik
-- Added three MIB variable so that CLI doesn't break
--
-- Revision 1.2  1996/02/27 22:58:09  hasmik
-- Created Global Mib variables. Added to the CIP portal variables
--
-- Revision 1.1  1995/12/28 18:10:33  hasmik
-- Initial Version
--
-- 



--
--    usr_pppml.mib - The USR PPP Mult-Link MIB module
--
--
-- Author:         <Joe Kralowetz>
--
-- $Id: usr_pppml.mib,v 1.10.2.12 1998/05/31 21:09:54 sanil Exp $
--
--  | Copyright (c) 1995 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-PPPML-MIB DEFINITIONS ::= BEGIN

          IMPORTS
               IpAddress, Counter
                    FROM RFC1155-SMI
               OBJECT-TYPE
                    FROM RFC-1212
               DisplayString, usrPPP, UsrConfigStatus
                    FROM USR-DEFINITIONS-MIB;


          -- All representations of MAC addresses in this MIB Module use,
          -- as a textual convention (i.e. this convention does not affect
          -- their encoding), the data type:

          MacAddress ::= OCTET STRING (SIZE (6))    -- a 6 octet address in
                                                    -- the "canonical" order
          -- defined by IEEE 802.1a, i.e., as if it were transmitted least
          -- significant bit first, even though 802.5 (in contrast to other
          -- 802.x protocols) requires MAC addresses to be transmitted most
          -- significant bit first.
          --
          -- 16-bit addresses, if needed, are represented by setting their
          -- upper 4 octets to all 0's, i.e., AAFF would be represented
          -- as 00000000AAFF.

          IpxAddress ::= IpAddress   -- a 4 octet address which represents
                                     -- represents 32-bit IPX Network Address.

          usrPPPBase      OBJECT IDENTIFIER ::= { usrPPP 1 }

          usrPPPMl        OBJECT IDENTIFIER ::= { usrPPP 2 }


          --
          -- The PPP Base Group.
          --

          usrPPPBaseRxAuth OBJECT-TYPE
              SYNTAX  INTEGER {
                        none(1),
                        pap(2),
                        chap(3),
                        any(4),
                        eapMD5(5),
                        msChap(6),
                        encryptedOnly(7),
                        radiusEapProxy(8),
                        anyExceptMsChap(9),
                        papORchap(10),
                        mschapv2(11)
                      }
              ACCESS   read-write
              STATUS   mandatory
              DESCRIPTION
                      "Indicates whether PPP requires dial-in users
                      to authenticate strictly via PAP, CHAP, EAP-MD5, with any,
                      none, encrypted only (CHAP, EAP-MD5, MS-CHAP), or 
                      RADIUS-EAP-Proxy."
              DEFVAL { none }
              --CONFIGURABLE
              ::= { usrPPPBase 1 }

          usrPPPBaseCfgFileName OBJECT-TYPE
              SYNTAX   DisplayString
              ACCESS   read-write
              STATUS   mandatory
              DESCRIPTION
                      "The name of a ConfigFile to read/write
                      permanent database records. If the value of this
                      object is an empty string, then the PPP process
                      uses the default name `@file://PppFile.cfg'."
              ::= { usrPPPBase 2 }

          usrPPPBaseCFMSaveStatus OBJECT-TYPE
              SYNTAX  UsrConfigStatus
              ACCESS  read-write
              STATUS  mandatory
              DESCRIPTION
                      "Setting the value of this object to `save'
                      causes the values of the PPP Base Group
                      entries to be written out to the current PPP
                      config file. While the new config file is being
                      written, the PPP process will set the value
                      of this flag set to `saving''. Any attempts to set
                      the value while it is  not `normal' (i.e. the file
                      is currently being written to the config file)
                      while result in a badValue error being returned.
                      Setting the value to `normal' will result in no
                      action."
              ::= { usrPPPBase 3 }


          usrPPPBaseTraceInterfaceIndex OBJECT-TYPE
              SYNTAX  INTEGER (0..2147483647)
              ACCESS  read-write
              STATUS  obsolete
              DESCRIPTION
                      "Sets the interface index for which the PPP
                       frames will be decoded and displayed according
                       to PPP Trace facility loglevel. When this value
                       is set to 0 none of the interfaces is selected"
              DEFVAL { 0 }
              ::= { usrPPPBase 4 }


          usrPPPBaseOffloading OBJECT-TYPE
              SYNTAX  INTEGER {
                        yes(2),
                        no(1)
                      }
              ACCESS   read-write
              STATUS   mandatory
              DESCRIPTION
                      "Indicates whether PPP framing can be offloaded to
					  the modem card, if modem card is capable of doing it."
              DEFVAL { yes }
              --CONFIGURABLE
              ::= { usrPPPBase 5 }


          usrPPPBaseCCPModemType OBJECT-TYPE
				SYNTAX	INTEGER 
				ACCESS	read-write
				STATUS	mandatory
              DESCRIPTION
                      "Indicates the types of call, for which CCP compression
					  will be enabled in the Gateway card PPP module. Possible
					  values are none(0x1) or all (0x10) or subset of 
					  digital(0x2), compressed analog(0x4),  
					  uncompressed analog (0x08) and pppoe (0x20). Default value is digital and
					  uncompressed analog."
              DEFVAL { 20  }
              --CONFIGURABLE
              ::= { usrPPPBase 6 }



          usrPPPBaseNBNSPrimary OBJECT-TYPE
				SYNTAX	IpAddress 
				ACCESS	read-write
				STATUS	mandatory
              DESCRIPTION
                      " Global config for NBNS primary server address. In the
					    absence of user specific NBNS address, this will be send
						in IPCP negotiation"
              DEFVAL { 0  }
              --CONFIGURABLE
              ::= { usrPPPBase 7 }


          usrPPPBaseNBNSSecondary OBJECT-TYPE
				SYNTAX  IpAddress 
				ACCESS	read-write
				STATUS	mandatory
              DESCRIPTION
                      " Global config for NBNS primary server address. In the
					    absence of user specific NBNS address, this will be send
						in IPCP negotiation"
              DEFVAL { 0  }
              --CONFIGURABLE
              ::= { usrPPPBase 8 }

          usrPPPBaseSystemDNSUsage OBJECT-TYPE
                SYNTAX  INTEGER {
                            system(0),
                            ppp(1),
                            none(2),
                            client(3)
                          }
                ACCESS  read-write
                STATUS  mandatory
              DESCRIPTION
                      "In the absence of user confgiured DNS addresses,
                       PPP will take DNS addresses from the system DNS
                       table. Source of the DNS table can be controlled by
                       this switch, system-dns or ppp-dns or none. If this
                       value set to none, none of these DNS table used"
 
              DEFVAL { 0  }
              --CONFIGURABLE
              ::= { usrPPPBase 9 }

            usrPPPBasePPPDNSPrimary OBJECT-TYPE
                SYNTAX  IpAddress
                ACCESS  read-write
                STATUS  mandatory
              DESCRIPTION
                      " Global config for PPP DNS primary server address. In the
                        absence of user specific DNS address, this will be send
                        in IPCP negotiation"
              DEFVAL { 0  }
              --CONFIGURABLE
              ::= { usrPPPBase 10 }
 
 
          usrPPPBasePPPDNSSecondary OBJECT-TYPE
                SYNTAX  IpAddress
                ACCESS  read-write
                STATUS  mandatory
              DESCRIPTION
                      " Global config for PPP DNS secondary server address. In the
                        absence of user specific DNS address, this will be send
                        in IPCP negotiation"
              DEFVAL { 0  }
              --CONFIGURABLE
              ::= { usrPPPBase 11 }

          usrPPPBaseSessionStartMessage OBJECT-TYPE
              SYNTAX    OCTET STRING
              ACCESS   read-write
              STATUS   mandatory
              DESCRIPTION
                     " This is the session start display message"
              --CONFIGURABLE
              ::= { usrPPPBase 12 }
 
 
          usrPPPBaseAuthPreference OBJECT-TYPE        
                SYNTAX  INTEGER {
                            default (1),
                            pap  (2),
                            chap (3),
							mschap (4),
							eap (5),
							radiuseapproxy (6)
                          }
                ACCESS  read-write
                STATUS  mandatory
              DESCRIPTION
                      "If PPP receive authentication is configured for ANY or,
					   ENCRYPTED_ANY this setting can be used to set the 
					   first authentication attempted" 
 
              DEFVAL { 1  }
              --CONFIGURABLE
              ::= { usrPPPBase 13 }

			 usrPPPBaseAcctForImatureDisc OBJECT-TYPE
              SYNTAX  INTEGER {
                        yes(2),
                        no(1)
                      }
              ACCESS   read-write
              STATUS   mandatory
              DESCRIPTION
                      "Indicates whether to send Acct Records to premature disconnect "
              DEFVAL { no }
              --CONFIGURABLE
              ::= { usrPPPBase 14 }
 

          --
          -- The PPP Bundle Group.
          --
          -- The following object reflect the values of the option
          -- parameters used over the PPP Bundle
          --   usrPPPBundleInstance
          --   usrPPPBundleOperStatus
          --   usrPPPBundleUserProfile
          --   usrPPPBundleActiveLinks
          --   usrPPPBundleLocalMMRU
          --   usrPPPBundleRemoteMMRU
          --   usrPPPBundleLocalEndptClass
          --   usrPPPBundleLocalEndptLength
          --   usrPPPBundleLocalEndptID
          --   usrPPPBundleRemoteEndptClass
          --   usrPPPBundleRemoteEndptLength
          --   usrPPPBundleRemoteEndptID
          --   usrPPPBundleTxTotalPkts
          --   usrPPPBundleTxCompPkts
          --   usrPPPBundleTxNoncompPkts
          --   usrPPPBundleTxEncryptPkts
          --   usrPPPBundleTxNonEncryptPkts
          --   usrPPPBundleTxTotalOrigBytes
          --   usrPPPBundleTxTotalLineBytes
          --   usrPPPBundleRxBadHdrs
          --   usrPPPBundleRxTotalPkts
          --   usrPPPBundleRxCompPkts
          --   usrPPPBundleRxNoncompPkts
          --   usrPPPBundleRxEncryptPkts
          --   usrPPPBundleRxNonEncryptPkts
          --   usrPPPBundleRxTotalOrigBytes
          --   usrPPPBundleRxTotalLineBytes


          usrPPPBundleTable   OBJECT-TYPE
               SYNTAX    SEQUENCE OF UsrPPPBundleEntry
               ACCESS    not-accessible
               STATUS    mandatory
               DESCRIPTION
                         "Table containing the Bundle parameters and
                         statistics for the local PPP entity."
               ::= { usrPPPMl 1 }


          usrPPPBundleEntry   OBJECT-TYPE
               SYNTAX    UsrPPPBundleEntry
               ACCESS    not-accessible
               STATUS    mandatory
               DESCRIPTION
                         "Status information for the PPP bundle."
               INDEX     { usrPPPBundleInstance }
               ::= { usrPPPBundleTable 1 }


          UsrPPPBundleEntry ::= SEQUENCE {
               usrPPPBundleInstance
                    INTEGER,
               usrPPPBundleOperStatus
                    INTEGER,
               usrPPPBundleUserProfile
                    OCTET STRING,
               usrPPPBundleActiveLinks
                    INTEGER,
               usrPPPBundleLocalMMRU
                    INTEGER,
               usrPPPBundleRemoteMMRU
                    INTEGER,
               usrPPPBundleLocalEndptClass
                    INTEGER,
               usrPPPBundleLocalEndptLength
                    INTEGER,
               usrPPPBundleLocalEndptID
                    OCTET STRING,
               usrPPPBundleRemoteEndptClass
                    INTEGER,
               usrPPPBundleRemoteEndptLength
                    INTEGER,
               usrPPPBundleRemoteEndptID
                    OCTET STRING,
               usrPPPBundleTxTotalPkts
                    Counter,
               usrPPPBundleTxCompPkts
                    Counter,
               usrPPPBundleTxNonCompPkts
                    Counter,
               usrPPPBundleTxTotalOrigBytes
                    Counter,
               usrPPPBundleTxTotalLineBytes
                    Counter,
               usrPPPBundleRxBadHeaders
                    Counter,
               usrPPPBundleRxTotalPkts
                    Counter,
               usrPPPBundleRxCompPkts
                    Counter,
               usrPPPBundleRxNonCompPkts
                    Counter,
               usrPPPBundleRxTotalOrigBytes
                    Counter,
               usrPPPBundleRxTotalLineBytes
                    Counter,
               usrPPPBundleTxEncryptPkts
                    Counter,
               usrPPPBundleTxNonEncryptPkts
                    Counter,
               usrPPPBundleRxEncryptPkts
                    Counter,
               usrPPPBundleRxNonEncryptPkts
                    Counter
          }


          usrPPPBundleInstance   OBJECT-TYPE
               SYNTAX    INTEGER
               ACCESS    read-only
               STATUS    mandatory
               DESCRIPTION
                         "The unique identifier of the instance of PPP
                         bundle to which this entry corresponds."
               ::= { usrPPPBundleEntry 1 }


          usrPPPBundleOperStatus   OBJECT-TYPE
               SYNTAX    INTEGER {opened(1), not-opened(2)}
               ACCESS    read-only
               STATUS    mandatory
               DESCRIPTION
                         "The operational status of the IP network
                         protocol. If the value of this object is up
                         then the finite state machine for the IP
                         network protocol has reached the Opened state."
               ::= { usrPPPBundleEntry 2 }


          usrPPPBundleUserProfile   OBJECT-TYPE
               SYNTAX    OCTET STRING
               ACCESS    read-only
               STATUS    mandatory
               DESCRIPTION
                         "The name of the User Profile that is being used
                         to contain the characteristics for this session.
                         The value of this object is meaningful only when
                         the link has reached the open state
                         (usrPPPBundleOperStatus is up)."
               ::= { usrPPPBundleEntry 3 }


          usrPPPBundleActiveLinks   OBJECT-TYPE
               SYNTAX    INTEGER(1..2147483647)
               ACCESS    read-only
               STATUS    mandatory
               DESCRIPTION
                         "The current number of links active for this
                         bundle. This count will be incremented when the
                         authentication control protocol for a new link
                         has reached the open state (usrPPPAuthOperStatus
                         is up). This count will be decremented when the
                         link is in a state where it can no longer pass
                         any application data packets."
               ::= { usrPPPBundleEntry 4 }


          usrPPPBundleLocalMMRU   OBJECT-TYPE
               SYNTAX    INTEGER(1..2147483647)
               ACCESS    read-only
               STATUS    mandatory
               DESCRIPTION
                         "The current value of the MMRU for the local PPP
                         Entity. This value is the MMRU that the remote
                         entity is using when sending packets to the
                         local PPP entity. The value of this object is
                         meaningful only when the link has reached the
                         open state (usrPPPBundleOperStatus is up)."
               ::= { usrPPPBundleEntry 5 }


          usrPPPBundleRemoteMMRU   OBJECT-TYPE
               SYNTAX    INTEGER(1..2147483647)
               ACCESS    read-only
               STATUS    mandatory
               DESCRIPTION
                         "The current value of the MMRU for the remote
                         PPP Entity. This value is the MMRU that the
                         local entity is using when sending packets to
                         the remote PPP entity. The value of this object
                         is meaningful only when the link has reached
                         the open state (usrPPPBundleOperStatus is up)."
               ::= { usrPPPBundleEntry 6 }


          usrPPPBundleLocalEndptClass   OBJECT-TYPE
               SYNTAX    INTEGER {
                         nullClass(1),
                         locallyAssignedAddress(2),
                         ipAddress(3),
                         ieeeMacAddress(4),
                         pppMagicNumberBlock(5),
                         networkDirNumber(6)
                    }
               ACCESS    read-only
               STATUS    mandatory
               DESCRIPTION
                         "The current value of the local Endpoint
                         Descriminator Class. This value indicates the type
                         of address being used as the identifier. The value
                         of this object is meaningful only when the link has
                         reached the open state (usrPPPBundleOperStatus is
                         up)."
               ::= { usrPPPBundleEntry 7 }


          usrPPPBundleLocalEndptLength   OBJECT-TYPE
               SYNTAX    INTEGER(0..20)
               ACCESS    read-only
               STATUS    mandatory
               DESCRIPTION
                         "The maximum length of the local Endpoint
                         Descriminator Address. The value of this object is
                         meaningful only when the link has reached the open
                         state (usrPPPBundleOperStatus is up)."
               ::= { usrPPPBundleEntry 8 }


          usrPPPBundleLocalEndptID   OBJECT-TYPE
               SYNTAX    OCTET STRING (SIZE(20))
               ACCESS    read-only
               STATUS    mandatory
               DESCRIPTION
                         "The value of the local Endpoint Descriminator
                         Address. The value of this object is meaningful
                         only when the link has reached the open state
                         (usrPPPBundleOperStatus is up)."
               ::= { usrPPPBundleEntry 9 }


          usrPPPBundleRemoteEndptClass   OBJECT-TYPE
               SYNTAX    INTEGER {
                         nullClass(1),
                         locallyAssignedAddress(2),
                         ipAddress(3),
                         ieeeMacAddress(4),
                         pppMagicNumberBlock(5),
                         networkDirNumber(6)
                    }
               ACCESS    read-only
               STATUS    mandatory
               DESCRIPTION
                         "The current value of the remote Endpoint
                         Descriminator Class. This value indicates the type
                         of address being used as the identifier. The value
                         of this object is meaningful only when the link has
                         reached the open state (usrPPPBundleOperStatus is
                         up)."
               ::= { usrPPPBundleEntry 10 }


          usrPPPBundleRemoteEndptLength   OBJECT-TYPE
               SYNTAX    INTEGER(0..20)
               ACCESS    read-only
               STATUS    mandatory
               DESCRIPTION
                         "The maximum length of the remote Endpoint
                         Descriminator Address. The value of this object is
                         meaningful only when the link has reached the open
                         state (usrPPPBundleOperStatus is up)."
               ::= { usrPPPBundleEntry 11 }


          usrPPPBundleRemoteEndptID   OBJECT-TYPE
               SYNTAX    OCTET STRING (SIZE(20))
               ACCESS    read-only
               STATUS    mandatory
               DESCRIPTION
                         "The value of the remote Endpoint Descriminator
                         Address. The value of this object is meaningful
                         only when the link has reached the open state
                         (usrPPPBundleOperStatus is up)."
               ::= { usrPPPBundleEntry 12 }


          usrPPPBundleTxTotalPkts   OBJECT-TYPE
               SYNTAX    Counter
               ACCESS    read-only
               STATUS    mandatory
               DESCRIPTION
                         "The total number of packets received from an upper
                         layer application for transmission over this bundle.
                         The value of this object is meaningful only when the
                         link has reached the open state
                         (usrPPPBundleOperStatus is up)."
               ::= { usrPPPBundleEntry 13 }


          usrPPPBundleTxCompPkts   OBJECT-TYPE
               SYNTAX    Counter
               ACCESS    read-only
               STATUS    mandatory
               DESCRIPTION
                         "The total number of packets received from an upper
                         layer application for transmission over this bundle
                         that were compressed by the PPP application before
                         handing the packet (or fragments) down to the lower
                         layer application. The value of this object is
                         meaningful only when the link has reached the open
                         state (usrPPPBundleOperStatus is up). Note that this
                         counter only represents packets that were compressed
                         over the BUNDLE (not links). If compression occurred
                         after the packet was fragmented (multilink), those
                         counters can be found at the link level."
               ::= { usrPPPBundleEntry 14 }


          usrPPPBundleTxNonCompPkts   OBJECT-TYPE
               SYNTAX    Counter
               ACCESS    read-only
               STATUS    mandatory
               DESCRIPTION
                         "The total number of packets received from an upper
                         layer application for transmission over this bundle
                         that were NOT compressed by the PPP application before
                         handing the packet (or fragments) down to the lower
                         layer application. The value of this object is
                         meaningful only when the link has reached the open
                         state (usrPPPBundleOperStatus is up). Note that this
                         counter only represents packets that were candidates
                         for compression over the BUNDLE (not links). If
                         link compression was enabled (multilink), the non-
                         compressed packet counters can be found at the link
                         level."
               ::= { usrPPPBundleEntry 15 }


          usrPPPBundleTxTotalOrigBytes   OBJECT-TYPE
               SYNTAX    Counter
               ACCESS    read-only
               STATUS    mandatory
               DESCRIPTION
                         "The total number of bytes received from an upper
                         layer application for transmission over this bundle.
                         This counter represents all data handed down to the
                         PPP application BEFORE compression takes place.
                         The value of this object is meaningful only when the
                         link has reached the open state
                         (usrPPPBundleOperStatus is up)."
               ::= { usrPPPBundleEntry 16 }


          usrPPPBundleTxTotalLineBytes   OBJECT-TYPE
               SYNTAX    Counter
               ACCESS    read-only
               STATUS    mandatory
               DESCRIPTION
                         "The total number of bytes that sent to a lower layer
                         application for transmission over this bundle.  This
                         counter represents all data to be handed down to
                         the lower layer application AFTER compression takes
                         place. The value of this object is meaningful only
                         when the link has reached the open state
                         (usrPPPBundleOperStatus is up)."
               ::= { usrPPPBundleEntry 17 }


          usrPPPBundleRxBadHeaders   OBJECT-TYPE
               SYNTAX    Counter
               ACCESS    read-only
               STATUS    mandatory
               DESCRIPTION
                         "The number of packets received with an
                         incorrect PPP Header (Address, Control,
                         or PID Field)."
               ::= { usrPPPBundleEntry 18 }


          usrPPPBundleRxTotalPkts   OBJECT-TYPE
               SYNTAX    Counter
               ACCESS    read-only
               STATUS    mandatory
               DESCRIPTION
                         "The total number of packets received from a lower
                         layer application over this bundle. The value of
                         this object is meaningful only when the link has
                         reached the open state
                         (usrPPPBundleOperStatus is up)."
               ::= { usrPPPBundleEntry 19 }


          usrPPPBundleRxCompPkts   OBJECT-TYPE
               SYNTAX    Counter
               ACCESS    read-only
               STATUS    mandatory
               DESCRIPTION
                         "The total number of packets received from a lower
                         layer application over this bundle that were
                         decompressed by the PPP application before handing
                         the packet to the upper layer application. The value
                         of this object is meaningful only when the link has
                         reached the open state (usrPPPBundleOperStatus is up).
                         Note that this counter only represents packets that
                         were decompressed over the BUNDLE (not links). If
                         decompression occurred before the packet was
                         reassembled (multilink), those counters can be found
                         at the link level."
               ::= { usrPPPBundleEntry 20 }


          usrPPPBundleRxNonCompPkts   OBJECT-TYPE
               SYNTAX    Counter
               ACCESS    read-only
               STATUS    mandatory
               DESCRIPTION
                         "The total number of packets received from a lower
                         layer application over this bundle that were NOT
                         decompressed by the PPP application before
                         handing the packet to the upper layer application.
                         The value of this object is meaningful only when
                         the link has reached the open state
                         (usrPPPBundleOperStatus is up). Note that this
                         counter only represents packets that were candidates
                         for decompression over the BUNDLE (not links). If
                         link (de)compression was enabled (multilink), the non-
                         compressed frame counters can be found at the link
                         level."
               ::= { usrPPPBundleEntry 21 }


          usrPPPBundleRxTotalOrigBytes   OBJECT-TYPE
               SYNTAX    Counter
               ACCESS    read-only
               STATUS    mandatory
               DESCRIPTION
                         "The total number of bytes that are to be handed up
                         to an upper layer application over this bundle. This
                         counter represents all data to be handed up AFTER
                         decompression and reassembly takes place. The value
                         of this object is meaningful only when the link has
                         reached the open state
                         (usrPPPBundleOperStatus is up)."
               ::= { usrPPPBundleEntry 22 }


          usrPPPBundleRxTotalLineBytes   OBJECT-TYPE
               SYNTAX    Counter
               ACCESS    read-only
               STATUS    mandatory
               DESCRIPTION
                         "The total number of bytes received from a lower
                         layer application over this bundle.  This
                         counter represents all data received BEFORE
                         decompression or reassembly takes place. The value
                         of this object is meaningful only when the link has
                         reached the open state
                         (usrPPPBundleOperStatus is up)."
               ::= { usrPPPBundleEntry 23 }


          usrPPPBundleTxEncryptPkts   OBJECT-TYPE
               SYNTAX    Counter
               ACCESS    read-only
               STATUS    mandatory
               DESCRIPTION
                         "The total number of packets received from an upper
                         layer application for transmission over this bundle
                         that were encrypted by the PPP application before
                         handing the packet (or fragments) down to the lower
                         layer application. The value of this object is
                         meaningful only when the link has reached the open
                         state (usrPPPBundleOperStatus is up). Note that this
                         counter only represents packets that were encrypted
                         over the BUNDLE (not links). If encryption occurred
                         after the packet was fragmented (multilink), those
                         counters can be found at the link level."
               ::= { usrPPPBundleEntry 24 }


          usrPPPBundleTxNonEncryptPkts   OBJECT-TYPE
               SYNTAX    Counter
               ACCESS    read-only
               STATUS    mandatory
               DESCRIPTION
                         "The total number of packets received from an upper
                         layer application for transmission over this bundle
                         that were NOT encrypted by the PPP application before
                         handing the packet (or fragments) down to the lower
                         layer application. The value of this object is
                         meaningful only when the link has reached the open
                         state (usrPPPBundleOperStatus is up). Note that this
                         counter only represents packets that were candidates
                         for encryption over the BUNDLE (not links). If
                         link encryption was enabled (multilink), the non-
                         encrypted packet counters can be found at the link
                         level."
               ::= { usrPPPBundleEntry 25 }


          usrPPPBundleRxEncryptPkts   OBJECT-TYPE
               SYNTAX    Counter
               ACCESS    read-only
               STATUS    mandatory
               DESCRIPTION
                         "The total number of packets received from a lower
                         layer application over this bundle that were
                         decrypted by the PPP application before handing
                         the packet to the upper layer application. The value
                         of this object is meaningful only when the link has
                         reached the open state (usrPPPBundleOperStatus is up).
                         Note that this counter only represents packets that
                         were decrypted over the BUNDLE (not links). If
                         decryption occurred before the packet was
                         reassembled (multilink), those counters can be found
                         at the link level."
               ::= { usrPPPBundleEntry 26 }


          usrPPPBundleRxNonEncryptPkts   OBJECT-TYPE
               SYNTAX    Counter
               ACCESS    read-only
               STATUS    mandatory
               DESCRIPTION
                         "The total number of packets received from a lower
                         layer application over this bundle that were NOT
                         decrypted by the PPP application before
                         handing the packet to the upper layer application.
                         The value of this object is meaningful only when
                         the link has reached the open state
                         (usrPPPBundleOperStatus is up). Note that this
                         counter only represents packets that were candidates
                         for decryption over the BUNDLE (not links). If
                         link decryption was enabled (multilink), the non-
                         encrypted frame counters can be found at the link
                         level."
               ::= { usrPPPBundleEntry 27 }


          --
          -- The PPP IP NCP Group.
          --
          -- The following object reflect the values of the option
          -- parameters used in the PPP IP Control Protocol
          --   usrPPPIpLocalToRemoteCompressionProtocol
          --   usrPPPIpRemoteToLocalCompressionProtocol
          --   usrPPPIpRemoteMaxSlotId
          --   usrPPPIpLocalMaxSlotId
          --   usrPPPIpLocalIpAddress
          --   usrPPPIpRemoteIpAddress
          -- These values are not available until after the PPP Option
          -- negotiation has completed, which is indicated by the link
          -- reaching the open state (i.e., usrPPPIpOperStatus is set to
          -- opened).
          --
          -- Therefore, when usrPPPIpOperStatus is not opened
          -- the contents of these objects is undefined. The value
          -- returned when accessing the objects is an implementation
          -- dependent issue.


          usrPPPIpTable   OBJECT-TYPE
               SYNTAX    SEQUENCE OF UsrPPPIpEntry
               ACCESS    not-accessible
               STATUS    mandatory
               DESCRIPTION
                         "Table containing the IP parameters and
                         statistics for the local PPP entity."
               ::= { usrPPPMl 2 }


          usrPPPIpEntry   OBJECT-TYPE
               SYNTAX    UsrPPPIpEntry
               ACCESS    not-accessible
               STATUS    mandatory
               DESCRIPTION
                         "IPCP status information for the PPP bundle."
               INDEX     { usrPPPBundleInstance }
               ::= { usrPPPIpTable 1 }


          UsrPPPIpEntry ::= SEQUENCE {
               usrPPPIpOperStatus
                    INTEGER,
               usrPPPIpLocalToRemoteCompressionProtocol
                    INTEGER,
               usrPPPIpRemoteToLocalCompressionProtocol
                    INTEGER,
               usrPPPIpRemoteMaxSlotId
                    INTEGER,
               usrPPPIpLocalMaxSlotId
                    INTEGER,
               usrPPPIpLocalIpAddress
                    IpAddress,
               usrPPPIpRemoteIpAddress
                    IpAddress
          }


          usrPPPIpOperStatus   OBJECT-TYPE
               SYNTAX    INTEGER {opened(1), not-opened(2)}
               ACCESS    read-only
               STATUS    mandatory
               DESCRIPTION
                         "The operational status of the IP network
                         protocol. If the value of this object is up
                         then the finite state machine for the IP
                         network protocol has reached the Opened state."
               ::= { usrPPPIpEntry 1 }


          usrPPPIpLocalToRemoteCompressionProtocol   OBJECT-TYPE
               SYNTAX    INTEGER {
                         none(1),
                         vj-tcp(2)
                    }
               ACCESS    read-only
               STATUS    mandatory
               DESCRIPTION
                         "The IP compression protocol that the local
                         PPP-IP entity uses when sending packets to the
                         remote PPP-IP entity. The value of this object
                         is meaningful only when the link has reached
                         the open state (usrPPPIpOperStatus is opened)."
               ::= { usrPPPIpEntry 2 }


          usrPPPIpRemoteToLocalCompressionProtocol   OBJECT-TYPE
               SYNTAX    INTEGER {
                         none(1),
                         vj-tcp(2)
                    }
               ACCESS    read-only
               STATUS    mandatory
               DESCRIPTION
                         "The IP compression protocol that the remote
                         PPP-IP entity uses when sending packets to the
                         local PPP-IP entity. The value of this object
                         is meaningful only when the link has reached
                         the open state (usrPPPIpOperStatus is opened)."
               ::= { usrPPPIpEntry 3 }


          usrPPPIpRemoteMaxSlotId   OBJECT-TYPE
               SYNTAX    INTEGER(0..255)
               ACCESS    read-only
               STATUS    mandatory
               DESCRIPTION
                         "The Max-Slot-Id parameter that the remote node
                         has advertised and that is in use on the link.
                         If vj-tcp header compression is not in use on
                         the link then the value of this object shall be
                         0. The value of this object is meaningful only
                         when the link has reached the open state
                         (usrPPPIpOperStatus is opened)."
               ::= { usrPPPIpEntry 4 }


          usrPPPIpLocalMaxSlotId   OBJECT-TYPE
               SYNTAX    INTEGER(0..255)
               ACCESS    read-only
               STATUS    mandatory
               DESCRIPTION
                         "The Max-Slot-Id parameter that the local node
                         has advertised and that is in use on the link.
                         If vj-tcp header compression is not in use on
                         the link then the value of this object shall be
                         0. The value of this object is meaningful only
                         when the link has reached the open state
                         (usrPPPIpOperStatus is opened)."
               ::= { usrPPPIpEntry 5 }


          usrPPPIpLocalIpAddress    OBJECT-TYPE
               SYNTAX    IpAddress
               ACCESS    read-only
               STATUS    mandatory
               DESCRIPTION
                         "The IP Address that the local node was either
                         configured for or assigned by the remote node.
                         The value of this object is meaningful only
                         when the link has reached the open state
                         (usrPPPIpOperStatus is opened)."
               ::= { usrPPPIpEntry 6 }


          usrPPPIpRemoteIpAddress    OBJECT-TYPE
               SYNTAX    IpAddress
               ACCESS    read-only
               STATUS    mandatory
               DESCRIPTION
                         "The IP Address that the remote node supplied
                         to the local node during link negotiation.
                         The value of this object is meaningful only
                         when the link has reached the open state
                         (usrPPPIpOperStatus is opened)."
               ::= { usrPPPIpEntry 7 }


          --
          -- The PPP IPX NCP Group.
          --
          -- The following object reflect the values of the option
          -- parameters used in the PPP IPX Control Protocol
          --   usrPPPIpxLocalIpxNetAddress
          --   usrPPPIpxRemoteIpxNetAddress
          --   usrPPPIpxLocalIpxNodeAddress
          --   usrPPPIpxRemoteIpxNodeAddress
          -- These values are not available until after the PPP Option
          -- negotiation has completed, which is indicated by the link
          -- reaching the open state (i.e., usrPPPIpxOperStatus is set to
          -- opened).
          --
          -- Therefore, when usrPPPIpxOperStatus is not opened
          -- the contents of these objects is undefined. The value
          -- returned when accessing the objects is an implementation
          -- dependent issue.


          usrPPPIpxTable  OBJECT-TYPE
               SYNTAX    SEQUENCE OF UsrPPPIpxEntry
               ACCESS    not-accessible
               STATUS    mandatory
               DESCRIPTION
                         "Table containing the IPX parameters and
                         statistics for the local PPP entity."
               ::= { usrPPPMl 3 }


          usrPPPIpxEntry  OBJECT-TYPE
               SYNTAX    UsrPPPIpxEntry
               ACCESS    not-accessible
               STATUS    mandatory
               DESCRIPTION
                         "IPXCP status information for the PPP bundle."
               INDEX     { usrPPPBundleInstance }
               ::= { usrPPPIpxTable 1 }


          UsrPPPIpxEntry ::= SEQUENCE {
               usrPPPIpxOperStatus
                    INTEGER,
               usrPPPIpxLocalIpxNetAddress
                    IpxAddress,
               usrPPPIpxRemoteIpxNetAddress
                    IpxAddress,
               usrPPPIpxLocalIpxNodeAddress
                    MacAddress,
               usrPPPIpxRemoteIpxNodeAddress
                    MacAddress
          }


          usrPPPIpxOperStatus   OBJECT-TYPE
               SYNTAX    INTEGER {opened(1), not-opened(2)}
               ACCESS    read-only
               STATUS    mandatory
               DESCRIPTION
                         "The operational status of the IPX network
                         protocol. If the value of this object is up
                         then the finite state machine for the IPX
                         network protocol has reached the Opened state."
               ::= { usrPPPIpxEntry 1 }


          usrPPPIpxLocalIpxNetAddress    OBJECT-TYPE
               SYNTAX    IpxAddress
               ACCESS    read-only
               STATUS    mandatory
               DESCRIPTION
                         "The IPX Network Address that the local node was
                         either configured for or assigned by the remote
                         node. The value of this object is meaningful
                         only when the link has reached the open state
                         (usrPPPIpxOperStatus is opened)."
               ::= { usrPPPIpxEntry 2 }


          usrPPPIpxRemoteIpxNetAddress    OBJECT-TYPE
               SYNTAX    IpxAddress
               ACCESS    read-only
               STATUS    mandatory
               DESCRIPTION
                         "The IPX Network Address that the remote node
                         supplied to the local node during link negotiation.
                         The value of this object is meaningful only
                         when the link has reached the open state
                         (usrPPPIpxOperStatus is opened)."
               ::= { usrPPPIpxEntry 3 }


          usrPPPIpxLocalIpxNodeAddress    OBJECT-TYPE
               SYNTAX    MacAddress
               ACCESS    read-only
               STATUS    mandatory
               DESCRIPTION
                         "The IPX Node Address that the local node was
                         either configured for or assigned by the remote
                         node. The value of this object is meaningful
                         only when the link has reached the open state
                         (usrPPPIpxOperStatus is opened)."
               ::= { usrPPPIpxEntry 4 }


          usrPPPIpxRemoteIpxNodeAddress    OBJECT-TYPE
               SYNTAX    MacAddress
               ACCESS    read-only
               STATUS    mandatory
               DESCRIPTION
                         "The IPX Node Address that the remote node
                         supplied to the local node during link negotiation.
                         The value of this object is meaningful only
                         when the link has reached the open state
                         (usrPPPIpxOperStatus is opened)."
               ::= { usrPPPIpxEntry 5 }


          --
          -- The PPP AppleTalk NCP Group.
          --
          -- The following object reflect the values of the option
          -- parameters used in the PPP AppleTalk Control Protocol
          --   usrPPPAtLocalAtNetAddress
          --   usrPPPAtRemoteAtNetAddress
          --   usrPPPAtLocalAtNodeAddress
          --   usrPPPAtRemoteAtNodeAddress
          -- These values are not available until after the PPP Option
          -- negotiation has completed, which is indicated by the link
          -- reaching the open state (i.e., usrPPPAtOperStatus is set to
          -- opened).
          --
          -- Therefore, when usrPPPAtOperStatus is not opened
          -- the contents of these objects is undefined. The value
          -- returned when accessing the objects is an implementation
          -- dependent issue.


          usrPPPAtTable  OBJECT-TYPE
               SYNTAX    SEQUENCE OF UsrPPPAtEntry
               ACCESS    not-accessible
               STATUS    mandatory
               DESCRIPTION
                         "Table containing the AppleTalk parameters and
                         statistics for the local PPP entity."
               ::= { usrPPPMl 4 }


          usrPPPAtEntry  OBJECT-TYPE
               SYNTAX    UsrPPPAtEntry
               ACCESS    not-accessible
               STATUS    mandatory
               DESCRIPTION
                         "ATCP status information for the PPP bundle."
               INDEX     { usrPPPBundleInstance }
               ::= { usrPPPAtTable 1 }


          UsrPPPAtEntry ::= SEQUENCE {
               usrPPPAtOperStatus
                    INTEGER,
               usrPPPAtLocalAtNetAddress
                    INTEGER,
               usrPPPAtRemoteAtNetAddress
                    INTEGER,
               usrPPPAtLocalAtNodeAddress
                    INTEGER,
               usrPPPAtRemoteAtNodeAddress
                    INTEGER
          }


          usrPPPAtOperStatus   OBJECT-TYPE
               SYNTAX    INTEGER {opened(1), not-opened(2)}
               ACCESS    read-only
               STATUS    mandatory
               DESCRIPTION
                         "The operational status of the AppleTalk network
                         protocol. If the value of this object is up
                         then the finite state machine for the AppleTalk
                         network protocol has reached the Opened state."
               ::= { usrPPPAtEntry 1 }


          usrPPPAtLocalAtNetAddress    OBJECT-TYPE
               SYNTAX    INTEGER
               ACCESS    read-only
               STATUS    mandatory
               DESCRIPTION
                         "The AppleTalk Network Address that the local node
                         was either configured for or assigned by the remote
                         node. The value of this object is meaningful
                         only when the link has reached the open state
                         (usrPPPAtOperStatus is opened)."
               ::= { usrPPPAtEntry 2 }


          usrPPPAtRemoteAtNetAddress    OBJECT-TYPE
               SYNTAX    INTEGER
               ACCESS    read-only
               STATUS    mandatory
               DESCRIPTION
                         "The AppleTalk Network Address that the remote node
                         supplied to the local node during link negotiation.
                         The value of this object is meaningful only
                         when the link has reached the open state
                         (usrPPPAtOperStatus is opened)."
               ::= { usrPPPAtEntry 3 }


          usrPPPAtLocalAtNodeAddress    OBJECT-TYPE
               SYNTAX    INTEGER
               ACCESS    read-only
               STATUS    mandatory
               DESCRIPTION
                         "The AppleTalk Node Address that the local node was
                         either configured for or assigned by the remote
                         node. The value of this object is meaningful
                         only when the link has reached the open state
                         (usrPPPAtOperStatus is opened)."
               ::= { usrPPPAtEntry 4 }


          usrPPPAtRemoteAtNodeAddress    OBJECT-TYPE
               SYNTAX    INTEGER
               ACCESS    read-only
               STATUS    mandatory
               DESCRIPTION
                         "The AppleTalk Node Address that the remote node
                         supplied to the local node during link negotiation.
                         The value of this object is meaningful only
                         when the link has reached the open state
                         (usrPPPAtOperStatus is opened)."
               ::= { usrPPPAtEntry 5 }


          --
          -- The PPP Bridge NCP Group.
          --
          -- The following object reflect the values of the option
          -- parameters used in the PPP Link Control Protocol
          --   usrPPPBridgeLocalToRemoteTinygramCompression
          --   usrPPPBridgeRemoteToLocalTinygramCompression
          --   usrPPPBridgeLocalToRemoteLanId
          --   usrPPPBridgeRemoteToLocalLanId
          --   usrPPPBridgeMacType
          --
          -- These values are not available until after the PPP Option
          -- negotiation has completed, which is indicated by the link
          -- reaching the open state (i.e. usrPPPBridgeOperStatus is set to
          -- opened).
          --
          -- Therefore, when usrPPPBridgeOperStatus is not opened
          -- the contents of these objects is undefined. The value
          -- returned when accessing the objects is an implementation
          -- dependent issue.


          usrPPPBridgeTable   OBJECT-TYPE
               SYNTAX    SEQUENCE OF UsrPPPBridgeEntry
               ACCESS    not-accessible
               STATUS    mandatory
               DESCRIPTION
                         "Table containing the parameters and statistics
                         for the local PPP entity that are related to
                         the operation of Bridging over the PPP."
               ::= { usrPPPMl 5 }


          usrPPPBridgeEntry   OBJECT-TYPE
               SYNTAX    UsrPPPBridgeEntry
               ACCESS    not-accessible
               STATUS    mandatory
               DESCRIPTION
                         "Bridging information for a particular PPP
                         link."
               INDEX     { usrPPPBundleInstance }
               ::= { usrPPPBridgeTable 1 }


          UsrPPPBridgeEntry ::= SEQUENCE {
               usrPPPBridgeOperStatus
                    INTEGER,
               usrPPPBridgeLocalToRemoteTinygramCompression
                    INTEGER,
               usrPPPBridgeRemoteToLocalTinygramCompression
                    INTEGER,
               usrPPPBridgeLocalToRemoteLanId
                    INTEGER,
               usrPPPBridgeRemoteToLocalLanId
                    INTEGER,
               usrPPPBridgeMacType
                    INTEGER
          }


          usrPPPBridgeOperStatus   OBJECT-TYPE
               SYNTAX    INTEGER {opened(1), not-opened(2)}
               ACCESS    read-only
               STATUS    mandatory
               DESCRIPTION
                         "The operational status of the Bridge network
                         protocol. If the value of this object is up
                         then the finite state machine for the Bridge
                         network protocol has reached the Opened state."
               ::= { usrPPPBridgeEntry 1 }


          usrPPPBridgeLocalToRemoteTinygramCompression   OBJECT-TYPE
               SYNTAX    INTEGER { true(1), false(2) }
               ACCESS    read-only
               STATUS    mandatory
               DESCRIPTION
                         "Indicates whether the local node will perform
                         Tinygram Compression when sending packets to
                         the remote entity. If false then the local
                         entity will not perform Tinygram Compression.
                         If true then the local entity will perform
                         Tinygram Compression. The value of this object
                         is meaningful only when the link has reached
                         the open state (usrPPPBridgeOperStatus is
                         opened)."
               REFERENCE
                         "Section 6.7, Tinygram Compression Option, of
                         RFC1220"
               ::= { usrPPPBridgeEntry 2 }


          usrPPPBridgeRemoteToLocalTinygramCompression   OBJECT-TYPE
               SYNTAX    INTEGER { true(1), false(2) }
               ACCESS    read-only
               STATUS    mandatory
               DESCRIPTION
                         "If false then the remote entity is not
                         expected to perform Tinygram Compression. If
                         true then the remote entity is expected to
                         perform Tinygram Compression. The value of this
                         object is meaningful only when the link has
                         reached the open state (usrPPPBridgeOperStatus is
                         opened)."
               REFERENCE
                         "Section 6.7, Tinygram Compression Option, of
                         RFC1220"
               ::= { usrPPPBridgeEntry 3 }

          usrPPPBridgeLocalToRemoteLanId   OBJECT-TYPE
               SYNTAX    INTEGER { true(1), false(2) }
               ACCESS    read-only
               STATUS    mandatory
               DESCRIPTION
                         "Indicates whether the local node will include
                         the LAN Identification field in transmitted
                         packets or not. If false then the local node
                         will not transmit this field, true means
                         that the field will be transmitted. The value
                         of this object is meaningful only when the link
                         has reached the open state (usrPPPBridgeOperStatus
                         is opened)."
               REFERENCE
                         "Section 6.8, LAN Identification Option, of
                         RFC1220"
               ::= { usrPPPBridgeEntry 4 }


          usrPPPBridgeRemoteToLocalLanId   OBJECT-TYPE
               SYNTAX    INTEGER { true(1), false(2) }
               ACCESS    read-only
               STATUS    mandatory
               DESCRIPTION
                         "Indicates whether the remote node has
                         indicated that it will include the LAN
                         Identification field in transmitted packets or
                         not. If false then the field will not be
                         transmitted, if true then the field will be
                         transmitted. The value of this object is
                         meaningful only when the link has reached the
                         open state (usrPPPBridgeOperStatus is opened)."
               REFERENCE
                         "Section 6.8, LAN Identification Option, of
                         RFC1220"
               ::= { usrPPPBridgeEntry 5 }


          usrPPPBridgeMacType   OBJECT-TYPE
               SYNTAX    INTEGER { ieee8023-ethernet(1), ieee8025(3) }
               ACCESS    read-only
               STATUS    mandatory
               DESCRIPTION
                         "Indicates which MAC framing type the local node
                         will accept and process properly. The value of
                         this object is meaningful only when the link has
                         reached the open state (usrPPPBridgeOperStatus
                         is opened)."
               REFERENCE
                         "Section 6.6, MAC Type Support Selection, of
                         RFC1212."
               ::= { usrPPPBridgeEntry 6 }


          --
          -- The PPP Compression CP Group.
          --
          -- The following object reflect the values of the option
          -- parameters used in the PPP Compression Control Protocol
          --   usrPPPCompOperStatus
          --   usrPPPCompAlgorithm
          -- These values are not available until after the PPP Option
          -- negotiation has completed, which is indicated by the link
          -- reaching the open state (i.e., usrPPPCompOperStatus is set to
          -- opened).
          --
          -- Therefore, when usrPPPCompOperStatus is not opened
          -- the contents of these objects is undefined. The value
          -- returned when accessing the objects is an implementation
          -- dependent issue.


          usrPPPCompTable   OBJECT-TYPE
               SYNTAX    SEQUENCE OF UsrPPPCompEntry
               ACCESS    not-accessible
               STATUS    mandatory
               DESCRIPTION
                         "Table containing the Compression parameters and
                         statistics for the local PPP entity."
               ::= { usrPPPMl 6 }


          usrPPPCompEntry   OBJECT-TYPE
               SYNTAX    UsrPPPCompEntry
               ACCESS    not-accessible
               STATUS    mandatory
               DESCRIPTION
                         "CCP status information for the PPP bundle."
               INDEX     { usrPPPBundleInstance }
               ::= { usrPPPCompTable 1 }


          UsrPPPCompEntry ::= SEQUENCE {
               usrPPPCompOperStatus
                    INTEGER,
               usrPPPCompAlgorithm
                    INTEGER
          }


          usrPPPCompOperStatus   OBJECT-TYPE
               SYNTAX    INTEGER {opened(1), not-opened(2), paused(3)}
               ACCESS    read-only
               STATUS    mandatory
               DESCRIPTION
                         "The operational status of the Compression control
                         protocol. If the value of this object is up
                         then the finite state machine for the Compression
                         control protocol has reached the Opened state."
               ::= { usrPPPCompEntry 1 }


          usrPPPCompAlgorithm   OBJECT-TYPE
               SYNTAX    INTEGER {
                         none(1),
                         microsoft(2),
                         ascend(3),
                         stac(4),
                         auto(5),
                         deflate(6)
                    }
               ACCESS    read-only
               STATUS    mandatory
               DESCRIPTION
                         "The compression protocol that the local
                         PPP entity uses when sending packets to the
                         remote PPP entity. The value of this object
                         is meaningful only when the link has reached
                         the open state (usrPPPCompOperStatus is opened)."
               ::= { usrPPPCompEntry 2 }

          --
          -- The PPP Encryption Group.
          --
          -- The following object reflect the values of the option
          -- parameters used in the PPP Encryption.  Currently only
		  -- MPPE is supported
          --   usrPPPEncryptOperStatus
          --   usrPPPEncryptAlgorithm
          -- These values are not available until after the PPP Option
          -- negotiation has completed, which is indicated by the link
          -- reaching the open state (i.e., usrPPPEncryptOperStatus is set to
          -- opened).
          --
          -- Therefore, when usrPPPEncryptOperStatus is not opened
          -- the contents of these objects is undefined. The value
          -- returned when accessing the objects is an implementation
          -- dependent issue.


          usrPPPEncryptTable   OBJECT-TYPE
               SYNTAX    SEQUENCE OF UsrPPPEncryptEntry
               ACCESS    not-accessible
               STATUS    mandatory
               DESCRIPTION
                         "Table containing the Encryption parameters and
                         statistics for the local PPP entity."
               ::= { usrPPPMl 7 }


          usrPPPEncryptEntry   OBJECT-TYPE
               SYNTAX    UsrPPPEncryptEntry
               ACCESS    not-accessible
               STATUS    mandatory
               DESCRIPTION
                         "CCP (encryption) status information for the PPP bundle."
               INDEX     { usrPPPBundleInstance }
               ::= { usrPPPEncryptTable 1 }


          UsrPPPEncryptEntry ::= SEQUENCE {
               usrPPPEncryptOperStatus
                    INTEGER,
               usrPPPEncryptAlgorithm
                    INTEGER
          }


          usrPPPEncryptOperStatus   OBJECT-TYPE
               SYNTAX    INTEGER {opened(1), not-opened(2)}
               ACCESS    read-only
               STATUS    mandatory
               DESCRIPTION
                         "The operational status of the Compression control
                         protocol when used to negotiate MPPE encryption. 
						 If the value of this object is up
                         then the finite state machine for the Compression
                         control protocol has reached the Opened state and
						 MPPE has been negotiated."
               ::= { usrPPPEncryptEntry 1 }


          usrPPPEncryptAlgorithm   OBJECT-TYPE
               SYNTAX    INTEGER {
                         none(1),
                         microsoft40bit(2),
                         microsoft128bit(3),
                         strongest(4),
                         try(5)
                    }
               ACCESS    read-only
               STATUS    mandatory
               DESCRIPTION
                         "The encryption protocol that the local
                         PPP entity uses when sending packets to the
                         remote PPP entity. The value of this object
                         is meaningful only when the link has reached
                         the open state (usrPPPEncryptOperStatus is opened)."
               ::= { usrPPPEncryptEntry 2 }

	  usrPPPBaseProtFieldComp OBJECT-TYPE
              SYNTAX  INTEGER {
                        enabled(1),
                        disabled(0)
                      }
              ACCESS   read-write
              STATUS   mandatory
              DESCRIPTION
                      "Indicates whether PPP Protocol field compression is
                       enabled/disabled."
              --CONFIGURABLE
              ::= { usrPPPBase 15 }
 
       usrPPPBaseAddrFieldComp OBJECT-TYPE
              SYNTAX  INTEGER {
                        enabled(1),
                        disabled(0)
                      }
              ACCESS   read-write
              STATUS   mandatory
              DESCRIPTION
                      "Indicates whether PPP Address field compression is
                       enabled/disabled."
              --CONFIGURABLE
              ::= { usrPPPBase 16 }

    	usrPPPBaseBacpBap OBJECT-TYPE
              SYNTAX  INTEGER {
                        enabled(1),
                        disabled(0)
                      }
              ACCESS   read-write
              STATUS   mandatory
              DESCRIPTION
                      "Indicates whether PPP Bacp and Bap enabled/disabled."
              --CONFIGURABLE
              ::= { usrPPPBase 17 }
 
       usrPPPBaseBapPhone OBJECT-TYPE
              SYNTAX  OCTET STRING (SIZE (0..240))
              ACCESS   read-write
              STATUS   mandatory
              DESCRIPTION
                      "The hunt_group phone number to be sent in BAP call-response"
              --CONFIGURABLE
              ::= { usrPPPBase 18 }
 
       usrPPPBaseMPPP OBJECT-TYPE
              SYNTAX  INTEGER {
                        enabled(1),
                        disabled(0)
                      }
              ACCESS   read-write
              STATUS   mandatory
              DESCRIPTION
                      "Indicates whether PPP Mutlilink is Enabled/Disabled"
              --CONFIGURABLE
              ::= { usrPPPBase 19 }
 
 
       usrPPPBaseReceiveACCM OBJECT-TYPE
              SYNTAX  INTEGER {
                        enabled(1),
                        disabled(0)
                      }
              ACCESS   read-write
              STATUS   mandatory
              DESCRIPTION
                      "Indicates whether PPP receive ACCM is Enabled/Disabled"
              --CONFIGURABLE
              ::= { usrPPPBase 20 }

    	usrPPPBaseNegCallback OBJECT-TYPE
              SYNTAX  INTEGER {
                        enabled(1),
                        disabled(0)
                      }
              ACCESS   read-write
              STATUS   mandatory
              DESCRIPTION
                      "Indicates whether PPP CBCP  enabled/disabled."
              --CONFIGURABLE
              ::= { usrPPPBase 21 }

	usrPPPSystemMRU   OBJECT-TYPE
               SYNTAX    INTEGER(128..1518)
               ACCESS    read-write
               STATUS    mandatory
               DESCRIPTION
                         "The current value of the MRU for the local PPP
                         Entity. This value is the MRU that the remote
                         entity is using when sending packets to the
                         local PPP entity." 
	       DEFVAL 	 { 1514 }
			--CONFIGURABLE
               ::= { usrPPPBase 22 }


    	usrPPPBaseRADIUSChallengeInPAP OBJECT-TYPE
              SYNTAX  INTEGER {
                        enabled(1),
                        disabled(0)
                      }
              ACCESS   read-write
              STATUS   mandatory
              DESCRIPTION
                      "Special processing of RADIUS Challenge, if the authe
					  ntication is PAP"
              --CONFIGURABLE
              ::= { usrPPPBase 23 }

		usrPPPBasePapRetries OBJECT-TYPE
			SYNTAX	INTEGER(1..10)
			ACCESS	read-write
			STATUS	mandatory
			DESCRIPTION
				"Indicates the retry limit for PAP protocol. Number of times
				PAP request shall be re-transmitted before timing out"
			DEFVAL { 3 }
			--CONFIGURABLE
			::= { usrPPPBase 24 }

       usrPPPBaseSendEDO OBJECT-TYPE
              SYNTAX  INTEGER {
                        enabled(1),
                        disabled(0)
                      }
              ACCESS   read-write
              STATUS   mandatory
              DESCRIPTION
                      "Indicates whether PPP should send EDO for a multilink call or not."
              --CONFIGURABLE
              ::= { usrPPPBase 26 }


END


--
--    usr_ppplink.mib - The USR PPP Link MIB module
--
--
-- Author:         <Joe Kralowetz>
--
-- $Id: usr_ppplink.mib,v 1.4.10.4 1998/01/07 22:16:09 jhaag Exp $
--
--  | Copyright (c) 1995 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-PPPLINK-MIB DEFINITIONS ::= BEGIN

          IMPORTS
               Counter
                    FROM RFC1155-SMI
               OBJECT-TYPE
                    FROM RFC-1212
               usrPPP
                    FROM USR-DEFINITIONS-MIB
               usrPPPBundleInstance
                    FROM USR-PPPML-MIB;

          usrPPPLk OBJECT IDENTIFIER ::= { usrPPP 3 }


          --
          -- The PPP Link Group.
          --
          -- The following objects reflect the values of the option
          -- parameters used over the PPP Link
          --   usrPPPLinkInstance
          --   usrPPPLinkOperStatus
          --   usrPPPLinkPhysicalIndex
          --   usrPPPLinkLocalMRU
          --   usrPPPLinkRemoteMRU
          --   usrPPPLinkLocalToPeerACCMap
          --   usrPPPLinkPeerToLocalACCMap
          --   usrPPPLinkLocalToRemoteProtocolCompression
          --   usrPPPLinkRemoteToLocalProtocolCompression
          --   usrPPPLinkLocalToRemoteACCompression
          --   usrPPPLinkRemoteToLocalACCompression
          --   usrPPPLinkTxTotalFrames
          --   usrPPPLinkTxTotalBytes
          --   usrPPPLinkRxPacketTooLongs
          --   usrPPPLinkRxTotalFrames
          --   usrPPPLinkRxTotalBytes
          --
          -- These values are not available until after the PPP Option
          -- negotiation has completed, which is indicated by the link
          -- reaching the open state (i.e., ifOperStatus is set to
          -- up).
          --
          -- Therefore, when ifOperStatus is not up
          -- the contents of these objects is undefined. The value
          -- returned when accessing the objects is an implementation
          -- dependent issue.


          usrPPPLinkTable   OBJECT-TYPE
               SYNTAX    SEQUENCE OF UsrPPPLinkEntry
               ACCESS    not-accessible
               STATUS    mandatory
               DESCRIPTION
                         "Table containing the Link parameters and
                         statistics for a local PPP entity."
               ::= { usrPPPLk 1 }


          usrPPPLinkEntry   OBJECT-TYPE
               SYNTAX    UsrPPPLinkEntry
               ACCESS    not-accessible
               STATUS    mandatory
               DESCRIPTION
                         "Status information for a PPP link."
               INDEX     { usrPPPBundleInstance, usrPPPLinkInstance }
               ::= { usrPPPLinkTable 1 }


          UsrPPPLinkEntry ::= SEQUENCE {
               usrPPPLinkInstance
                    INTEGER,
               usrPPPLinkOperStatus
                    INTEGER,
               usrPPPLinkPhysicalIndex
                    INTEGER,
               usrPPPLinkInterfaceName
                    OCTET STRING,
               usrPPPLinkLocalMRU
                    INTEGER,
               usrPPPLinkRemoteMRU
                    INTEGER,
               usrPPPLinkLocalToPeerACCMap
                    OCTET STRING,
               usrPPPLinkPeerToLocalACCMap
                    OCTET STRING,
               usrPPPLinkLocalToRemoteProtocolCompression
                    INTEGER,
               usrPPPLinkRemoteToLocalProtocolCompression
                    INTEGER,
               usrPPPLinkLocalToRemoteACCompression
                    INTEGER,
               usrPPPLinkRemoteToLocalACCompression
                    INTEGER,
               usrPPPLinkTxTotalFrames
                    Counter,
               usrPPPLinkTxTotalBytes
                    Counter,
               usrPPPLinkRxPacketTooLongs
                    Counter,
               usrPPPLinkRxTotalFrames
                    Counter,
               usrPPPLinkRxTotalBytes
                    Counter
          }


          usrPPPLinkInstance   OBJECT-TYPE
               SYNTAX    INTEGER
               ACCESS    read-only
               STATUS    mandatory
               DESCRIPTION
                         "The unique identifier of the instance of PPP
                         link to which this entry corresponds."
               ::= { usrPPPLinkEntry 1 }


          usrPPPLinkOperStatus   OBJECT-TYPE
               SYNTAX    INTEGER {opened(1), not-opened(2)}
               ACCESS    read-only
               STATUS    mandatory
               DESCRIPTION
                         "The operational status of the Link control
                         protocol. If the value of this object is up
                         then the finite state machine for the Link
                         control protocol has reached the Opened state."
               ::= { usrPPPLinkEntry 2 }


          usrPPPLinkPhysicalIndex   OBJECT-TYPE
               SYNTAX    INTEGER(0..2147483647)
               ACCESS    read-only
               STATUS    mandatory
               DESCRIPTION
                         "The value of ifIndex that identifies the
                         lower-level interface over which this PPP Link
                         is operating. This interface would usually be
                         an HDLC or RS-232 type of interface. If there
                         is no lower-layer interface element, or there
                         is no ifEntry for the element, or the element
                         can not be identified, then the value of this
                         object is 0."
               ::= { usrPPPLinkEntry 3 }


          usrPPPLinkInterfaceName   OBJECT-TYPE
               SYNTAX    OCTET STRING
               ACCESS    read-only
               STATUS    mandatory
               DESCRIPTION
                         "The value of the Name that identifies the
                         lower-level interface over which this PPP Link
                         is operating. This interface would usually be
                         an HDLC or RS-232 type of interface. If there
                         is no lower-layer interface element, or there
                         is no ifEntry for the element, or the element
                         can not be identified, then the value of this
                         object is 0."
               ::= { usrPPPLinkEntry 4 }

          usrPPPLinkLocalMRU   OBJECT-TYPE
               SYNTAX    INTEGER(1..2147483647)
               ACCESS    read-only
               STATUS    mandatory
               DESCRIPTION
                         "The current value of the MRU for the local PPP
                         Entity. This value is the MRU that the remote
                         entity is using when sending packets to the
                         local PPP entity. The value of this object is
                         meaningful only when the link has reached the
                         open state (usrPPPLinkOperStatus is up)."
               ::= { usrPPPLinkEntry 5 }


          usrPPPLinkRemoteMRU   OBJECT-TYPE
               SYNTAX    INTEGER(1..2147483647)
               ACCESS    read-only
               STATUS    mandatory
               DESCRIPTION
                         "The current value of the MRU for the remote
                         PPP Entity. This value is the MRU that the
                         local entity is using when sending packets to
                         the remote PPP entity. The value of this object
                         is meaningful only when the link has reached
                         the open state (usrPPPLinkOperStatus is up)."
               ::= { usrPPPLinkEntry 6 }


          usrPPPLinkLocalToPeerACCMap   OBJECT-TYPE
               SYNTAX    OCTET STRING (SIZE (4))
               ACCESS    read-only
               STATUS    mandatory
               DESCRIPTION
                         "The current value of the ACC Map used for
                         sending packets from the local PPP entity to
                         the remote PPP entity. The value of this object
                         is meaningful only when the link has reached
                         the open state (usrPPPLinkOperStatus is up)."
               ::= { usrPPPLinkEntry 7 }


          usrPPPLinkPeerToLocalACCMap   OBJECT-TYPE
               SYNTAX    OCTET STRING (SIZE (4))
               ACCESS    read-only
               STATUS    mandatory
               DESCRIPTION
                         "The ACC Map used by the remote PPP entity when
                         transmitting packets to the local PPP entity.
                         The value of this object is meaningful only
                         when the link has reached the open state
                         (usrPPPLinkOperStatus is up)."
               ::= { usrPPPLinkEntry 8 }


          usrPPPLinkLocalToRemoteProtocolCompression
               OBJECT-TYPE
               SYNTAX    INTEGER {
                         enabled(1),
                         disabled(2)
                    }
               ACCESS    read-only
               STATUS    mandatory
               DESCRIPTION
                         "Indicates whether the local PPP entity will
                         use Protocol Compression when transmitting
                         packets to the remote PPP entity. The value of
                         this object is meaningful only when the link
                         has reached the open state (usrPPPLinkOperStatus
                         is up)."
               ::= { usrPPPLinkEntry 9 }


          usrPPPLinkRemoteToLocalProtocolCompression
               OBJECT-TYPE
               SYNTAX    INTEGER {
                         enabled(1),
                         disabled(2)
                    }
               ACCESS    read-only
               STATUS    mandatory
               DESCRIPTION
                         "Indicates whether the remote PPP entity will
                         use Protocol Compression when transmitting
                         packets to the local PPP entity. The value of
                         this object is meaningful only when the link
                         has reached the open state (usrPPPLinkOperStatus
                         is up)."
               ::= { usrPPPLinkEntry 10 }


          usrPPPLinkLocalToRemoteACCompression   OBJECT-TYPE
               SYNTAX    INTEGER {
                         enabled(1),
                         disabled(2)
                    }
               ACCESS    read-only
               STATUS    mandatory
               DESCRIPTION
                         "Indicates whether the local PPP entity will
                         use Address and Control Compression when
                         transmitting packets to the remote PPP entity.
                         The value of this object is meaningful only
                         when the link has reached the open state
                         (usrPPPLinkOperStatus is up)."
               ::= { usrPPPLinkEntry 11 }


          usrPPPLinkRemoteToLocalACCompression   OBJECT-TYPE
               SYNTAX    INTEGER {
                         enabled(1),
                         disabled(2)
                    }
               ACCESS    read-only
               STATUS    mandatory
               DESCRIPTION
                         "Indicates whether the remote PPP entity will
                         use Address and Control Compression when
                         transmitting packets to the local PPP entity.
                         The value of this object is meaningful only
                         when the link has reached the open state
                         (usrPPPLinkOperStatus is up)."
               ::= { usrPPPLinkEntry 12 }


          usrPPPLinkTxTotalFrames   OBJECT-TYPE
               SYNTAX    Counter
               ACCESS    read-only
               STATUS    mandatory
               DESCRIPTION
                         "The total number of frames received from the PPP
                         application for transmission over this link.
                         The value of this object is meaningful only when the
                         link has reached the open state
                         (usrPPPLinkOperStatus is up)."
               ::= { usrPPPLinkEntry 13 }


          usrPPPLinkTxTotalBytes   OBJECT-TYPE
               SYNTAX    Counter
               ACCESS    read-only
               STATUS    mandatory
               DESCRIPTION
                         "The total number of bytes received from the PPP
                         application for transmission over this link. The
                         value of this object is meaningful only when the
                         link has reached the open state
                         (usrPPPLinkOperStatus is up)."
               ::= { usrPPPLinkEntry 14 }


          usrPPPLinkRxPacketTooLongs   OBJECT-TYPE
               SYNTAX    Counter
               ACCESS    read-only
               STATUS    mandatory
               DESCRIPTION
                         "The number of received packets that have been
                         discarded because their length exceeded the
                         MRU. NOTE, packets which are longer than the
                         MRU but which are successfully received and
                         processed are NOT included in this count."
               ::= { usrPPPLinkEntry 15 }


          usrPPPLinkRxTotalFrames   OBJECT-TYPE
               SYNTAX    Counter
               ACCESS    read-only
               STATUS    mandatory
               DESCRIPTION
                         "The total number of frames received from a lower
                         layer application over this link. The value of
                         this object is meaningful only when the link has
                         reached the open state (usrPPPLinkOperStatus is up)."
               ::= { usrPPPLinkEntry 16 }


          usrPPPLinkRxTotalBytes   OBJECT-TYPE
               SYNTAX    Counter
               ACCESS    read-only
               STATUS    mandatory
               DESCRIPTION
                         "The total number of bytes received from a lower
                         layer application over this link. The value of
                         this object is meaningful only when the link has
                         reached the open state (usrPPPLinkOperStatus is
                         up)."
               ::= { usrPPPLinkEntry 17 }


          --
          -- The PPP Authentication Group.
          --
          -- The following objects reflect the values of the option
          -- parameters used in the PPP Authenticaion Control Protocol
          --   usrPPPAuthOperStatus
          --   usrPPPAuthLclToRemProtocol
          --   usrPPPAuthRemToLclProtocol


          usrPPPAuthTable   OBJECT-TYPE
               SYNTAX    SEQUENCE OF UsrPPPAuthEntry
               ACCESS    not-accessible
               STATUS    mandatory
               DESCRIPTION
                         "Table containing the Authentication status
                         information for a local PPP entity."
               ::= { usrPPPLk 2 }


          usrPPPAuthEntry   OBJECT-TYPE
               SYNTAX    UsrPPPAuthEntry
               ACCESS    not-accessible
               STATUS    mandatory
               DESCRIPTION
                         "Authentication status information for a PPP link."
               INDEX     { usrPPPBundleInstance, usrPPPLinkInstance }
               ::= { usrPPPAuthTable 1 }


          UsrPPPAuthEntry ::= SEQUENCE {
               usrPPPAuthOperStatus
                    INTEGER,
               usrPPPAuthLclToRemProtocol
                    INTEGER,
               usrPPPAuthRemToLclProtocol
                    INTEGER
          }


          usrPPPAuthOperStatus   OBJECT-TYPE
               SYNTAX    INTEGER {
                         opened(1),
                         not-opened(2)
                    }
               ACCESS    read-only
               STATUS    mandatory
               DESCRIPTION
                         "The operational status of the Authentication control
                         protocol. If the value of this object is up
                         then the finite state machine for the Authentication
                         control protocol has reached the Opened state."
               ::= { usrPPPAuthEntry 1 }


          usrPPPAuthLclToRemProtocol OBJECT-TYPE
               SYNTAX    INTEGER {
                        none(1),
                        pap(2),
                        chap(3),
                        any(4),
                        eapMD5(5),
                        msChap(6),
                        encryptedOnly(7),
                        radiusEapProxy(8)
                    }
               ACCESS    read-only
               STATUS    mandatory
               DESCRIPTION
                         "This is the authentication protocol that was used
                         by the local PPP entity when it authenticated the
                         local PPP entity to the remote PPP entity. The
                         value of this object is meaningful only when the
                         authentication has reached the open state
                         (usrPPPAuthOperStatus is up)."
               ::= { usrPPPAuthEntry 2 }


          usrPPPAuthRemToLclProtocol OBJECT-TYPE
               SYNTAX    INTEGER {
                        none(1),
                        pap(2),
                        chap(3),
                        any(4),
                        eapMD5(5),
                        msChap(6),
                        encryptedOnly(7),
                        radiusEapProxy(8)
                    }
               ACCESS    read-only
               STATUS    mandatory
               DESCRIPTION
                         "This is the authentication protocol that was used
                         by the remote PPP entity when it authenticated the
                         remote PPP entity to the local PPP entity. The
                         value of this object is meaningful only when the
                         authentication has reached the open state
                         (usrPPPAuthOperStatus is up)."
               ::= { usrPPPAuthEntry 3 }

END

--
--	usr_ip.mib
--
--
-- Author:         Jim Halpin
--
-- $Id: usr_ip.mib,v 1.26.2.17 1998/05/19 22:52:19 senthil Exp $
--
--  | Copyright (c) 1995 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-IP-MIB DEFINITIONS ::= BEGIN

	IMPORTS
	     Counter32, IpAddress, Integer32,
             OBJECT-TYPE, MODULE-IDENTITY
             FROM SNMPv2-SMI

             TruthValue
	     FROM SNMPv2-TC

             DisplayString, common, UsrConfigStatus, 
             UsrNetLogicalId
             FROM USR-DEFINITIONS-MIB;


   usrIp MODULE-IDENTITY
         LAST-UPDATED "0001021505Z"
         ORGANIZATION "3Com Corporation, Carrier Division"
         CONTACT-INFO "Customer Support"

         DESCRIPTION
                 "The proprietary defined objects for IP"
         ::= { common 12 }

   -- Begin managed object definitions here...

usrIpVersion OBJECT-TYPE
	SYNTAX		DisplayString
	MAX-ACCESS	read-only
	STATUS		current
	DESCRIPTION
		"The current software version of the IP Forwarder."
::= { usrIp 1 }

usrIpCFMStatusFlag OBJECT-TYPE
	SYNTAX		UsrConfigStatus
	MAX-ACCESS	read-write
	STATUS		current
	DESCRIPTION
		"This variable controls saving and loading of configuration
           information for the IP Module. The value can be set to either 
           save(2) or load(4) by a management station; a GET following
           should return normal(1). The other values indicate if any 
           configuration operation and what type is in progress."
::= { usrIp 2 }

usrIpCfgFileName OBJECT-TYPE
	SYNTAX      DisplayString
	MAX-ACCESS  read-write
	STATUS      current
	DESCRIPTION		
		"The name of a ConfigFile to read/write  permanent database records.
		 If the value of this object is an empty string, then the
		 IP module uses the default name `@file://IPModule.cfg'. "
::= { usrIp 3 }


usrIpNetworkTable OBJECT-TYPE
	SYNTAX SEQUENCE OF UsrIpNetworkEntry
	MAX-ACCESS not-accessible
	STATUS current
	DESCRIPTION
		"The (conceptual) table of IP Networks. The objects in this table
		 are essentially read/write versions of the ipAddrTable in MIB-2.
		 These objects are defined as read/write so that they can be configured
		 by a Network Manager at the time an IP Network is added to the Netserver
		 configuration. Any attempt to modify these parameters when the network
		 is in an active state will fail."
::= { usrIp 4 }

usrIpNetworkEntry OBJECT-TYPE
	SYNTAX UsrIpNetworkEntry
	MAX-ACCESS not-accessible
	STATUS current
	DESCRIPTION
		"A (conceptual) entry for one IP Network."
	INDEX { usrIpNetId }
::= { usrIpNetworkTable 1 }

UsrIpNetworkEntry ::= SEQUENCE {
	usrIpNetId				UsrNetLogicalId,
	usrIpNetAddr				IpAddress,
	usrIpNetMask				IpAddress,
	usrIpNetBcastAddr			Integer32,
	usrIpNetReasmMaxSize			Integer32,
	usrIpNetRoutingProtocol			INTEGER,
	usrIpNetSendDefaultRoutePolicy  	INTEGER,
	usrIpNetSendRoutesPolicy 		INTEGER,
	usrIpNetSendSubnetsOnlyPolicy 	        INTEGER,
	usrIpNetAcceptDefaultRoutePolicy 	INTEGER,
	usrIpNetSilentPolicy 			INTEGER,
	usrIpNetSplitHorizonPolicy 		INTEGER,
	usrIpNetPoisonReversePolicy 		INTEGER,
	usrIpNetFlashUpdatePolicy 		INTEGER,
	usrIpNetSimpleAuthenPolicy		INTEGER,
	usrIpNetSendRipV1CompatPolicy 	        INTEGER,
	usrIpNetRcvRipV1Policy	 		INTEGER,
	usrIpNetRcvRipV2Policy	 		INTEGER,
	usrIpNetRip2AuthKey  			OCTET STRING,
	usrIpNetReconfigNeeded                  TruthValue,
	usrIpNetRoutingMetric                   Integer32,
	usrIpNetExportMetric                    Integer32,
	usrIpNetRoutingNone                     INTEGER,
	usrIpNetRoutingRipV1			INTEGER,
	usrIpNetRoutingRipV2			INTEGER,
	usrIpNetRoutingOspf			INTEGER
	}

usrIpNetId OBJECT-TYPE
	SYNTAX		UsrNetLogicalId
	MAX-ACCESS		not-accessible
	STATUS		current
	DESCRIPTION
		"The logical identifier of the IP Network. This is the value
		 of the usrCfgNetLogicalId object in the usrCfgNetworkTable.
		 The IP forwarder returns this identifier to the Configuration
		 process in the FWD_ADD_NETWORK_RSP message. It allows management
		 applications to correlate Network Table entries with protocol
		 specific table entries."
::= { usrIpNetworkEntry 1 }

usrIpNetAddr OBJECT-TYPE
	SYNTAX  IpAddress
     MAX-ACCESS  read-only
     STATUS  current
     DESCRIPTION
		"The IP address this network has assigned to the
		 local interface."
::= { usrIpNetworkEntry 2 }

usrIpNetMask OBJECT-TYPE
     SYNTAX  IpAddress
     MAX-ACCESS  read-only
     STATUS  current
     DESCRIPTION
		"The subnet mask associated with the IP address of
           this entry.  The value of the mask is an IP
           address with all the network bits set to 1 and all
           the hosts bits set to 0."
::= { usrIpNetworkEntry 3 }

usrIpNetBcastAddr OBJECT-TYPE
     SYNTAX  Integer32 (0..1)
     MAX-ACCESS  read-write
	STATUS  current
     DESCRIPTION
          "The value of the least-significant bit in the IP
           broadcast address used for sending datagrams on
           the (logical) interface associated with the IP
           address of this entry.  For example, when the
           Internet standard all-ones broadcast address is
           used, the value will be 1.  This value applies to
           both the subnet and network broadcasts addresses
           used by the entity on this (logical) interface."
::= { usrIpNetworkEntry 4 }

usrIpNetReasmMaxSize OBJECT-TYPE
     SYNTAX  Integer32 (0..65535)
     MAX-ACCESS  read-write
     STATUS  current
     DESCRIPTION
		"The size of the largest IP datagram which this
           entity can re-assemble from incoming IP fragmented
           datagrams received on this interface."
::= { usrIpNetworkEntry 5 }

usrIpNetRoutingProtocol OBJECT-TYPE
	SYNTAX INTEGER {
			none(0),
			ripv1(1),
			ripv2(2)
		}
	MAX-ACCESS read-write
	STATUS obsolete
	DESCRIPTION
		"The routing protocol to be operated on this IP network."
::= { usrIpNetworkEntry 6 }

usrIpNetSendDefaultRoutePolicy OBJECT-TYPE
	SYNTAX	INTEGER {
		disable(0),
		enable(1)
	}
	MAX-ACCESS	read-write
	STATUS	current
	DESCRIPTION
		"Allows disabling or enabling of the send default route RIP policy.
		 This policy is enabled by default."
::= { usrIpNetworkEntry 7 }

	
usrIpNetSendRoutesPolicy OBJECT-TYPE
	SYNTAX	INTEGER {
		disable(0),
		enable(1)
	}
	MAX-ACCESS	read-write
	STATUS	current
	DESCRIPTION
		"Allows disabling or enabling of the send routes RIP policy.
		 This policy is enabled by default."
::= { usrIpNetworkEntry 8 }

usrIpNetSendSubnetsOnlyPolicy OBJECT-TYPE
	SYNTAX	INTEGER {
		disable(0),
		enable(1)
	}
	MAX-ACCESS	read-write
	STATUS	current
	DESCRIPTION
		"Allows disabling or enabling of the send subnets only RIP policy.
		 This policy is enabled by default."
::= { usrIpNetworkEntry 9 }

usrIpNetAcceptDefaultRoutePolicy OBJECT-TYPE
	SYNTAX	INTEGER {
		disable(0),
		enable(1)
	}
	MAX-ACCESS	read-write
	STATUS	current
	DESCRIPTION
		"Allows disabling or enabling of the accept default route RIP policy.
		 This policy is disabled by default."
::= { usrIpNetworkEntry 10 }

usrIpNetSilentPolicy OBJECT-TYPE
	SYNTAX	INTEGER {
		disable(0),
		enable(1)
	}
	MAX-ACCESS	read-write
	STATUS	current
	DESCRIPTION
		"Allows disabling or enabling of the silent policy.
		 This policy is disabled by default."
::= { usrIpNetworkEntry 11 }

usrIpNetSplitHorizonPolicy OBJECT-TYPE
	SYNTAX	INTEGER {
		disable(0),
		enable(1)
	}
	MAX-ACCESS	read-write
	STATUS	current
	DESCRIPTION
		"Allows disabling or enabling of the split horizon RIP policy.
		 This policy is enabled by default."
::= { usrIpNetworkEntry 12 }

usrIpNetPoisonReversePolicy OBJECT-TYPE
	SYNTAX	INTEGER {
		disable(0),
		enable(1)
	}
	MAX-ACCESS	read-write
	STATUS	current
	DESCRIPTION
		"Allows disabling or enabling of the poison reverse RIP policy.
	 	 This policy is enabled by default."
::= { usrIpNetworkEntry 13 }

usrIpNetFlashUpdatePolicy OBJECT-TYPE
	SYNTAX	INTEGER {
		disable(0),
		enable(1)
	}
	MAX-ACCESS	read-write
	STATUS	current
	DESCRIPTION
		"Allows disabling or enabling of the flash update RIP policy.
		 This policy is enabled by default."
::= { usrIpNetworkEntry 14 }

usrIpNetSimpleAuthenPolicy OBJECT-TYPE
	SYNTAX	INTEGER {
		disable(0),
		enable(1)
	}
	MAX-ACCESS	read-write
	STATUS	current
	DESCRIPTION
		"Allows disabling or enabling of the simple authentication RIP policy.
		 This policy is valid for RIPV2 only and is enabled by default when
		 RIPV2 is selected as the routing protocol."
::= { usrIpNetworkEntry 15 }

usrIpNetSendRipV1CompatPolicy OBJECT-TYPE
	SYNTAX	INTEGER {
		disable(0),
		enable(1)
	}
	MAX-ACCESS	read-write
	STATUS	current
	DESCRIPTION
		"Allows disabling or enabling of the send RipV1 compatible policy.
		 This policy is enabled by default."
::= { usrIpNetworkEntry 16 }

usrIpNetRcvRipV1Policy OBJECT-TYPE
	SYNTAX	INTEGER {
		disable(0),
		enable(1)
	}
	MAX-ACCESS	read-write
	STATUS	current
	DESCRIPTION
		"Allows disabling or enabling of the receive RipV1 policy.
		 This policy is enabled by default."
::= { usrIpNetworkEntry 17 }

usrIpNetRcvRipV2Policy OBJECT-TYPE
	SYNTAX	INTEGER {
		disable(0),
		enable(1)
	}
	MAX-ACCESS	read-write
	STATUS	current
	DESCRIPTION
		"Allows disabling or enabling of the receive RipV2 policy.
		 This policy is enabled by default."
::= { usrIpNetworkEntry 18 }

usrIpNetRip2AuthKey OBJECT-TYPE
	SYNTAX OCTET STRING (SIZE(0..16))
	MAX-ACCESS read-write
	STATUS current
	DESCRIPTION
		"this variable defines the authentication key for ip rip2.  when
		 this variable is set, by default, the authentication type is also
		 set to simple."
::= { usrIpNetworkEntry 19 }

usrIpNetReconfigNeeded  OBJECT-TYPE
       SYNTAX      TruthValue
       MAX-ACCESS  read-only
       STATUS      current
       DESCRIPTION
               "This object has a value of TRUE by default. If any other
			 object in the usrIpNetworkTable has been changed since the
			 network was enabled, the value of this object becomes TRUE.

			 All object values in this table only take effect when
			 the network is enabled. This object is meant to notify 
			 the system administrator that at least one network parameter
			 has been modified and the network should be reinitialized
			 in order for the new parameter values to take effect.

			 The network can be automatically reconfigured by setting
			 the network state to 'reconfigure' in the usrCfgNetStatus
			 object of the usrCfgNetworkTable."
::= { usrIpNetworkEntry 20 }


usrIpNetRoutingMetric OBJECT-TYPE
        SYNTAX Integer32 (1..16)
        MAX-ACCESS read-write
        STATUS current
        DESCRIPTION
                "The routing metric for using this IP network."
::= { usrIpNetworkEntry 21 }

usrIpNetExportMetric OBJECT-TYPE
        SYNTAX Integer32 (0..15)
        MAX-ACCESS read-write
        STATUS current
        DESCRIPTION
                "The metric for advertising route through this IP network."
::= { usrIpNetworkEntry 22 }

usrIpNetRoutingNone OBJECT-TYPE
	SYNTAX INTEGER {
			disable(0),
			enable(1)
		}
	MAX-ACCESS read-write
	STATUS current
	DESCRIPTION
		"Specifies that no routing protocol will be operating on this 
           IP network. Only valid SET option is enable(1) since disable is
           meaningless unless a specific routing protocol is set; 
           doing this will automatically set RoutingProtocolNone to disable(0)"
::= { usrIpNetworkEntry 27 }

usrIpNetRoutingRipV1 OBJECT-TYPE
	SYNTAX INTEGER {
			disable(0),
			enable(1)
		}
	MAX-ACCESS read-write
	STATUS current
	DESCRIPTION
		"Specifies if the RIPv1 routing protocol will be operating
           or not operating on this IP network."
::= { usrIpNetworkEntry 28 }

usrIpNetRoutingRipV2 OBJECT-TYPE
	SYNTAX INTEGER {
			disable(0),
			enable(1)
		}
	MAX-ACCESS read-write
	STATUS current
	DESCRIPTION
		"Specifies if the RIPv2 routing protocol will be operating
           or not operating on this IP network."
::= { usrIpNetworkEntry 29 }

usrIpNetRoutingOspf OBJECT-TYPE
	SYNTAX INTEGER {
			disable(0),
			enable(1)
		}
	MAX-ACCESS read-write
	STATUS current
	DESCRIPTION
		"Specifies if the OSPF routing protocol will be operating
           or not operating on this IP network."
::= { usrIpNetworkEntry 30 }


usrIpAddressPoolSize	OBJECT-TYPE
	SYNTAX	Integer32 (0..254)
	MAX-ACCESS	read-write
	STATUS	obsolete
	DESCRIPTION
		"this variable denotes the size of the dynamic address assignment
		 pool.  the default size is 8. no, not olympic.  to have a size other
		 than the default, one should set the pool size to the desired number
		 before setting usrIpAddressPoolBegin."
	-- CONFIGURABLE
::= { usrIp 5 }

usrIpAddressPoolBegin	OBJECT-TYPE
	SYNTAX	IpAddress
	MAX-ACCESS read-write
	STATUS	obsolete
	DESCRIPTION
		"the variable denotes the starting ip address of the dynamic 
		 address assignment pool.  one needs to restart the system to change 
		 it once it is set."
	-- CONFIGURABLE
::= { usrIp 6 }

usrIpHostAddress	OBJECT-TYPE
	SYNTAX	IpAddress
	MAX-ACCESS read-write
	STATUS	current
	DESCRIPTION
	   "this variable shows the host ip address of the system.  it is 
	    registered automatically by the ip forwarder and is not settable
            via SNMP. In general, the host address is also the ip address of 
            the first added lan interface's ip address."
	--CONFIGURABLE
::= { usrIp 7 }

usrIpRoutesFlag OBJECT-TYPE
	SYNTAX UsrConfigStatus
	MAX-ACCESS read-write
	STATUS current
	DESCRIPTION
		"this flag triggers cfm to save/load ip static routes, good luck."
::= { usrIp 8 }

usrIpForwarding OBJECT-TYPE
     SYNTAX  INTEGER {
             forwarding(1),    -- acting as a gateway
             not-forwarding(2) -- NOT acting as a gateway
             }
	MAX-ACCESS read-write
	STATUS current
	DESCRIPTION
		"this variable mirrors the ipForwarding flag in MIB-II"
	--CONFIGURABLE
::= { usrIp 9 }

usrIpIcmp OBJECT IDENTIFIER ::= { usrIp 10 }

usrIpIcmpOutRouterAdvertise OBJECT-TYPE
     SYNTAX  Counter32
     MAX-ACCESS  read-only
     STATUS  current
     DESCRIPTION
          "The total number of ICMP Router Advertisement messages 
           that has been sent by the router.  Note this counter 
           includes all those counted by icmpOutMsgs."
::= { usrIpIcmp 1 }

usrIpIcmpInRouterAdvertise OBJECT-TYPE
     SYNTAX  Counter32
     MAX-ACCESS  read-only
     STATUS  current
     DESCRIPTION
          "The total number of ICMP Router Advertisement messages 
           that the router has received.  Note this counter 
	      includes all those counted by icmpInMsgs."
::= { usrIpIcmp 2 }

usrIpIcmpInRouterSolicit OBJECT-TYPE
     SYNTAX  Counter32
     MAX-ACCESS  read-only
     STATUS  current
     DESCRIPTION
          "The total number of ICMP Router Solicitation messages
           that has been received by the router.  Note this counter
	      includes all those counted by icmpInMsgs."
::= { usrIpIcmp 3 }

usrIpIcmpLogFlag OBJECT-TYPE
     SYNTAX  INTEGER {
             logging(1),    -- syslogging is ENABLED
             not-logging(0) -- syslogging is DISABLED
             }
	MAX-ACCESS read-write
	STATUS current
	DESCRIPTION
		"Flag indicates whether ICMP syslogging is enabled or
           or not."
	--CONFIGURABLE
::= { usrIpIcmp 4 }

usrIpIcmpRouterAdvertiseFlag OBJECT-TYPE
     SYNTAX  INTEGER {
             enable(1),    -- router advertise is ENABLED
             disable(0) -- router advertise is DISABLED
             }
	MAX-ACCESS read-write
	STATUS current
	DESCRIPTION
		"Flag indicates whether ICMP router advertisement is enabled or
           or not."
	--CONFIGURABLE
::= { usrIpIcmp 5 }

usrIpDropAllFO1 OBJECT-TYPE
     SYNTAX  INTEGER {
             enable(1),    -- dropping ip packet with FO = 1
             disable(0)    -- NOT dropping.
             }
	MAX-ACCESS read-write
	STATUS current
	DESCRIPTION
		"indicating whether ip packet with FO = 1 is to be dropped"
	--CONFIGURABLE
::= { usrIp 11 }

usrIpDropTcpFO1 OBJECT-TYPE
     SYNTAX  INTEGER {
             enable(1),   -- dropping ip packet with FO==1 AND protocol==TCP
             disable(0)   -- NOT dropping.
             }
	MAX-ACCESS read-write
	STATUS current
	DESCRIPTION
		"indicating whether ip packet with FO == 1 AND protocol == TCP 
		 is to be dropped"
	--CONFIGURABLE
::= { usrIp 12 }

usrIpDropOptions OBJECT-TYPE
     SYNTAX  INTEGER {
             enable(1),   -- dropping ip packet with options
             disable(0)   -- NOT dropping.
             }
	MAX-ACCESS read-write
	STATUS current
	DESCRIPTION
		"indicating whether ip packet with options is to be dropped"
	--CONFIGURABLE
::= { usrIp 13 }

usrIpDropSRRoute OBJECT-TYPE
     SYNTAX  INTEGER {
             enable(1),   -- dropping ip packet with OPTION==Source Route
             disable(0)   -- NOT dropping.
             }
	MAX-ACCESS read-write
	STATUS current
	DESCRIPTION
		"indicating whether ip packet with  OPTION==Source Route
		 is to be dropped"
	--CONFIGURABLE
::= { usrIp 14 }

usrIpAddrPoolTable OBJECT-TYPE
	SYNTAX SEQUENCE OF UsrIpAddrPoolEntry
	MAX-ACCESS not-accessible
	STATUS current
	DESCRIPTION
		"The table of IP Address Pools. These objects are defined 
		 as read/write so that they can be configured by a Network
		 Manager at the time an IP Address Pool is added."
::= { usrIp 15}

usrIpAddrPoolEntry OBJECT-TYPE
	SYNTAX UsrIpAddrPoolEntry
	MAX-ACCESS not-accessible
	STATUS current
	DESCRIPTION
		"A (conceptual) entry for one IP Address Pool. To create 
		 a new row in this table the objects usrIpAddrPoolBegin
	      and usrIpAddrPoolNetMask must be provided."
	INDEX { usrIpAddrPoolName}
::= { usrIpAddrPoolTable 1 }

UsrIpAddrPoolEntry ::= SEQUENCE {
	usrIpAddrPoolName		DisplayString,
	usrIpAddrPoolBegin		IpAddress,
	usrIpAddrPoolNetMask    	IpAddress,
	usrIpAddrPoolSize		Integer32,
	usrIpAddrPoolState		INTEGER,
	usrIpAddrPoolRoute 		INTEGER,
	usrIpAddrPoolStatus		INTEGER,
        usrIpAddrPoolInUse              Integer32,
        usrIpAddrPoolMaxWasted          Integer32,
	usrIpAddrPoolPriority		INTEGER
	}

usrIpAddrPoolName	OBJECT-TYPE
	SYNTAX	 DisplayString (SIZE (1..16))
	MAX-ACCESS	 not-accessible
	STATUS	 current
	DESCRIPTION
		"the name of this IP address pool."
::= { usrIpAddrPoolEntry 1 }

usrIpAddrPoolBegin	OBJECT-TYPE
	SYNTAX	 IpAddress
	MAX-ACCESS	 read-write
	STATUS	 current
	DESCRIPTION
		"the starting ip address of this IP address pool."
	--CONFIGURABLE
::= { usrIpAddrPoolEntry 2 }

usrIpAddrPoolNetMask	 OBJECT-TYPE
	SYNTAX	 IpAddress
	MAX-ACCESS	 read-write
	STATUS	 current
	DESCRIPTION
		"the network mask for this IP address pool."
	--CONFIGURABLE
::= { usrIpAddrPoolEntry 3 }

usrIpAddrPoolSize	 OBJECT-TYPE
	SYNTAX	 Integer32 (1..4096)
	MAX-ACCESS	 read-write
	STATUS	 current
	DESCRIPTION
		"the number of IP addresses in this pool. the default size is 1"
	--CONFIGURABLE
::= { usrIpAddrPoolEntry 4 }

usrIpAddrPoolState	 OBJECT-TYPE
	SYNTAX	 INTEGER	{
		public(1),
		private(2)
	}
	MAX-ACCESS	 read-write
	STATUS	 current
	DESCRIPTION
		"If this object is set to public(1) an IP address can be selected
		 from this pool for any user not assigned to a pool.  If set to
		 private(2) IP addresses can only be selected from this pool by 
		 users assigned to it. "
	--CONFIGURABLE
::= { usrIpAddrPoolEntry 5 }


usrIpAddrPoolRoute	 OBJECT-TYPE
	SYNTAX	 INTEGER	{
		aggregate(1),
		no-aggregate(2),
		aggr-multiple-route(3)
	}
	MAX-ACCESS	 read-write
	STATUS	 current
	DESCRIPTION
		"If this object is set to aggregate(1) a host routes
                 within RIP updates will be aggregated.  If set to 
                 no_aggregate(2) host routes will not be aggregated."
	--CONFIGURABLE
::= { usrIpAddrPoolEntry 6 }

usrIpAddrPoolStatus 	OBJECT-TYPE
	SYNTAX	 INTEGER {
		delete(1),
		active(2),
		remove(3),
		remove-pending(4),
		delete-pending(5)
	}
	MAX-ACCESS	 read-write
	STATUS	 current
	DESCRIPTION
		"This object can only be set to delete(1) or active(2).
           If set to active(2) IP addresses can be assigned from this pool. 
		 If set to delete(1) this pool is being deleted so no new users can 	
		 be assigned IP addresses from this pool.  If set to remove(3) IP 
		 addresses are being removed from this pool so no new users can
		 be assigned IP address from this pool.  If set to remove_pending(4) 
		 this pool is currently waiting for users to release IP addresses that
		 need to be deleted, new users can be assigned IP addresses from
		 this pool.  If set to delete_pending(5) this pool is waiting for users
		 to release IP addresses so this pool can be deleted.  No new users
		can be assigned from this pool "
::= { usrIpAddrPoolEntry 7 }

usrIpAddrPoolInUse       OBJECT-TYPE
        SYNTAX   Integer32
        MAX-ACCESS   read-only 
        STATUS   current
        DESCRIPTION
                "the number of pool addresses in use.  This is calculated using the size
                 and the number of entries available. "
::= { usrIpAddrPoolEntry 8 }

    
usrIpAddrPoolMaxWasted       OBJECT-TYPE   
        SYNTAX   Integer32
        MAX-ACCESS   read-write
        STATUS   current     
        DESCRIPTION
                "the Max number of pool addresses wasted in case of
                 multiple routes aggr pool"
    --CONFIGURABLE
::= { usrIpAddrPoolEntry 9 } 

usrIpAddrPoolPriority	OBJECT-TYPE
	SYNTAX	INTEGER
	MAX-ACCESS	read-write
	STATUS	current
	DESCRIPTION
		"Priority for a Pool. Address pool selection for NOT round-robin
		 method shall use this field. Lowest value (1) has highest priority."
    --CONFIGURABLE
::= { usrIpAddrPoolEntry 10 }


usrIpAddressPoolFilter OBJECT-TYPE
     SYNTAX  INTEGER {
             filtering(1),       -- enable ip address_pool_filtering 
             not-filtering(2)    -- disable ip address_pool_filtering
             }
	MAX-ACCESS read-write
	STATUS current
	DESCRIPTION
		"This object may only be set to enable(1) or disable
                 (2).  If set to enable(1) and if IP address found in
                 any pools, but for which a host route does not exits, 
                 will return null route to drop packet.  If set to 
                 disable(2) there will be no check for IP address in
                 pool table.  This is disabled by default."
	--CONFIGURABLE
::= { usrIp 16 }


usrIpSRCPPPAddress OBJECT-TYPE
	SYNTAX	IpAddress
	MAX-ACCESS	read-write
	STATUS	current
	DESCRIPTION
		" This variable sets the local address for WAN links (SLIP/PPP). If zero
		system will user internal or other ethernet address for it"
	--CONFIGURABLE
::= { usrIp 17 }


usrIpSRCRADIUSAddress OBJECT-TYPE
	SYNTAX	IpAddress
	MAX-ACCESS	read-write
	STATUS	current
	DESCRIPTION
		"For all radius packets send out this will the source address. If zero
		 internal ip address or interface IP address will be the source address
		 ."
	--CONFIGURABLE
::= { usrIp 18 }


usrIpSRCSyslogAddress OBJECT-TYPE
	SYNTAX	IpAddress
	MAX-ACCESS	read-write
	STATUS	current
	DESCRIPTION
		"For all Syslog packets send out this will the source address. If zero
		 internal ip address or interface IP address will be the source address
		 ."
	--CONFIGURABLE
::= { usrIp 19 }


usrIpClearArp OBJECT-TYPE
        SYNTAX  Integer32
	MAX-ACCESS read-write
	STATUS current
	DESCRIPTION
		"This object is used to clear the entire ARP cache"
::= { usrIp 20 }


usrIpSrcIGMPAddress OBJECT-TYPE
	SYNTAX	IpAddress
	MAX-ACCESS	read-write
	STATUS	current
	DESCRIPTION
		"For all IGMP packets send out this will the source address. If zero
		 internal ip address or interface IP address will be the source address
		 ."
	--CONFIGURABLE
::= { usrIp 21 }



usrIpAddressPoolRoundRobin OBJECT-TYPE
     SYNTAX  INTEGER {
             round-robin(1),     -- enable ip address_pool_round_robin 
             not-round-robin(2)  -- disable ip address_pool_round_robin 
             }
	MAX-ACCESS read-write
	STATUS current
	DESCRIPTION
		"This object may only be set to enable(1) or disable
           (2).  If set to enable(1), addresses will be allocated
		 from address pools in round-robin fashion.  If set to
		 disable(2), addresses will be allocated from the first
		 pool until all of its addresses are depleted.  Then
		 addresses will be allocated from the next pool, and so
		 forth.  This is enabled by default."
	--CONFIGURABLE
::= { usrIp 22 }

usrIpDefaultRouteTable OBJECT-TYPE
	SYNTAX SEQUENCE OF UsrIpDefaultRouteEntry
	MAX-ACCESS not-accessible
	STATUS current
	DESCRIPTION
		"Table of default route entries. Since all default
                routes have all 0's address and mask gateway address
                will be used as a index."
::= { usrIp 23 }

usrIpDefaultRouteEntry OBJECT-TYPE
	SYNTAX UsrIpDefaultRouteEntry
	MAX-ACCESS not-accessible
	STATUS current
	DESCRIPTION
		"All 0's for the network and all 0's mask."
	INDEX { usrIpDefaultRouteGateway }
::= { usrIpDefaultRouteTable 1 }

UsrIpDefaultRouteEntry ::= SEQUENCE {
	usrIpDefaultRouteGateway        IpAddress,
        usrIpDefaultRouteStatus         INTEGER,
	usrIpDefaultRouteMetric         Integer32
	}

usrIpDefaultRouteGateway OBJECT-TYPE
    SYNTAX  IpAddress
    MAX-ACCESS  read-only
    STATUS  current
    DESCRIPTION
		"Gateway for this default route."
::= { usrIpDefaultRouteEntry 1 }

usrIpDefaultRouteStatus OBJECT-TYPE
    SYNTAX INTEGER{
          create(1),
          delete(2),
          disable(3)
    }
    MAX-ACCESS  read-write
    STATUS  current
    DESCRIPTION
		"Create/delete parameter."
	--CONFIGURABLE
::= { usrIpDefaultRouteEntry 2 }

usrIpDefaultRouteMetric OBJECT-TYPE
    SYNTAX  Integer32
    MAX-ACCESS  read-write
    STATUS  current
    DESCRIPTION
        "Metric for this default route."
	--CONFIGURABLE
::= { usrIpDefaultRouteEntry 3 }

usrGlobalSourceIpFilterFlag OBJECT-TYPE 
    SYNTAX INTEGER
    {
       disabled(2),
       enabled(1)
    }
    MAX-ACCESS   read-write 
    STATUS   current
    DESCRIPTION
        "Indicates whether Global Source address assurance  
         feature is enabled."
             --CONFIGURABLE
::= { usrIp 24 }

usrIpIeaSendUnsolicitedArp OBJECT-TYPE
    SYNTAX      TruthValue
    MAX-ACCESS read-write
    STATUS current
    DESCRIPTION
      "This flag is FALSE by default. In order to send unsolicited ARP
       request when the user gets connected, the needs to be set to TRUE"
    --CONFIGURABLE
::= { usrIp 25 }
 
usrIpIeaForceNexthopRoute OBJECT-TYPE
    SYNTAX TruthValue
    MAX-ACCESS read-write
    STATUS current
    DESCRIPTION
  	    "This flag is FALSE[DISABLED] by default. This flags DISABLED states NOT 
		 to drop the connection for the user if the next hop in INVALID and also to use 
		 other routes to forward the packets when the next hop router is unreachable. 
		 If the value is ENABLED, then the user will be disconnected if nexthop route is 
		 INVALID and also drop the packets when nexthop route becomes unreachable."
    --CONFIGURABLE
::= { usrIp 26 }

usrIpSRCPingAddress OBJECT-TYPE
    SYNTAX  IpAddress
    MAX-ACCESS  read-write
    STATUS  current
    DESCRIPTION
        "This variable sets the src address for ping"
    --CONFIGURABLE
::= { usrIp 27 }
 
usrIpSRCTraceRouteAddress OBJECT-TYPE
    SYNTAX  IpAddress
    MAX-ACCESS  read-write
    STATUS  current
    DESCRIPTION
        "This variable sets the src address for traceroute"
    --CONFIGURABLE
::= { usrIp 28 }


usrIpProxyArpAllDialinNet OBJECT-TYPE 
    SYNTAX INTEGER
    {
       disabled(2),
       enabled(1)
    }
    MAX-ACCESS   read-write 
    STATUS   current
    DESCRIPTION
        "Indicates whether Proxy ARPing all dialin networks 
         feature is enabled. Default is disabled"
             --CONFIGURABLE
::= { usrIp 29 }

usrIpSendHostUnreachForPool OBJECT-TYPE
    SYNTAX INTEGER
    {
       disabled(2),
       enabled(1)
    }
    MAX-ACCESS   read-write
    STATUS   current
    DESCRIPTION
        "Indicates whether to send icmp unreachable for pool addresses
         Default is disabled"
   --CONFIGURABLE
::= { usrIp 30 }

usrIpIeaNextHopRouting OBJECT-TYPE
    SYNTAX  TruthValue
    MAX-ACCESS read-write
    STATUS current
    DESCRIPTION
      "This is a flag which says whether next hop routing is enabled or not.
       The default value is TRUE [ENABLED]"
    --CONFIGURABLE
::= { usrIp 31 }

usrIpSrcVTPAddress OBJECT-TYPE
        SYNTAX  IpAddress
        MAX-ACCESS  read-write
        STATUS  current
        DESCRIPTION
                "For all VTP packets send out this will the source address.
                 If zero internal ip address or interface IP address
                 will be the source address."
 
        --CONFIGURABLE 
::= { usrIp 32 }


usrIpSrcPPTPAddress OBJECT-TYPE
        SYNTAX  IpAddress
        MAX-ACCESS  read-write
        STATUS  current
        DESCRIPTION
        "For all PPTP packets sent out by the PAC, this will the source address.
         If this is zero then the internal ip addr or interface IP addr will be
         the source address ."
        --CONFIGURABLE
::= { usrIp 33 }

usrIpSrcL2TPAddress OBJECT-TYPE
    SYNTAX  IpAddress
    MAX-ACCESS  read-write
    STATUS  current
    DESCRIPTION 
        "For all L2TP packets sent out by the LAC, this will the source address.
         If this is zero then the internal ip addr or interface IP addr will be
         the source address ."
    --CONFIGURABLE
::= { usrIp 34 }


          -- the IP source address based routing table

          -- The IP routing table contains an entry for each route
          -- presently known to this entity.

          usrIpSrcRouteTable OBJECT-TYPE
              SYNTAX  SEQUENCE OF UsrIpSrcRouteEntry
              MAX-ACCESS  not-accessible
              STATUS  current
              DESCRIPTION
                      "This entity's IP Source Routing table."
              ::= { usrIp 35 }

          usrIpSrcRouteEntry OBJECT-TYPE
              SYNTAX  UsrIpSrcRouteEntry
              MAX-ACCESS  not-accessible
              STATUS  current
              DESCRIPTION
                      "A route to a particular destination."
              INDEX   { usrIpSrcRouteDest }
              ::= { usrIpSrcRouteTable 1 }

          UsrIpSrcRouteEntry ::=
              SEQUENCE {
                  usrIpSrcRouteDest
                      IpAddress,
                  usrIpSrcRouteIfIndex
                      Integer32,
                  usrIpSrcRouteMetric1
                      Integer32,
                  usrIpSrcRouteNextHop
                      IpAddress,
                  usrIpSrcRouteType
                      INTEGER,
                  usrIpSrcRouteProto
                      INTEGER,
                  usrIpSrcRouteMask
                      IpAddress,
                  usrIpSrcRouteStatus
                      INTEGER
              }

          usrIpSrcRouteDest OBJECT-TYPE
              SYNTAX  IpAddress
              MAX-ACCESS  read-write
              STATUS  current
              DESCRIPTION
                      "The destination IP address of this route.  An
                      entry with a value of 0.0.0.0 is considered a
                      default route.  Multiple routes to a single
                      destination can appear in the table, but access to
                      such multiple entries is dependent on the table-
                      access mechanisms defined by the network
                      management protocol in use."
                 --CONFIGURABLE
              ::= { usrIpSrcRouteEntry 1 }

          usrIpSrcRouteIfIndex OBJECT-TYPE
              SYNTAX  Integer32
              MAX-ACCESS  read-write
              STATUS  current
              DESCRIPTION
                      "The index value which uniquely identifies the
                      local interface through which the next hop of this
                      route should be reached.  The interface identified
                      by a particular value of this index is the same
                      interface as identified by the same value of
                      ifIndex."
              ::= { usrIpSrcRouteEntry 2 }

          usrIpSrcRouteMetric1 OBJECT-TYPE
              SYNTAX  Integer32 (0..15)
              MAX-ACCESS  read-write
              STATUS  current
              DESCRIPTION
                      "The primary routing metric for this route.  The
                      semantics of this metric are determined by the
                      routing-protocol specified in the route's
                      ipRouteProto value.  If this metric is not used,
                      its value should be set to -1."
              --CONFIGURABLE
              ::= { usrIpSrcRouteEntry 3 }

          usrIpSrcRouteNextHop OBJECT-TYPE
              SYNTAX  IpAddress
              MAX-ACCESS  read-write
              STATUS  current
              DESCRIPTION
                      "The IP address of the next hop of this route.
                      (In the case of a route bound to an interface
                      which is realized via a broadcast media, the value
                      of this field is the agent's IP address on that
                      interface.)"
               --CONFIGURABLE
              ::= { usrIpSrcRouteEntry 4 }

          usrIpSrcRouteType OBJECT-TYPE
              SYNTAX  INTEGER {
                          other(1),        -- none of the following

                          invalid(2),      -- an invalidated route
                                           -- route to directly
                          direct(3),       -- connected (sub-)network

                                           -- route to a non-local
                          indirect(4)      -- host/network/sub-network
                      }
              MAX-ACCESS  read-write
              STATUS  current
              DESCRIPTION
                      "The type of route.  Note that the values
                      direct(3) and indirect(4) refer to the notion of
                      direct and indirect routing in the IP
                      architecture. The only value settable from SNMP
                      is invalid(2).

                      Setting this object to the value invalid(2) has
                      the effect of invalidating the corresponding entry
                      in the ipRouteTable object.  That is, it
                      effectively disassociates the destination
                      identified with said entry from the route
                      identified with said entry.  It is an
                      implementation-specific matter as to whether the
                      agent removes an invalidated entry from the table.
                      Accordingly, management stations must be prepared
                      to receive tabular information from agents that
                      corresponds to entries not currently in use.
                      Proper interpretation of such entries requires
                      examination of the relevant ipRouteType object."
              ::= { usrIpSrcRouteEntry 5 }

          usrIpSrcRouteProto OBJECT-TYPE
              SYNTAX  INTEGER {
                          other(1),       -- none of the following

                                          -- non-protocol information,
                                          -- e.g., manually configured
                          local(2),       -- entries

                                          -- set via a network
                          netmgmt(3),     -- management protocol

                                          -- obtained via ICMP,
                          icmp(4),        -- e.g., Redirect

                                          -- the remaining values are
                                          -- all gateway routing
                                          -- protocols
                          egp(5),
                          ggp(6),
                          hello(7),
                          rip(8),
                          is-is(9),
                          es-is(10),
                          ciscoIgrp(11),
                          bbnSpfIgp(12),
                          ospf(13),
                          bgp(14),
                          source(15)
                      }
              MAX-ACCESS  read-only
              STATUS  current
              DESCRIPTION
                      "The routing mechanism via which this route was
                      learned.  Inclusion of values for gateway routing
                      protocols is not intended to imply that hosts
                      should support those protocols."
              ::= { usrIpSrcRouteEntry 6 }

          usrIpSrcRouteMask OBJECT-TYPE
              SYNTAX  IpAddress
              MAX-ACCESS  read-write
              STATUS  current
              DESCRIPTION
                      "Indicate the mask to be logical-ANDed with the
                      destination address before being compared to the
                      value in the ipSrcRouteDest field.  For those systems
                      that do not support arbitrary subnet masks, an
                      agent constructs the value of the ipRouteMask by
                      determining whether the value of the correspondent
                      ipSrcRouteDest field belong to a class-A, B, or C
                      network, and then using one of:

                           mask           network
                           255.0.0.0      class-A
                           255.255.0.0    class-B
                           255.255.255.0  class-C

                      If the value of the ipRouteDest is 0.0.0.0 (a
                      default route), then the mask value is also
                      0.0.0.0.  It should be noted that all IP routing
                      subsystems implicitly use this mechanism."
              --CONFIGURABLE
              ::= { usrIpSrcRouteEntry 7 }

          usrIpSrcRouteStatus OBJECT-TYPE
              SYNTAX  INTEGER {
                                up(1),
                                down(2),
                                invalid(3)
                                }
              MAX-ACCESS  read-write
              STATUS  current
              DESCRIPTION
                      "Whether the route is UP or DOWN - updated 
                       internally depending upon whether the network 
                       goes up or down. Not settable via SNMP."
              ::= { usrIpSrcRouteEntry 8 }

-- The following table is modeled after IGMP.

usrIpSrcRouteInterfaceTable OBJECT-TYPE
    SYNTAX     SEQUENCE OF UsrIpSrcRouteInterfaceEntry
    MAX-ACCESS not-accessible
    STATUS     current
    DESCRIPTION
    "The table listing the interfaces on which source based routing is enabled."
    ::= { usrIp 36 }

usrIpSrcRouteInterfaceEntry OBJECT-TYPE
    SYNTAX     UsrIpSrcRouteInterfaceEntry
    MAX-ACCESS not-accessible
    STATUS     current
    DESCRIPTION
    "An entry representing an interface on which source based routing is enabled."
    INDEX      { usrIpSrcRouteInterfaceIfName }
    ::= { usrIpSrcRouteInterfaceTable 1 }

UsrIpSrcRouteInterfaceEntry ::= SEQUENCE {
    usrIpSrcRouteInterfaceIfName       DisplayString,
    usrIpSrcRouteInterfaceEnabled      TruthValue
}

usrIpSrcRouteInterfaceIfName OBJECT-TYPE
    SYNTAX     DisplayString (SIZE (1..32))
    MAX-ACCESS not-accessible
    STATUS     current
    DESCRIPTION
            "The interface name for which source rbased routing is enabled."
::= { usrIpSrcRouteInterfaceEntry 1 }

usrIpSrcRouteInterfaceEnabled OBJECT-TYPE
    SYNTAX     TruthValue                                                 
    MAX-ACCESS read-write                                                 
    STATUS     current                                                   
    DESCRIPTION 
             "Whether source routing is enabled or not." 
    DEFVAL    { false }
    --CONFIGURABLE                         
::= { usrIpSrcRouteInterfaceEntry 2 }                                        

   
usrIpRespondToDirectedBcst OBJECT-TYPE 
    SYNTAX INTEGER
    {
       disabled(2),
       enabled(1)
    }
    MAX-ACCESS   read-write 
    STATUS   current
    DESCRIPTION
        "Disable responding to directed bcast globally"
             --CONFIGURABLE
::= { usrIp 37 }


usrIpForwardDirectedBcst OBJECT-TYPE 
    SYNTAX INTEGER
    {
       disabled(2),
       enabled(1)
    }
    MAX-ACCESS   read-write 
    STATUS   current
    DESCRIPTION
        "Enable directed bcast forwarding in IP"
             --CONFIGURABLE
::= { usrIp 39 }

usrIpStaticArpTable OBJECT-TYPE
	SYNTAX SEQUENCE OF UsrIpStaticRouteEntry
	MAX-ACCESS not-accessible
	STATUS current
	DESCRIPTION
		"Table of Static Arp cache"
::= { usrIp 38 }

usrIpStaticArpEntry OBJECT-TYPE
	SYNTAX UsrIpStaticRouteEntry
	MAX-ACCESS not-accessible
	STATUS current
	DESCRIPTION
		""
	INDEX { usrIpStaticArpIpAddr,usrIpusrIpStaticArpInt}
::= { usrIpStaticArpTable 1 }

UsrIpStaticRouteEntry ::= SEQUENCE {
	usrIpStaticArpIpAddr        IpAddress,
	usrIpusrIpStaticArpInt      OCTET STRING,
	usrIpStaticArpStatus	    INTEGER,
        usrIpStaticArpMacAddr       OCTET STRING,
	usrIpStaticArpState	    INTEGER
	}

usrIpStaticArpIpAddr OBJECT-TYPE
    SYNTAX  IpAddress
    MAX-ACCESS  read-only
    STATUS  current
    DESCRIPTION
		"The ip address of the ARP entry"
::= { usrIpStaticArpEntry 1 }

usrIpusrIpStaticArpInt OBJECT-TYPE
    SYNTAX  OCTET STRING (SIZE(0..16))
    MAX-ACCESS  read-only
    STATUS  current
    DESCRIPTION
		"The interface of the static ARP entry"
::= { usrIpStaticArpEntry 2 }

usrIpStaticArpStatus OBJECT-TYPE
    SYNTAX  INTEGER {
                add(1), -- set when arp entry added
                delete(2) -- delete entry
                }
	MAX-ACCESS read-write
	STATUS current
	DESCRIPTION
		"This object is used to identify the ARP operation.
                 It is set to 1 when an entry is added; setting it
                 to 2 will delete the entry."
   --CONFIGURABLE
::= { usrIpStaticArpEntry 3 }

usrIpStaticArpMacAddr OBJECT-TYPE
    SYNTAX OCTET STRING (SIZE(6))
	MAX-ACCESS read-write
	STATUS current
	DESCRIPTION
		"This object is used to store the associated MAC address"
   --CONFIGURABLE
::= { usrIpStaticArpEntry 4 }

usrIpStaticArpState OBJECT-TYPE
	SYNTAX	INTEGER {
		public(1),
		private(2),
                invalid(3)
	}
	MAX-ACCESS	read-write
	STATUS	current
	DESCRIPTION
		"This is the type of static arp entry. Public/private "
   --CONFIGURABLE
::= { usrIpStaticArpEntry 5 }

usrIpAggregateRouteTable OBJECT-TYPE
    SYNTAX  SEQUENCE OF UsrIpAggregateRouteEntry
    MAX-ACCESS  not-accessible
    STATUS  current
    DESCRIPTION
        "This table is used to display multiple aggregate routes for an
         IP pool. An IP pool could be segregated into multiple sub pools.
         depending on the size."          
    
    ::= { usrIp 40 } 
    
usrIpAggregateRouteEntry OBJECT-TYPE 
    SYNTAX  UsrIpAggregateRouteEntry
    MAX-ACCESS  not-accessible
    STATUS  current
    DESCRIPTION    
        "A table of PoolName, Initial Address, Aggregate Route, Endpoint address,
         Type"      
    INDEX { usrIpAggInitPoolAddress }
    ::= { usrIpAggregateRouteTable 1 }
   
UsrIpAggregateRouteEntry ::= 
    SEQUENCE {
        usrIpAggInitPoolAddress  
            IpAddress,
        usrIpAggPoolName
            DisplayString,     
        usrIpAggPoolAggregateRoute
            IpAddress,
        usrIpAggPoolNetMask
            IpAddress,
        usrIpAggPoolSize
            Integer32,
        usrIpAggPoolType    
            Integer32    
    }   

usrIpAggInitPoolAddress OBJECT-TYPE
    SYNTAX  IpAddress
    MAX-ACCESS  read-only
    STATUS  current
    DESCRIPTION
        "Initial pool address for aggregate pool"
    ::= { usrIpAggregateRouteEntry 1 }
 
usrIpAggPoolName OBJECT-TYPE
    SYNTAX  DisplayString
    MAX-ACCESS  read-only
    STATUS  current
    DESCRIPTION
        "Aggregate Pool name"
    ::= { usrIpAggregateRouteEntry 2 }
 
usrIpAggPoolAggregateRoute OBJECT-TYPE
    SYNTAX  IpAddress
    MAX-ACCESS  read-only
    STATUS  current
    DESCRIPTION
        "Aggregate route that will be broadcasted"
    ::= { usrIpAggregateRouteEntry 3 }
 
usrIpAggPoolNetMask OBJECT-TYPE
    SYNTAX  IpAddress
    MAX-ACCESS  read-only
    STATUS  current
    DESCRIPTION
        "Mask for an aggregate route pool"
    ::= { usrIpAggregateRouteEntry 4 }
 
usrIpAggPoolSize OBJECT-TYPE
    SYNTAX  Integer32
    MAX-ACCESS  read-only
    STATUS  current
    DESCRIPTION
        "Indicates the last valid address in this aggregate pool"
    ::= { usrIpAggregateRouteEntry 5 }
 
usrIpAggPoolType OBJECT-TYPE
    SYNTAX  Integer32
    MAX-ACCESS  read-only
    STATUS  current
    DESCRIPTION
        "Indicates the type of the aggregate pool. It might be
         MULTI_AGGREGATE, NON_AGGREGATE, AGGREGATE"
    ::= { usrIpAggregateRouteEntry 6 }


END         -- End USR-IP-MIB DEFINITIONS
--
--	usr_invarp.mib - A proprietary MIB file for Inverse ARP cache 
--
--
-- Author:        P K Das 
--
-- $Id: usr_invarp.mib,v 1.0.0.0 1999/1/8 13:20:25 psd Exp $
--
--  | Copyright (c) 1999 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-INVERSEARP-MIB DEFINITIONS ::= BEGIN

	IMPORTS
	  RowStatus
                FROM SNMPv2-TC
          IpAddress
                FROM RFC1155-SMI
          OBJECT-TYPE,  MODULE-IDENTITY, Integer32
                FROM SNMPv2-SMI
          PhysAddress, common
                FROM USR-DEFINITIONS-MIB;


        usrInverseARP    MODULE-IDENTITY
         LAST-UPDATED "0001141020Z" -- Friday, January 14, 10:20, 2000
         ORGANIZATION "3Com Corporation, Carrier Division"
         CONTACT-INFO "Customer Support"
      
         DESCRIPTION
                 "The proprietary object definitions for Inverse ARP."
         ::= { common 73 }

   -- Begin managed object definitions here...

   -- The Inverse ARP Table contains the mapping of IP Address(network address)
   -- to dlci-interface pair for IP networks over Frame Relay PTP connections.

usrInverseARPTable OBJECT-TYPE
	SYNTAX SEQUENCE OF UsrInverseARPEntry
	MAX-ACCESS not-accessible
	STATUS current 
	DESCRIPTION
		"The Inverse ARP cache for Frame Relay Networks"
::= { usrInverseARP 1 }

usrInverseARPEntry OBJECT-TYPE
	SYNTAX UsrInverseARPEntry
	MAX-ACCESS not-accessible
	STATUS current
	DESCRIPTION
		"An Inverse ARP cache entry"
	INDEX { usrInverseARPIfIndex, usrInverseARPNetAddress }
::= { usrInverseARPTable 1 }

UsrInverseARPEntry ::= SEQUENCE {
        usrInverseARPIfIndex     Integer32,
        usrInverseARPPhysAddress PhysAddress,
        usrInverseARPNetAddress  IpAddress,
        usrInverseARPType        INTEGER,
        usrInverseARPAge         Integer32,
	usrInverseARPStatus      RowStatus
        }

usrInverseARPIfIndex OBJECT-TYPE
        SYNTAX  Integer32
        MAX-ACCESS  read-write
        STATUS  current
        DESCRIPTION
                "The interface on which this entry's equivalence
                is effective.  The interface identified by a
                particular value of this index is the same
                interface as identified by the same value of
                ifIndex."
        --CONFIGURABLE
::= { usrInverseARPEntry 1 }

usrInverseARPPhysAddress OBJECT-TYPE
        SYNTAX  PhysAddress
        MAX-ACCESS  read-write
        STATUS  current
        DESCRIPTION
                "The media-dependent `physical' address. For Frame Relay PTMP network,
                it's six byte long; 4 byte DLCI followed by 2byte interface(physical) index"
        --CONFIGURABLE
::= { usrInverseARPEntry 2 }


usrInverseARPNetAddress OBJECT-TYPE
        SYNTAX  IpAddress
        MAX-ACCESS  read-write
        STATUS  current
        DESCRIPTION
                "The IpAddress corresponding to the media-
                dependent `physical' address."
        --CONFIGURABLE
::= { usrInverseARPEntry 3 }
 
usrInverseARPType OBJECT-TYPE
        SYNTAX  INTEGER {
                    other(0),        -- none of the following
                    invalid(1),      -- an invalidated mapping
                    dynamic(2),
                    static(3)
                }
        MAX-ACCESS  read-write
        STATUS  current
        DESCRIPTION
                "The type of mapping"
        --CONFIGURABLE
::= { usrInverseARPEntry 4 }

usrInverseARPAge OBJECT-TYPE
        SYNTAX  Integer32
        MAX-ACCESS  read-write
        STATUS  current
        DESCRIPTION
                "The current timeout age of an entry"
        --CONFIGURABLE
::= { usrInverseARPEntry 5 }

usrInverseARPStatus OBJECT-TYPE
	SYNTAX  RowStatus
	MAX-ACCESS    read-write
	STATUS  current
	DESCRIPTION
		"The status of this row of the Inverse ARP Table. "
	--CONFIGURABLE
::= { usrInverseARPEntry 6 }


usrInverseARPConfigGroup OBJECT IDENTIFIER ::= { usrInverseARP 2 }

usrInverseARPTxInterval OBJECT-TYPE
        SYNTAX  Integer32
        MAX-ACCESS  read-write
        STATUS  current
        DESCRIPTION
                "The Inverse ARP transmit frequency in secs"
	--CONFIGURABLE
::= { usrInverseARPConfigGroup 1 }

usrInverseARPMaxAge OBJECT-TYPE
        SYNTAX  Integer32
        MAX-ACCESS  read-write
        STATUS  current
        DESCRIPTION
                "The Maximum age count of an entry before it is deleted from the cache. 
                 One count corresponds to one Inverse ARP transmit frequency period."
	--CONFIGURABLE
::= { usrInverseARPConfigGroup 2 }

usrInverseARPCacheClear OBJECT-TYPE
        SYNTAX  Integer32
        MAX-ACCESS  read-write
        STATUS  current
        DESCRIPTION
                "This object is used to clear the entire Inverse ARP cache."
::= { usrInverseARP 3 }

END         -- End USR-INVERSEARP-MIB definitions

--
--
--	usr_ip_routing.mib
--
--
-- Author:         han-son on
--
-- $Id: usr_ip_routing.mib,v 1.8.10.7 1998/05/19 22:52:24 senthil Exp $
--
--  | Copyright (c) 1995 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-IP-ROUTING-MIB DEFINITIONS ::= BEGIN

	IMPORTS
		usrIpRouting, UsrNetLogicalId, DisplayString, UsrConfigStatus
				FROM USR-DEFINITIONS-MIB
		Counter, IpAddress
				FROM RFC1155-SMI
		OBJECT-TYPE
				FROM RFC-1212;

-- Begin IP routing object definitions here...

usrIpRouterId	OBJECT-TYPE
	SYNTAX	IpAddress
	ACCESS	read-write
	STATUS	mandatory
	DESCRIPTION
		"the router id is usually the ip address of one of the router's
		 lan interface ip address.  this variable can only be set when
		 usrIpAdminStatus is set to disabled."
::= {usrIpRouting 1}

usrIpAdminStatus	OBJECT-TYPE
	SYNTAX	INTEGER {
			enabled(1),
			disabled(2)
		}
	ACCESS	read-write
	STATUS	mandatory
	DESCRIPTION
		"this variable is used to enable or disable the ip routing instance."
        --CONFIGURABLE
::= {usrIpRouting 2}

usrIpStaticProtoStatus	OBJECT-TYPE
	SYNTAX	INTEGER {
			enable(1),
			disable(2)
		}
	ACCESS	read-write
	STATUS	mandatory
	DESCRIPTION
		"this variable is used to enable or disable static remote routes"
::= {usrIpRouting 3}

usrIpASNumber	OBJECT-TYPE
	SYNTAX	INTEGER (1..65535)
	ACCESS	read-write
	STATUS	mandatory
	DESCRIPTION
		"this is the autonomous system number used by egp, which can only be 
		 modified when usrIpAdminStatus is set to disabled."
::= {usrIpRouting 4}

usrIpRtabMaxAdmin	OBJECT-TYPE
	SYNTAX		INTEGER (30..65535)
	ACCESS		read-write
	STATUS		mandatory
	DESCRIPTION
		"the max admin route table entries for next set.  this is put in by
		 rci for lightstream atm.  it is not used by lanlinker or netserver."
::= {usrIpRouting 5}

usrIpRtabMax	OBJECT-TYPE
	SYNTAX	INTEGER (30..20000)
	ACCESS	read-only
	STATUS	mandatory
	DESCRIPTION
		"this displays the maximum routing table size, this
                 value can no longer be modified. The max size of the
                 routing table is determined at compilation time, 
                 based on the DFLT_RTH_CNT. DFLT_RTH_CNT is currently 
		 set to 3880."
::= {usrIpRouting 6}

usrIpNHEntryMax	OBJECT-TYPE
	SYNTAX		INTEGER (256..65535)
	ACCESS		read-write
	STATUS		mandatory
	DESCRIPTION
		"this defines the maximum next hop entries, which can only be 
		 modified when usrIpAdminStatus is set to disabled.  the default
		 is 512"
::= {usrIpRouting 7}

usrIpRtEntryCount	OBJECT-TYPE
	SYNTAX		Counter
	ACCESS		read-only
	STATUS		mandatory
	DESCRIPTION
		"this keeps the number of route entries."
::= {usrIpRouting 8}

usrIpGenStat	OBJECT-TYPE
	SYNTAX	INTEGER {
			create(1),
			delete(2)
		}
	ACCESS	read-write
	STATUS	mandatory
	DESCRIPTION
		"this variable denotes the existence of the ip routing instance,
		 which can also be used to delete the routing instance."
::= {usrIpRouting 9}

usrIpRipGenStat	OBJECT-TYPE
	SYNTAX		INTEGER {
				enabled(1),
				disabled(2)
			}
	ACCESS		read-write
	STATUS		mandatory
	DESCRIPTION
		"this mib variable is used to enable or disable the ip rip instance
		 at the ip routing instance level.  it is a no op if ip rip instance
		 is not yet created.
		 the rip instance, i.e. usrIpRipAdminStatus, may still remain
		 disabled, if it is either not created or it was disabled at ip rip
		 instance level.  to fully enable the rip instance, one has to make
		 sure that ip rip instance is already created and enabled on both
		 levels."
::= {usrIpRouting 10}

usrIpRipAdminStatus	OBJECT-TYPE
	SYNTAX		INTEGER {
				create(1),
				delete(2)
		}
	ACCESS		read-write
	STATUS		mandatory
	DESCRIPTION
		"this variable is used to create or delete the ip rip instance."
::= {usrIpRouting 11}

usrIpRipFlags	OBJECT-TYPE
	SYNTAX	INTEGER
	ACCESS	read-write
	STATUS	mandatory
	DESCRIPTION
		"three Flags  are supported by this mib object,
		 only RIP_FLAG_RFC1058_METRICS, RIP_FLAG_SEND_REQUEST are
		 accessible.

		 RIP_FLAG_JITTER_UPDATE	:=	0x00000002 (default)		
		 RIP_FLAG_RFC1058_METRICS:=	0x00000008 (default)
		 RIP_FLAG_SEND_REQUEST	:=	0x00000010 (default) "
::= {usrIpRouting 12}

usrIpIfbTable	OBJECT-TYPE
	SYNTAX	SEQUENCE OF UsrIpIfbEntry
	ACCESS	not-accessible
	STATUS	mandatory
	DESCRIPTION
		"rci uses interface block to describe the system's network interface
		 which is similar to pilgrim portal."
::= {usrIpRouting 13}

usrIpIfbEntry	OBJECT-TYPE
	SYNTAX	UsrIpIfbEntry
	ACCESS	not-accessible
	STATUS	mandatory
	DESCRIPTION
		"an entry for one ip interface block."
	INDEX {usrIpIfbEntAddr, usrIpIfbEntIfIndex}
::= {usrIpIfbTable 1}

UsrIpIfbEntry ::= SEQUENCE {
	usrIpIfbEntAddr		IpAddress,
	usrIpIfbEntIfIndex		UsrNetLogicalId,
	usrIpIfbEntIfHandle		INTEGER,
	usrIpIfbEntNetMask		IpAddress,
	usrIpIfbEntOnesBc		INTEGER,
	usrIpIfbEntZerosBc		INTEGER,
	usrIpIfbEntReasmMaxSize	INTEGER,
	usrIpIfbEntType		INTEGER,
	usrIpIfbEntNbrAddr		IpAddress,
	usrIpIfbEntAdminStatus	INTEGER,
	usrIpIfbEntStat		INTEGER,
	usrIpIfbEntPortDown		INTEGER
}

usrIpIfbEntAddr	OBJECT-TYPE
	SYNTAX		IpAddress
	ACCESS		read-only
	STATUS		mandatory
	DESCRIPTION
		"ip network interface address, i.e. host address"
::= {usrIpIfbEntry 1}

usrIpIfbEntIfIndex	OBJECT-TYPE
	SYNTAX		UsrNetLogicalId
	ACCESS		read-only
	STATUS		mandatory
	DESCRIPTION
		"the logical identifier of the ip network."
::={usrIpIfbEntry 2}

usrIpIfbEntIfHandle	OBJECT-TYPE
	SYNTAX		INTEGER
	ACCESS		read-only
	STATUS		mandatory
	DESCRIPTION
		"don't know yet"
::= {usrIpIfbEntry 3}

usrIpIfbEntNetMask	OBJECT-TYPE
	SYNTAX		IpAddress
	ACCESS		read-only
	STATUS		mandatory
	DESCRIPTION
		"the subnet mask associated w/ the ip address of this entry."
::= {usrIpIfbEntry 4}

usrIpIfbEntOnesBc	OBJECT-TYPE
	SYNTAX		INTEGER (0..1)
	ACCESS		read-only
	STATUS		mandatory
	DESCRIPTION
		"the value of the least-significant bit in the ip broadcast address
		 used for sending datagrams on the (logical) interface associated w/
		 the ip address of this entry."
::= {usrIpIfbEntry 5}

usrIpIfbEntZerosBc	OBJECT-TYPE
	SYNTAX		INTEGER (0..1)
	ACCESS		not-accessible
	STATUS		mandatory
	DESCRIPTION
		"the value of the least-significant bit in the ip broadcast address
		 used for sending datagrams on the (logical) interface associated w/
		 the ip address of this entry."
::= {usrIpIfbEntry 6}

usrIpIfbEntReasmMaxSize	OBJECT-TYPE
	SYNTAX			INTEGER (0..65535)
	ACCESS			read-only
	STATUS			mandatory
	DESCRIPTION
		"the size of the largest ip datagram which this entity can re-assemble
		 from incoming ip fragmented datagrams received on this interface.
		 it is usually equivalent to the mtu of the interface."
::= {usrIpIfbEntry 7}

usrIpIfbEntType	OBJECT-TYPE
	SYNTAX		INTEGER {
				broadcast(1),
				non-broadcast(2),
				point-to-point(3)
			}
	ACCESS		read-only
	STATUS		mandatory
	DESCRIPTION
		"this denotes the ip network (logical) type."
::= {usrIpIfbEntry 8}

usrIpIfbEntNbrAddr	OBJECT-TYPE
	SYNTAX		IpAddress
	ACCESS		read-write
	STATUS		mandatory
	DESCRIPTION
		"this may be needed for point to point connection."
::= {usrIpIfbEntry 9}

usrIpIfbEntAdminStatus	OBJECT-TYPE
	SYNTAX			INTEGER {
					enabled(1),
					disabled(2)
				}
	ACCESS			read-write
	STATUS			mandatory
	DESCRIPTION
		"this variable is used to enable or disable this interface block"
::= {usrIpIfbEntry 10}

usrIpIfbEntStat	OBJECT-TYPE
	SYNTAX		INTEGER {
				create(1),
				delete(2)
			}
	ACCESS		not-accessible
	STATUS		mandatory
	DESCRIPTION
		"this variable is used to create or delete an interface block."
::= {usrIpIfbEntry 11}

usrIpIfbEntPortDown	OBJECT-TYPE
	SYNTAX		INTEGER {
				active(1),
				inactive(2)
			}
	ACCESS		not-accessible
	STATUS		mandatory
	DESCRIPTION
		"this variable is used to indicate the state of the hardware."
::= {usrIpIfbEntry 12}

usrIpRipGenAdminStat	OBJECT-TYPE
	SYNTAX			INTEGER {
					enabled(1),
					disabled(2)
				}
	ACCESS			read-write
	STATUS			mandatory
	DESCRIPTION
		"this variable is used to disable or enable the ip rip instance at
		 the rip instance level."
        --CONFIGURABLE
::= {usrIpRouting 14}

usrIpRipGenIntfCnt	OBJECT-TYPE
	SYNTAX		INTEGER
	ACCESS		read-only
	STATUS		mandatory
	DESCRIPTION
		"this variable shows the number of the ip rip interfaces."
::= {usrIpRouting 15}

usrIpRipGenNbrCnt	OBJECT-TYPE
	SYNTAX		INTEGER
	ACCESS		read-only
	STATUS		mandatory
	DESCRIPTION
		"this variable shows the number of the rip neighbours."
::= {usrIpRouting 16}

usrIpRipGenJitter	OBJECT-TYPE
	SYNTAX		INTEGER {
				enabled(1),
				disabled(2)
			}
	ACCESS		read-write
	STATUS		mandatory
	DESCRIPTION
		"this variable is used to enable or disable the rip packet
		 jitter feature."
::= {usrIpRouting 17}

usrIpRipIfTable	OBJECT-TYPE
	SYNTAX		SEQUENCE OF UsrIpRipIfEntry
	ACCESS		not-accessible
	STATUS		mandatory
	DESCRIPTION
		"rci uses interface block to describe the system's network interface
		 which is similar to pilgrim portal."
::= {usrIpRouting 18}

usrIpRipIfEntry	OBJECT-TYPE
	SYNTAX		UsrIpRipIfEntry
	ACCESS		not-accessible
	STATUS		mandatory
	DESCRIPTION
		"an entry of rip interface block."
	INDEX {usrIpRipIfEntAddr, usrIpRipIfEntAddrLessIf}
::= {usrIpRipIfTable 1}

UsrIpRipIfEntry ::= SEQUENCE {
	usrIpRipIfEntAddr			IpAddress,
	usrIpRipIfEntAddrLessIf		INTEGER,
	usrIpRipIfVersion			INTEGER,
	usrIpRipIfType				INTEGER,
	usrIpRipIfAdminStat			INTEGER,
	usrIpRipIfMetric			INTEGER,
	usrIpRipIfSendDefault		INTEGER,
	usrIpRipIfAcceptDefault		INTEGER,
	usrIpRipIfSubnetsOnly		INTEGER,
	usrIpRipIfSilent			INTEGER,
	usrIpRipIfSplitHorizon		INTEGER,
	usrIpRipIfPoison			INTEGER,
	usrIpRipIfFlash			INTEGER,
	usrIpRipIfDfltRouteMetric	INTEGER,
	usrIpRipIfPortDown			INTEGER,
	usrIpRipIfStat				INTEGER,
	usrIpRip2IfStatRcvBadPackets	INTEGER,
	usrIpRip2IfStatRcvBadRoutes	INTEGER,
	usrIpRip2IfStatSendUpdates	INTEGER
}

usrIpRipIfEntAddr	OBJECT-TYPE
	SYNTAX		IpAddress
	ACCESS		read-only
	STATUS		mandatory
	DESCRIPTION
		"the interface ip address."
::= {usrIpRipIfEntry 1}

usrIpRipIfEntAddrLessIf	OBJECT-TYPE
	SYNTAX			INTEGER
	ACCESS			read-only
	STATUS			mandatory
	DESCRIPTION
		"this column is used when the interface ip address is not specified.
		 in general, it is equal to network id."
::= {usrIpRipIfEntry 2}

usrIpRipIfVersion	OBJECT-TYPE
	SYNTAX		INTEGER {
				ripv1(1),
				ripv2(2)
			}
	ACCESS		read-write
	STATUS		mandatory
	DESCRIPTION
		"this variable tells what version of rip this interface is running."
::= {usrIpRipIfEntry 3}

usrIpRipIfType	OBJECT-TYPE
	SYNTAX	INTEGER {
			broadcast(1),
			non-broadcast(2),
			point-to-point(3)
		}
	ACCESS	read-write
	STATUS	mandatory
	DESCRIPTION
		"this variable shows the interface type, i.e. broadcast,
		 non-broadcast, point-to-point and undefined."
::= {usrIpRipIfEntry 4}

usrIpRipIfAdminStat	OBJECT-TYPE
	SYNTAX		INTEGER {
				enabled(1),
				disabled(2)
			}
	ACCESS		read-write
	STATUS		mandatory
	DESCRIPTION
		"this variable shows whether the rip is enabled for this interface."
::= {usrIpRipIfEntry 5}

usrIpRipIfMetric	OBJECT-TYPE
	SYNTAX		INTEGER (1..16)
	ACCESS		read-write
	STATUS		mandatory
	DESCRIPTION
		"this variable is to define the metric for this interface."
::= {usrIpRipIfEntry 6}

usrIpRipIfSendDefault	OBJECT-TYPE
	SYNTAX			INTEGER {
					enabled(1),
					disabled(2)
				}
	ACCESS			read-write
	STATUS			mandatory
	DESCRIPTION
		"this variable is to enable advertising the default route."
::= {usrIpRipIfEntry 7}

usrIpRipIfAcceptDefault	OBJECT-TYPE
	SYNTAX			INTEGER {
					enabled(1),
					disabled(2)
				}
	ACCESS			read-write
	STATUS			mandatory
	DESCRIPTION
		"this variable is to enable accepting the default route."
::= {usrIpRipIfEntry 8}

usrIpRipIfSubnetsOnly	OBJECT-TYPE
	SYNTAX			INTEGER {
					enabled(1),
					disabled(2)
				}
	ACCESS			read-write
	STATUS			mandatory
	DESCRIPTION
		"this variable is to enable this interface to advertise
		 only subnet routes only."
::= {usrIpRipIfEntry 9}

usrIpRipIfSilent	OBJECT-TYPE
	SYNTAX		INTEGER {
				enabled(1),
				disabled(2)
			}
	ACCESS		read-write
	STATUS		mandatory
	DESCRIPTION
		"this variable is to enable listen-only feature for this interface."
::= {usrIpRipIfEntry 10}

usrIpRipIfSplitHorizon	OBJECT-TYPE
	SYNTAX			INTEGER {
					enabled(1),
					disabled(2)
				}
	ACCESS			read-write
	STATUS			mandatory
	DESCRIPTION
		"this variable is to enable split horizon."
::= {usrIpRipIfEntry 11}

usrIpRipIfPoison	OBJECT-TYPE
	SYNTAX		INTEGER {
				enabled(1),
				disabled(2)
			}
	ACCESS		read-write
	STATUS		mandatory
	DESCRIPTION
		"this variable is to enable poison reverse."
::= {usrIpRipIfEntry 12}

usrIpRipIfFlash	OBJECT-TYPE
	SYNTAX		INTEGER {
				enabled(1),
				disabled(2)
			}
	ACCESS		read-write
	STATUS		mandatory
	DESCRIPTION
		"this variable is to enable sending flash update."
::= {usrIpRipIfEntry 13}

usrIpRipIfDfltRouteMetric	OBJECT-TYPE
	SYNTAX				INTEGER (1..16)
	ACCESS				read-write
	STATUS				mandatory
	DESCRIPTION
		"this variable specifies the metric of the default route."
::= {usrIpRipIfEntry 14}

usrIpRipIfPortDown	OBJECT-TYPE
	SYNTAX		INTEGER {
				down(1),
				up(2)
			}
	ACCESS		read-only
	STATUS		mandatory
	DESCRIPTION
		"this variable denotes the status of the physical port."
::= {usrIpRipIfEntry 15}

usrIpRipIfStat	OBJECT-TYPE
	SYNTAX	INTEGER {
			create(1),
			delete(2)
		}
	ACCESS	read-write
	STATUS	mandatory
	DESCRIPTION
		"this variable is to delete the rip interface."
::= {usrIpRipIfEntry 16}

usrIpRip2IfStatRcvBadPackets	OBJECT-TYPE
	SYNTAX				INTEGER
	ACCESS				read-only
	STATUS				mandatory
	DESCRIPTION
		"ripv2 received bad packet counter."
::= {usrIpRipIfEntry 17}

usrIpRip2IfStatRcvBadRoutes	OBJECT-TYPE
	SYNTAX				INTEGER
	ACCESS				read-only
	STATUS				mandatory
	DESCRIPTION
		"ripv2 received bad route counter."
::= {usrIpRipIfEntry 18}

usrIpRip2IfStatSendUpdates	OBJECT-TYPE
	SYNTAX				INTEGER
	ACCESS				read-only
	STATUS				mandatory
	DESCRIPTION
		"ripv2 sent update packet counter."
::= {usrIpRipIfEntry 19}

usrIpRip2IfConfTable	OBJECT-TYPE
	SYNTAX			SEQUENCE OF UsrIpRip2IfConfEntry
	ACCESS			not-accessible
	STATUS			mandatory
	DESCRIPTION
		"table for ripv2 specific interface configuration information"
::= {usrIpRouting 19}

usrIpRip2IfConfEntry	OBJECT-TYPE
	SYNTAX			UsrIpRip2IfConfEntry
	ACCESS			not-accessible
	STATUS			mandatory
	DESCRIPTION
		"an entry of ripv2 interface configuration table."
	INDEX {rip2IfConfAddress, rip2IfConfIndex}
::= {usrIpRip2IfConfTable 1}

UsrIpRip2IfConfEntry ::= SEQUENCE {
	rip2IfConfAddress			IpAddress,
	rip2IfConfIndex			INTEGER,
	rip2IfConfDomain			INTEGER,
	rip2IfConfAuthType			INTEGER,
	rip2IfConfAuthKey			OCTET STRING,
	rip2IfConfSend				INTEGER,
	rip2IfConfReceive			INTEGER,
	rip2IfConfDefaultMetric		INTEGER,
	rip2IfConfStatus			INTEGER,
	rip2IfConfSrcAddress		INTEGER
}

rip2IfConfAddress	OBJECT-TYPE
	SYNTAX		IpAddress
	ACCESS		read-only
	STATUS		mandatory
	DESCRIPTION
		"the network interface address."
::= {usrIpRip2IfConfEntry 1}

rip2IfConfIndex	OBJECT-TYPE
	SYNTAX		INTEGER
	ACCESS		read-only
	STATUS		mandatory
	DESCRIPTION
		"the network id."
::= {usrIpRip2IfConfEntry 2}

rip2IfConfDomain	OBJECT-TYPE
	SYNTAX		INTEGER
	ACCESS		not-accessible
	STATUS		mandatory
	DESCRIPTION
		"this thing is obsolete."
::= {usrIpRip2IfConfEntry 3}

rip2IfConfAuthType	OBJECT-TYPE
	SYNTAX		INTEGER {
				none(1),
				simple(2),
				md5(3)
			}
	ACCESS		read-write
	STATUS		mandatory
	DESCRIPTION
		"this variable specifies the authentication type.  md5 is not 
		 supported in this version yet."
::= {usrIpRip2IfConfEntry 4}

rip2IfConfAuthKey	OBJECT-TYPE
	SYNTAX		OCTET STRING (SIZE(16))
	ACCESS		read-write
	STATUS		mandatory
	DESCRIPTION
		"the authentication key is defined here."
::= {usrIpRip2IfConfEntry 5}

rip2IfConfSend		OBJECT-TYPE
	SYNTAX		INTEGER {
				none(1),
				version1(2),
				compatible(3),
				version2(4)
			}
	ACCESS		read-write
	STATUS		mandatory
	DESCRIPTION
		"this variable defines the send policy."
::= {usrIpRip2IfConfEntry 6}

rip2IfConfReceive	OBJECT-TYPE
	SYNTAX		INTEGER {
				version1(1),
				version2(2),
				both(3),
				none(4)
			}
	ACCESS		read-write
	STATUS		mandatory
	DESCRIPTION
		"this variable defines the receive policy."
::= {usrIpRip2IfConfEntry 7}

rip2IfConfDefaultMetric	OBJECT-TYPE
	SYNTAX		INTEGER
	ACCESS		read-write
	STATUS		mandatory
	DESCRIPTION
		"this variable defines the default metric of this network interface."
::= {usrIpRip2IfConfEntry 8}

rip2IfConfStatus	OBJECT-TYPE
	SYNTAX		INTEGER {
				enabled(1),
				disabled(2)
			}
	ACCESS		read-write
	STATUS		mandatory
	DESCRIPTION
		""
::= {usrIpRip2IfConfEntry 9}

rip2IfConfSrcAddress	OBJECT-TYPE
	SYNTAX			INTEGER
	ACCESS			read-only
	STATUS			mandatory
	DESCRIPTION
		""
::= {usrIpRip2IfConfEntry 10}

          usrIpDelRouteAll OBJECT-TYPE
              SYNTAX  INTEGER
              ACCESS  read-write
              STATUS  mandatory
              DESCRIPTION
                      "This object is used to clear the hole routing table"
              ::= { usrIpRouting 20 }

usrIPRterBaseCfgFileName OBJECT-TYPE
        SYNTAX   DisplayString 
        ACCESS   read-write
        STATUS   mandatory
        DESCRIPTION 
                      "The name of a ConfigFile to read/write
                      permanent database records. If the value of this
                      object is an empty string, then the SLIP process
                      uses the default name `@file://SlipFile.cfg'."
::= { usrIpRouting 21 } 
                
usrIPRterBaseCFMSaveStatus OBJECT-TYPE
        SYNTAX  UsrConfigStatus
        ACCESS  read-write
        STATUS  mandatory
        DESCRIPTION
                      "Setting the value of this object to `save'
                      causes the values of the SLIP Base Group
                      entries to be written out to the current SLIP
                      config file. While the new config file is being
                      written, the SLIP process will set the value
                      of this flag set to `saving''. Any attempts to set
                      the value while it is  not `normal' (i.e. the file
                      is currently being written to the config file)
                      while result in a badValue error being returned.
                      Setting the value to `normal' will result in no
                      action."
::= { usrIpRouting 22 }

-- ------------------------------------------------------------

          -- the USR IP Routing Table Head Structure

          usrIpRTH OBJECT-TYPE
              SYNTAX  SEQUENCE OF UsrIpRTHEntry
              ACCESS  not-accessible
              STATUS  mandatory
              DESCRIPTION
                      "This entity's IP Routing table."
              ::= { usrIpRouting 23 }

          usrIpRTHEntry OBJECT-TYPE
              SYNTAX  UsrIpRTHEntry
              ACCESS  not-accessible
              STATUS  mandatory
              DESCRIPTION
                      "A route to a particular destination."
              INDEX   { usrIpRTHDest, usrIpRTHMask, usrIpRTHNhId }
              ::= { usrIpRTH 1 }

          UsrIpRTHEntry ::=
              SEQUENCE {
                  usrIpRTHDest
                      IpAddress,
                  usrIpRTHMask
                      IpAddress,
                  usrIpRTHProto
                      INTEGER,
                  usrIpRTHMetric
                      INTEGER,
                  usrIpRTHClass
                      INTEGER,
                  usrIpRTHFwdFlags
                      INTEGER,
                  usrIpRTHAge
                      INTEGER,
                  usrIpRTHNhId
                      INTEGER,
                  usrIpRTHNextHop
                      IpAddress,
                  usrIpRTHIfIndex
                      INTEGER
              }

          usrIpRTHDest OBJECT-TYPE
              SYNTAX  IpAddress
              ACCESS  read-write
              STATUS  mandatory
              DESCRIPTION
                      "The destination IP address of this route.  An
                      entry with a value of 0.0.0.0 is considered a
                      default route.  Multiple routes to a single
                      destination can appear in the table, but access to
                      such multiple entries is dependent on the table-
                      access mechanisms defined by the network
                      management protocol in use."
	         --CONFIGURABLE
              ::= { usrIpRTHEntry 1 }

          usrIpRTHMask OBJECT-TYPE
              SYNTAX  IpAddress
              ACCESS  read-write
              STATUS  mandatory
              DESCRIPTION
                      "Indicate the mask to be logical-ANDed with the
                      destination address before being compared to the
                      value in the ipRTHDest field.  For those systems
                      that do not support arbitrary subnet masks, an
                      agent constructs the value of the ipRTHMask by
                      determining whether the value of the correspondent
                      ipRTHDest field belong to a class-A, B, or C
                      network, and then using one of:

                           mask           network
                           255.0.0.0      class-A
                           255.255.0.0    class-B
                           255.255.255.0  class-C

                      If the value of the ipRTHDest is 0.0.0.0 (a
                      default route), then the mask value is also
                      0.0.0.0.  It should be noted that all IP routing
                      subsystems implicitly use this mechanism."
	      --CONFIGURABLE
              ::= { usrIpRTHEntry 2 }

          usrIpRTHProto OBJECT-TYPE
              SYNTAX  INTEGER {
                          other(0),       -- none of the following

                          local(1),       -- static local

                          remote(2),      -- static remote

                          special(3),     -- static special

                                          -- the remaining values are
                                          -- all gateway routing
                                          -- protocols

                          ospf(4),        -- OSPF
                          ospfExt(5),     -- OSPF External
                          ospfDisc3(6),   -- OSPF discard routes
                          ospfDisc7(7),   -- OSPF discard routes
                          rip(8),         -- RIP
                          ripDisc(9),     -- RIP discard routes
                          egp(10),        -- EGP
                          bgpExt(11),     -- BGP External
                          bgpInt(12),     -- BGP Internal
                          bgpAggrDisc(13),-- BGP Aggregate
			  redistrib(14)   -- Server redistribution
                      }
              ACCESS  read-only
              STATUS  mandatory
              DESCRIPTION
                      "The routing mechanism via which this route was
                      learned.  Inclusion of values for gateway routing
                      protocols is not intended to imply that hosts
                      should support those protocols."
              ::= { usrIpRTHEntry 3 }

          usrIpRTHMetric OBJECT-TYPE
              SYNTAX  INTEGER
              ACCESS  read-write
              STATUS  mandatory
              DESCRIPTION
                      "The primary routing metric for this route.  The
                      semantics of this metric are determined by the
                      routing-protocol specified in the route's
                      ipRTHProto value.  If this metric is not used,
                      its value should be set to -1."
              --CONFIGURABLE
              ::= { usrIpRTHEntry 4 }

          usrIpRTHClass OBJECT-TYPE
              SYNTAX  INTEGER
              ACCESS  read-write
              STATUS  mandatory
              DESCRIPTION
                      "The forward class is preference class associated
                      with this route.  There are 3 classes; the lower
                      the class the more preferred the route.  
                          Local routes are in Class 0.  These are the 
                          most preferred routes.

                          OSPF Internal routes are also in Class 0.  OSPF
                          internal routes are less preferred than Local
                          Routes.

                          OSPF External routes are Class 1 or Class 2.

                          Static configured and RIP routes are Class 1.

                          BGP and EGP routes are Class 2."
              ::= { usrIpRTHEntry 5 }

          usrIpRTHFwdFlags OBJECT-TYPE
              SYNTAX  INTEGER
              ACCESS  read-write
              STATUS  mandatory
              DESCRIPTION
                      "Forward flags are hints to the forwarding engine
                      as to what to do with the incoming packet."
              ::= { usrIpRTHEntry 6 }

          usrIpRTHAge OBJECT-TYPE
              SYNTAX  INTEGER
              ACCESS  read-write
              STATUS  mandatory
              DESCRIPTION
                      "The number of seconds since this route was last
                      updated or otherwise determined to be correct.
                      Note that no semantics of `too old' can be implied
                      except through knowledge of the routing protocol
                      by which the route was learned."
              ::= { usrIpRTHEntry 7 }

          usrIpRTHNhId OBJECT-TYPE
              SYNTAX  INTEGER
              ACCESS  read-write
              STATUS  mandatory
              DESCRIPTION
                      "The index into the globally defined Next Hop
                       Block."
              ::= { usrIpRTHEntry 8 }

          usrIpRTHNextHop OBJECT-TYPE
              SYNTAX  IpAddress
              ACCESS  read-write
              STATUS  mandatory
              DESCRIPTION
                      "The IP address of the next hop of this route.
                      (In the case of a route bound to an interface
                      which is realized via a broadcast media, the value
                      of this field is the agent's IP address on that
                      interface.)"
	       --CONFIGURABLE
              ::= { usrIpRTHEntry 9 }

          usrIpRTHIfIndex OBJECT-TYPE
              SYNTAX  INTEGER
              ACCESS  read-write
              STATUS  mandatory
              DESCRIPTION
                      "The index value which uniquely identifies the
                      local interface through which the next hop of this
                      route should be reached.  The interface identified
                      by a particular value of this index is the same
                      interface as identified by the same value of
                      ifIndex."
              ::= { usrIpRTHEntry 10 }

-- ------------------------------------------------------------

          -- the USR IP Routing Table Entry Structure

          usrIpRTE OBJECT-TYPE
              SYNTAX  SEQUENCE OF UsrIpRTEEntry
              ACCESS  not-accessible
              STATUS  mandatory
              DESCRIPTION
                      "This entity's IP Routing table."
              ::= { usrIpRouting 24 }

          usrIpRTEEntry OBJECT-TYPE
              SYNTAX  UsrIpRTEEntry
              ACCESS  not-accessible
              STATUS  mandatory
              DESCRIPTION
                      "A route to a particular destination."
              INDEX   { usrIpRTEDest, usrIpRTEMask, usrIpRTEPref, usrIpRTEMetric, usrIpRTEProto, usrIpRTENhId }
              ::= { usrIpRTE 1 }

          UsrIpRTEEntry ::=
              SEQUENCE {
                  usrIpRTEDest
                      IpAddress,
                  usrIpRTEMask
                      IpAddress,
                  usrIpRTEProto
                      INTEGER,
                  usrIpRTEMetric
                      INTEGER,
                  usrIpRTEAge
                      INTEGER,
                  usrIpRTEFwdFlags
                      INTEGER,
                  usrIpRTEPref
                      INTEGER,
                  usrIpRTENhId
                      INTEGER,
                  usrIpRTENextHop
                      IpAddress,
                  usrIpRTEIfIndex
                      INTEGER
              }

          usrIpRTEDest OBJECT-TYPE
              SYNTAX  IpAddress
              ACCESS  read-write
              STATUS  mandatory
              DESCRIPTION
                      "The destination IP address of this route.  An
                      entry with a value of 0.0.0.0 is considered a
                      default route.  Multiple routes to a single
                      destination can appear in the table, but access to
                      such multiple entries is dependent on the table-
                      access mechanisms defined by the network
                      management protocol in use."
	         --CONFIGURABLE
              ::= { usrIpRTEEntry 1 }

          usrIpRTEMask OBJECT-TYPE
              SYNTAX  IpAddress
              ACCESS  read-write
              STATUS  mandatory
              DESCRIPTION
                      "Indicate the mask to be logical-ANDed with the
                      destination address before being compared to the
                      value in the ipRTEDest field.  For those systems
                      that do not support arbitrary subnet masks, an
                      agent constructs the value of the ipRTEMask by
                      determining whether the value of the correspondent
                      ipRTEDest field belong to a class-A, B, or C
                      network, and then using one of:

                           mask           network
                           255.0.0.0      class-A
                           255.255.0.0    class-B
                           255.255.255.0  class-C

                      If the value of the ipRTEDest is 0.0.0.0 (a
                      default route), then the mask value is also
                      0.0.0.0.  It should be noted that all IP routing
                      subsystems implicitly use this mechanism."
	      --CONFIGURABLE
              ::= { usrIpRTEEntry 2 }

          usrIpRTEProto OBJECT-TYPE
              SYNTAX  INTEGER {
                          other(0),       -- none of the following

                          local(1),       -- static local

                          remote(2),      -- static remote

                          special(3),     -- static special

                                          -- the remaining values are
                                          -- all gateway routing
                                          -- protocols

                          ospf(4),        -- OSPF
                          ospfExt(5),     -- OSPF External
                          ospfDisc3(6),   -- OSPF discard routes
                          ospfDisc7(7),   -- OSPF discard routes
                          rip(8),         -- RIP
                          ripDisc(9),     -- RIP discard routes
                          egp(10),        -- EGP
                          bgpExt(11),     -- BGP External
                          bgpInt(12),     -- BGP Internal
                          bgpAggrDisc(13),-- BGP Aggregate
			  redistrib(14)   -- Server redistribution
                      }
              ACCESS  read-only
              STATUS  mandatory
              DESCRIPTION
                      "The routing mechanism via which this route was
                      learned.  Inclusion of values for gateway routing
                      protocols is not intended to imply that hosts
                      should support those protocols."
              ::= { usrIpRTEEntry 3 }

          usrIpRTEMetric OBJECT-TYPE
              SYNTAX  INTEGER
              ACCESS  read-write
              STATUS  mandatory
              DESCRIPTION
                      "The primary routing metric for this route.  The
                      semantics of this metric are determined by the
                      routing-protocol specified in the route's
                      ipRTEProto value.  If this metric is not used,
                      its value should be set to -1."
              --CONFIGURABLE
              ::= { usrIpRTEEntry 4 }

          usrIpRTEAge OBJECT-TYPE
              SYNTAX  INTEGER
              ACCESS  read-write
              STATUS  mandatory
              DESCRIPTION
                      "The number of seconds since this route was last
                      updated or otherwise determined to be correct.
                      Note that no semantics of `too old' can be implied
                      except through knowledge of the routing protocol
                      by which the route was learned."
              ::= { usrIpRTEEntry 5 }

          usrIpRTEFwdFlags OBJECT-TYPE
              SYNTAX  INTEGER
              ACCESS  read-write
              STATUS  mandatory
              DESCRIPTION
                      "Forward flags are hints to the forwarding engine
                      as to what to do with the incoming packet."
              ::= { usrIpRTEEntry 6 }

          usrIpRTEPref OBJECT-TYPE
              SYNTAX  INTEGER
              ACCESS  read-write
              STATUS  mandatory
              DESCRIPTION
                      "The preference associated with this route after
                      it has been added to the routing table."
              ::= { usrIpRTEEntry 7 }

          usrIpRTENhId OBJECT-TYPE
              SYNTAX  INTEGER
              ACCESS  read-write
              STATUS  mandatory
              DESCRIPTION
                      "The index into the globally defined Next Hop
                       Block."
              ::= { usrIpRTEEntry 8 }

          usrIpRTENextHop OBJECT-TYPE
              SYNTAX  IpAddress
              ACCESS  read-write
              STATUS  mandatory
              DESCRIPTION
                      "The IP address of the next hop of this route.
                      (In the case of a route bound to an interface
                      which is realized via a broadcast media, the value
                      of this field is the agent's IP address on that
                      interface.)"
	       --CONFIGURABLE
              ::= { usrIpRTEEntry 9 }

          usrIpRTEIfIndex OBJECT-TYPE
              SYNTAX  INTEGER
              ACCESS  read-write
              STATUS  mandatory
              DESCRIPTION
                      "The index value which uniquely identifies the
                      local interface through which the next hop of this
                      route should be reached.  The interface identified
                      by a particular value of this index is the same
                      interface as identified by the same value of
                      ifIndex."
              ::= { usrIpRTEEntry 10 }

          usrIpRipRXPacketCount	OBJECT-TYPE
          	SYNTAX	INTEGER
                ACCESS	read-only
                STATUS	mandatory
                DESCRIPTION
                        "Number of IP RIP packets received."
          ::= {usrIpRouting 26}

          usrIpRipTXPacketCount	OBJECT-TYPE
          	SYNTAX	INTEGER
                ACCESS	read-only
                STATUS	mandatory
                DESCRIPTION
                        "Number of IP RIP packets transmitted."
          ::= {usrIpRouting 27}

          usrIpRipIncorrectPacketCount	OBJECT-TYPE
          	SYNTAX	INTEGER
                ACCESS	read-only
                STATUS	mandatory
                DESCRIPTION
                        "Number of incorrect IP RIP packets received."
          ::= {usrIpRouting 28}


-- ------------------------------------------------------------

END			-- End Template MIB definitions
--
--	filter.mib - Filter MIB file
--
--
-- Author:         Fritz Reeve
--
-- $Id: usr_filter.mib,v 1.10.2.1 1997/09/17 19:06:29 psd Exp $
--
--  | Copyright (c) 1996 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

Usr-Filter-MIB DEFINITIONS ::= BEGIN

        IMPORTS
          OBJECT-TYPE
                  FROM RFC-1212
          DisplayString, usrFilter, UsrConfigStatus, UsrFilterName
                  FROM USR-DEFINITIONS-MIB;

   -- textual conventions

   -- Begin managed object definitions here...


     usrFilterConfigFileName OBJECT-TYPE
         SYNTAX      DisplayString
         ACCESS      read-write
         STATUS      mandatory
         DESCRIPTION             
            "The name of a ConfigFile to read/write permanent database
             records.  If the value of this object is an empty string, 
             then the Filter Manager process uses the default name 
             `@file://filter.cfg'. "
     ::= { usrFilter 1 }

     usrFilterCFMStatusFlag  OBJECT-TYPE
         SYNTAX      UsrConfigStatus
         ACCESS      read-write
         STATUS      mandatory
         DESCRIPTION
            "Setting the value of this object to `save' causes the values
             of the SNMP Group to be written out to the current config
             file, which is stored in the usrFilterConfigFileName object.
             While the new ConfigFile is being written, the SNMP process
             will set the value of this flag to `saving''. Any
             attempts to set the value while it is not `normal'
             (i.e. the file is currently being written to the
             ConfigFile) will result in a badValue error being
             returned. Setting the value to `normal' will result in no
             action."
     ::= { usrFilter 2 }

     usrFilterTable OBJECT-TYPE
         SYNTAX   SEQUENCE OF UsrFilterEntry
         ACCESS   not-accessible
         STATUS   mandatory
         DESCRIPTION
            "A table of packet filter names.  The actual filter
             information is stored in an ASCII file in flash."
     ::= { usrFilter 3 }

     usrFilterEntry OBJECT-TYPE
         SYNTAX   UsrFilterEntry
         ACCESS   not-accessible
         STATUS   mandatory
         DESCRIPTION
                "The parameters for a packet filter."
         INDEX {usrFilterName}
     ::= { usrFilterTable 1 }

     --
     -- The row is composed of these components
     --

     UsrFilterEntry ::=
         SEQUENCE {
         usrFilterName
            UsrFilterName,
         usrFilterStatus
            INTEGER,
         usrFilterProtocols
            INTEGER,
         usrFilterVerifyError
            DisplayString
     }

     usrFilterName OBJECT-TYPE
         SYNTAX  UsrFilterName
         ACCESS  not-accessible
         STATUS  mandatory
         DESCRIPTION
            "The character name for this filter."
     ::= { usrFilterEntry 1 }

     usrFilterStatus OBJECT-TYPE
         SYNTAX  INTEGER {
                         normal(1),
                         delete(2),
                         verify(3),
                         reading(4),       -- File reading in progress
                         verifying(5),     -- Filter verification in progress
                         compiling(6),     -- Filter compilation in progress
                         verifyFailed(7),  -- Filter verification failed
                         starting(8)       -- Filter operation starting
                         }
         ACCESS  read-write
         STATUS  mandatory
         DESCRIPTION
            "The status of this filter entry. Valid row entries in this
             table have the status field set to normal. The settable values
             are normal and delete.  If the instance is not in the table 
             and the status is normal, this will be an add operation.  If the
             instance is in the table and the status is normal, this will be a
             modify operation.  If the instance is in the table and the 
             status is delete, this will be a delete operation.  The values 
             reading, verifying, and compiling are read-only."
         --CONFIGURABLE
     ::= { usrFilterEntry 2 }

     usrFilterProtocols OBJECT-TYPE
         SYNTAX  INTEGER {
                         bridge(1),        -- Bridge filter
                         bridge-call(2),   -- Bridge Call filter
                         ip(4),            -- IP filter
                         ip-call(8),       -- IP Call filter
                         ipx(16),          -- IPX filter
                         ipx-call(32),     -- IPX Call filter
                         atalk(64),        -- AppleTalk filter
                         atalk-call(128),  -- Appletalk Call filter
                         rip(256),         -- IP RIP filter
                         xrip(512),        -- IPX RIP filter
                         sap(1024),        -- IPX SAP filter
                         rtmp(2048),       -- AppleTalk RTMP filter
                         zip(4096),        -- Appletalk ZIP filter
                         access(8192),     -- Login Access filter
					arap(16384)       -- ARAP Zone filter 
                         }
         ACCESS  read-only
         STATUS  mandatory
         DESCRIPTION
            "Packet filters can be created for the following protocols:
             BRIDGE, IP, IPX, AppleTalk, IP-RIP, IPX-RIP, IPX-SAP, ATALK-RTMP.
             There will be others in the future.  This object uses the 32 bit 
             integer as a bit field.  A single filter specification may contain
             one or more protocols."
     ::= { usrFilterEntry 3 }

     usrFilterVerifyError OBJECT-TYPE
         SYNTAX  DisplayString (SIZE (0..255))
         ACCESS  read-only
         STATUS  mandatory
         DESCRIPTION
            "The error string returned when a filter fails its verification
             process.  Otherwise, this field is NULL."
     ::= { usrFilterEntry 4 }

 usrFilterPktLogFlag OBJECT-TYPE
         SYNTAX  INTEGER {
                         all   (1),
                         radius(2),
                         off   (3)
                         }
         ACCESS  read-write
         STATUS  mandatory
         DESCRIPTION
            "A flag that controls the generation of syslog messages for filtered
             packets.
             
              all    - all filtered packets will generate a syslog message.
              radius - the radius attribute, Filter-Log-Packet will control syslog
                       message generation.
              off    - no syslog messages will be generated."
             
         --CONFIGURABLE
     ::= { usrFilter 4 }
     
usrFilterPktLogSize OBJECT-TYPE
         SYNTAX  INTEGER (0..493)
         ACCESS  read-write
         STATUS  mandatory
         DESCRIPTION
            "The size of a filtered packet that will be included in the actual 
             syslog message.  The default value is 0.  NOTE: syslog can only 
             handle 1028 bytes of ascii text, therefore packet data must 
             converted from hex to ascii, thus reducing the maxium packet data 
             size in half. When syslog begin and end strings are added it is 
             further reduced to 493 bytes." 


             
         --CONFIGURABLE
     ::= { usrFilter 5 }     
     
usrFilterPktLogCount OBJECT-TYPE
         SYNTAX  INTEGER 
         ACCESS  read-only
         STATUS  mandatory
         DESCRIPTION
            "The number of packets that were filtered and sent to syslog."
             
     ::= { usrFilter 6 }          
END         -- End Filter MIB definitions

--
-- For the revision history to work correctly, after a new MIB file has been
-- added to the CVS repository the first time the CVS Admin person needs to
-- set the correct comment string delimter for the file.
--
-- $Log: usr_filter.mib,v $
-- Revision 1.10.2.1  1997/09/17 19:06:29  psd
-- Merged 2.0 to 3.0
--
--Revision 1.11  1997/07/14  19:10:00  ussrey
--fixed bug #1710 usrFilterPktLogSize did not include the default value of 0 in the range. also changed description.
--
--Revision 1.10  1997/04/09  21:04:59  ussrey
-- added usrFilterPktLogCount
--
-- Revision 1.9  1997/03/31 15:50:08  ussrey
-- added usrFilterPktLogSize and usrFilterPktLogFlag used for syslogging filtered packets
--
-- Revision 1.8  1997/02/03 19:41:40  sef
-- fixed typo in last checkin
--
-- Revision 1.7  1997/02/03 19:37:31  sef
-- add ARAP zone filter value
--
-- Revision 1.6  1996/09/25 21:07:37  patton
-- Put in error message
--
-- Revision 1.4.2.2  1996/09/20 15:47:18  freeve
-- Add new status info and object for verify error string
--
-- Revision 1.4.2.1  1996/09/12 18:32:07  jhalpin
-- Fix Filter protocol bits, build usr_cli.mib into usr_netserver.mib, remove unneeded definitions from usr_definitions.mib
--
-- Revision 1.4  1996/04/17 22:56:25  freeve
-- Create and use usrFilteName type
--
-- Revision 1.3  1996/03/29 20:05:19  psd
-- Config file name is not configurable.
--
-- Revision 1.2  1996/03/25 23:59:52  freeve
-- Add Configuration File Manager objects and consolidate the status and 
-- state fields into one.
--
-- Revision 1.1  1996/03/18 21:01:40  freeve
-- First cut at filter MIB
--
--
--

--
--	usr_pm.mib	   The Policy Manager MIB file
--
--
-- Author:         Colm Terrett
--
--




USR-PM-MIB DEFINITIONS ::= BEGIN

	IMPORTS
          OBJECT-TYPE
                  FROM RFC-1212
		TruthValue
			   FROM SNMPv2-TC
          DisplayString, usrPm, UsrConfigStatus,  UsrPolicyfileName
                  FROM USR-DEFINITIONS-MIB;


   -- Begin managed object definitions here...


usrPmCFMStatusFlag OBJECT-TYPE
	SYNTAX		UsrConfigStatus
	ACCESS		read-write
	STATUS		mandatory
	DESCRIPTION
		"This variable controls saving and loading of configuration
           information for the PM Module. The value can 
           be set to either save or load by a management station. The other
           values indicate if any configuration operation and what type
           is in progress."
::= { usrPm 1 }



usrPmCfgFileName OBJECT-TYPE
	SYNTAX      DisplayString
	ACCESS      read-write
	STATUS      mandatory
	DESCRIPTION		
		"The name of a ConfigFile to read/write  permanent database records.
		 If the value of this object is an empty string, then the
		 PM module uses the default name `@file://PMModule.cfg'. "
::= { usrPm 2 }


usrPmConfigTable OBJECT-TYPE
	SYNTAX SEQUENCE OF UsrPmConfigEntry
	ACCESS not-accessible
	STATUS mandatory
	DESCRIPTION
		""
::= { usrPm 3 }

usrPmConfigEntry OBJECT-TYPE
	SYNTAX UsrPmConfigEntry
	ACCESS not-accessible
	STATUS mandatory
	DESCRIPTION
		""
	INDEX { usrPmConfigIndex }
::= { usrPmConfigTable 1 }



UsrPmConfigEntry ::= SEQUENCE {
	usrPmState						TruthValue,
	usrPmRemoteManAccess			TruthValue,
	usrPmRemoteManType				DisplayString,
	usrPmAlarmLevel					INTEGER,
	usrPmAlarmPktSize				INTEGER,
	usrPmAlarmStorageLocation		DisplayString,
	usrPmRefreshTimeout				INTEGER,
	usrPmSupportedApplications		DisplayString,
        usrPmConfigIndex INTEGER
	}


usrPmConfigIndex         OBJECT-TYPE
           SYNTAX          INTEGER
           ACCESS      read-only
           STATUS          mandatory
           DESCRIPTION
              " A unique value for each PM Config file. "
           ::= { usrPmConfigEntry 9 }
 

usrPmState OBJECT-TYPE
 	SYNTAX  TruthValue
 	ACCESS  read-only
 	STATUS  mandatory
 	DESCRIPTION
    "This flag shows whether the Policy Manager has been enabled or disabled."
::= { usrPmConfigEntry 1 }

usrPmRemoteManAccess OBJECT-TYPE
 	SYNTAX  TruthValue
 	ACCESS  read-only
 	STATUS  mandatory
 	DESCRIPTION
    "This flag shows whether the Policy Manager allows remote configuration/management
    by an Management Station or not."
::= { usrPmConfigEntry 2 }

usrPmRemoteManType OBJECT-TYPE
 	SYNTAX  DisplayString
 	ACCESS  read-only
 	STATUS  mandatory
 	DESCRIPTION
    "Describes the means by which a remote management station can configure/manage the
    Policy Manager, e.g. via http, snmp etc."
::= { usrPmConfigEntry 3 }

usrPmAlarmLevel OBJECT-TYPE
 	SYNTAX  INTEGER
 	ACCESS  read-only
 	STATUS  mandatory
 	DESCRIPTION
    "This value determines the grade of information logging done by the Policy Manager
    /Flow Manager."
::= { usrPmConfigEntry 4 }

usrPmAlarmPktSize OBJECT-TYPE
 	SYNTAX  INTEGER
 	ACCESS  read-only
 	STATUS  mandatory
 	DESCRIPTION
    "The size of the packet that will be saved in syslog (or other) records."
::= { usrPmConfigEntry 5 }

usrPmAlarmStorageLocation OBJECT-TYPE
 	SYNTAX  DisplayString
 	ACCESS  read-only
 	STATUS  mandatory
 	DESCRIPTION
    "The destination for alarm messages and records."
::= { usrPmConfigEntry 6 }

usrPmRefreshTimeout OBJECT-TYPE
 	SYNTAX  INTEGER
 	ACCESS  read-only
 	STATUS  mandatory
 	DESCRIPTION
    "The time (in minutes) during checks on validity of flows in the flow database."
::= { usrPmConfigEntry 7 }

usrPmSupportedApplications OBJECT-TYPE
 	SYNTAX  DisplayString
 	ACCESS  read-only
 	STATUS  mandatory
 	DESCRIPTION
    "Client Applications registered with the Policy Manager (QOS,IPSEC,NAT,FW,SOCKS)."
::= { usrPmConfigEntry 8 }



usrPolicyTable OBJECT-TYPE
     SYNTAX   SEQUENCE OF UsrPolicyEntry
     ACCESS   not-accessible
     STATUS   mandatory
     DESCRIPTION
        "A table of policy file names.  The actual policy
         information is stored in an ASCII file in flash."
 ::= { usrPm 4 }

usrPolicyEntry OBJECT-TYPE
     SYNTAX   UsrPolicyEntry
     ACCESS   not-accessible
     STATUS   mandatory
     DESCRIPTION
            "The parameters for a policy file."
--     INDEX {usrFilterName} Wrong changed by Satish
       INDEX {usrPolicyfileName}
 ::= { usrPolicyTable 1 }
 -- ::= { usrFilterTable 1 } Wrong changed to policy table Satish

 --
 -- The row is composed of these components
 --

 -- usrPolicyEntry ::= Changed it to Upper case Satish

 UsrPolicyEntry ::=
     SEQUENCE {
     usrPolicyfileName
       UsrPolicyfileName ,
     usrPolicyfileStatus
        INTEGER,
     usrPolicyfileAssociation
        DisplayString,
     usrPolicyfileVerifyError
        DisplayString,
     usrPolicyPrintAccess
        INTEGER
 }

 usrPolicyfileName OBJECT-TYPE
     SYNTAX  UsrPolicyfileName
     ACCESS  not-accessible
     STATUS  mandatory
     DESCRIPTION
        "The character name for this policy file."
 ::= { usrPolicyEntry 1 }

 -- ::= { usrFilterEntry 1 } Satish modified from Filter to Policy

 usrPolicyfileStatus OBJECT-TYPE
     SYNTAX  INTEGER {
                     normal(1),
                     delete(2),
                     update(4),
                     reading(8),       -- File reading in progress
                     converting(16),     -- Filter verification in progress
                     compiling(32),     -- Filter compilation in progress
                     compileFailed(64),  -- Filter verification failed
                     starting(128)       -- Filter operation starting
                     }
     ACCESS  read-write
     STATUS  mandatory
     DESCRIPTION
        "The status of this policy file entry. Valid row entries in this
         table have the status field set to normal. The settable values
         are normal and delete.  If the instance is not in the table 
         and the status is normal, this will be an add operation.  If the
         instance is in the table and the status is normal, this will be a
         modify operation.  If the instance is in the table and the 
         status is delete, this will be a delete operation.  The values 
         reading, verifying, and compiling are read-only."
     --CONFIGURABLE
 -- ::= { usrFilterEntry 2 } Changed by Satish
 ::= { usrPolicyEntry 2 }

 
 usrPolicyfileAssociation OBJECT-TYPE
     SYNTAX  DisplayString (SIZE (0..255))
     ACCESS  read-only
     STATUS  mandatory
     DESCRIPTION
        "Details the interface/user that this Policy file is associated with."
-- ::= { usrFilterEntry 4 } Changed by Satish
 ::= { usrPolicyEntry 3 }


 usrPolicyfileVerifyError OBJECT-TYPE
     SYNTAX  DisplayString (SIZE (0..255))
     ACCESS  read-only
     STATUS  mandatory
     DESCRIPTION
        "The error string returned when a policy file fails its verification
         process.  Otherwise, this field is NULL."
 -- ::= { usrFilterEntry 4 }
 ::= { usrPolicyEntry 4 }

usrPolicyPrintAccess OBJECT-TYPE
       SYNTAX      INTEGER {
                            off (0),
                            on (1)
                           }
       ACCESS      read-write
       STATUS      mandatory
       DESCRIPTION "This  will allow user policy to be printed 
                    during compilation. "
::= { usrPolicyEntry 5 }

END    -- End Filter MIB definitions

--
--	usr_ip.mib
--
--
-- Author:         Brian Winter
--
-- $Id: 
--
--  | Copyright (c) 1995 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

TERM-PROT-MIB DEFINITIONS ::= BEGIN

	IMPORTS
                RowStatus
                        FROM SNMPv2-TC
		  IpAddress
		 	  	  FROM RFC1155-SMI
          OBJECT-TYPE
                  FROM RFC-1212
          TruthValue
		  FROM SNMPv2-TC
          DisplayString, usrTermProt, UsrConfigStatus
                  FROM USR-DEFINITIONS-MIB;

-- Begin managed object definitions here...

usrTermProtCFMStatusFlag OBJECT-TYPE
	SYNTAX		UsrConfigStatus
	ACCESS		read-write
	STATUS		mandatory
	DESCRIPTION
		"This variable controls saving and loading of configuration
		information for the Terminal Protocols Module. The value can 
		be set to either save or load by a management station. The other
		values indicate if any configuration operation and what type
		is in progress."
::= { usrTermProt 1 }

usrTermProtCfgFileName OBJECT-TYPE
	SYNTAX      DisplayString
	ACCESS      read-only
	STATUS      mandatory
	DESCRIPTION		
		"The name of a ConfigFile to read/write  permanent database records.
		 If the value of this object is an empty string, then the Terminal
		 Protocols module uses the default name `@file://TermProt.cfg'. "
::= { usrTermProt 2 }

usrTermProtConnectedMsg OBJECT-TYPE
	SYNTAX      DisplayString
	ACCESS      read-write
	STATUS      mandatory
	DESCRIPTION		
		"The string which is displayed when a ClearTCP client session
		is connected to the remote TCP host. If the value of this object
		is an empty string, the Terminal Protocols module uses a 
		default of CONNECTED"
	--CONFIGURABLE
::= { usrTermProt 3 }

usrTermProtTelnetEscEnabled OBJECT-TYPE
	SYNTAX      TruthValue
	ACCESS      read-write
	STATUS      mandatory
	DESCRIPTION		
		"If set to false(2), this object prevents all Telnet Clients
		from using the escape character during a session. If they
		enter that character, it will be sent as regular text. If
		set to true(1), the user will be permitted to enter the
		escape character to use the local Telnet command line."
	--CONFIGURABLE
::= { usrTermProt 4 }

usrTermProtAllowManageUsers OBJECT-TYPE
        SYNTAX  INTEGER {
                        manage-off(0),
                        manage-on (1)
                        }
        ACCESS  read-write
        STATUS  mandatory
        DESCRIPTION
                "This variable turns on/off the ability to manage the system
                 through telnet server connections."
        --CONFIGURABLE
::= { usrTermProt 5 }

usrTermProtTelnetShowTryingMsg  OBJECT-TYPE
	SYNTAX      TruthValue
        ACCESS  read-write
        STATUS  mandatory
        DESCRIPTION
                "This variable turns on/off the trying status message for 
                 telnet to terminal servers."
        --CONFIGURABLE
::= { usrTermProt 6 }

usrTermProtTelnetClientAccess OBJECT-TYPE
	SYNTAX      TruthValue
	ACCESS      read-write
	STATUS      mandatory
	DESCRIPTION		
		"This flag decides whether to use the client access table.
		 By default, this value will be false.
		If set to true(1), the users can telnet into the HiPer only
		from ip addresses added in the client access table. If the value
		if set to false (0), the client access table is not referred."
	--CONFIGURABLE
::= { usrTermProt 7 }

usrTelnetAccessTable OBJECT-TYPE
		SYNTAX  SEQUENCE OF UsrTelnetAccessEntry
         	ACCESS  not-accessible
         	STATUS  mandatory
         	DESCRIPTION
            "The Telnet access table"
::= { usrTermProt 8 }

usrTelnetAccessEntry OBJECT-TYPE
         	SYNTAX  UsrTelnetAccessEntry
         	ACCESS  not-accessible
         	STATUS  mandatory
         	DESCRIPTION
            ""
         INDEX   { usrTelnetAccessIpAddr }
::= { usrTelnetAccessTable 1 }

UsrTelnetAccessEntry ::=
         	SEQUENCE {
         	usrTelnetAccessIpAddr IpAddress,
         	usrTelnetAccessIpMask IpAddress,
         	usrTelnetAccessStatus INTEGER
         }

usrTelnetAccessIpAddr OBJECT-TYPE
         	SYNTAX  IpAddress
         	ACCESS  not-accessible
         	STATUS  mandatory
         	DESCRIPTION
            "The IP Address of the station allowed for telnet into HiPerARC."
::= { usrTelnetAccessEntry 1 }

usrTelnetAccessStatus OBJECT-TYPE
	 	SYNTAX   INTEGER {
			add(1),
			normal(2),
			delete(3)
			}
         	ACCESS   read-write
         	STATUS   mandatory
         	DESCRIPTION
            "The status of the entry for this address."
          --CONFIGURABLE
::= { usrTelnetAccessEntry 2 }

usrTelnetAccessIpMask OBJECT-TYPE
         	SYNTAX  IpAddress
         	ACCESS  read-write
         	STATUS  mandatory
         	DESCRIPTION
            "The IP Address of the station allowed for telnet into HiPerARC."
        --CONFIGURABLE
::= { usrTelnetAccessEntry 3 }


usrTelnetTerminalDownloadMode OBJECT-TYPE
			SYNTAX      TruthValue
			ACCESS      read-write
         	STATUS  mandatory
         	DESCRIPTION
            "Will cause telnet client on non-23 port disable ECHO in local
			 and remote side"
        --CONFIGURABLE
::= { usrTermProt 9 }

usrTermProtRloginEscEnabled OBJECT-TYPE
    SYNTAX      TruthValue
    ACCESS      read-write
    STATUS      mandatory
    DESCRIPTION
        "If set to false(2), this object prevents all Rlogin Clients
        from using the escape character during a session. If they
        enter that character, it will be sent as regular text. If
        set to true(1), the user will be permitted to enter the
        escape character to use the local Telnet command line."
    --CONFIGURABLE
::= { usrTermProt 10 }


usrTermProtTelnetShowDisconnect  OBJECT-TYPE
	SYNTAX      TruthValue
        ACCESS  read-write
        STATUS  mandatory
        DESCRIPTION
                "This variable turns on/off the disconnect message for 
                 telnet/cleartcp connections "
        --CONFIGURABLE
::= { usrTermProt 11 }

usrCTCPEncryptionTable OBJECT-TYPE
	SYNTAX SEQUENCE OF UsrCTCPEncryptionEntry
	ACCESS not-accessible
	STATUS mandatory
	DESCRIPTION
		"The table of cleartcp encryption ids and keys. "
::= { usrTermProt 12 }

usrTermProtTelnetBannerFile  OBJECT-TYPE
	SYNTAX      OCTET STRING
        ACCESS  read-write
        STATUS  mandatory
        DESCRIPTION
                " Banner text displayed to admin users telneting to the system"
        --CONFIGURABLE
::= { usrTermProt 13 }

usrCTCPEncryptionEntry OBJECT-TYPE
	SYNTAX UsrCTCPEncryptionEntry
	ACCESS not-accessible
	STATUS mandatory
	DESCRIPTION
                "A (conceptual) entry for one encryption id and key."
	INDEX { usrCTCPEncryptionId }
::= { usrCTCPEncryptionTable 1 }

UsrCTCPEncryptionEntry ::= SEQUENCE {
	usrCTCPEncryptionId		DisplayString,
	usrCTCPEncryptionKey	INTEGER,
        usrCTCPEncryptionStatus     RowStatus
	}

usrCTCPEncryptionId OBJECT-TYPE
	SYNTAX		DisplayString
	ACCESS          not-accessible
	STATUS		mandatory
	DESCRIPTION
		"The logical identifier of the encryption id-key Table. "
::= { usrCTCPEncryptionEntry 1 }

usrCTCPEncryptionKey OBJECT-TYPE
	SYNTAX		INTEGER
	ACCESS          read-write
	STATUS		mandatory
	DESCRIPTION
		"Key number corresponds to the encryption-id in the table"
	--CONFIGURABLE
::= { usrCTCPEncryptionEntry 2 }

usrCTCPEncryptionStatus OBJECT-TYPE
	SYNTAX		RowStatus
	ACCESS          read-write
	STATUS		mandatory
	DESCRIPTION
		"The status of this row of the CTCP Encryption Table. "
	--CONFIGURABLE
::= { usrCTCPEncryptionEntry 3 }


END 
--
--    usr_fr.mib - The USR Frame Relay MIB module
--
--
-- Author:         <Ginny Walker>
--
-- $Id: usr_fr.mib,v 1.9.10.2 1998/06/03 21:47:38 cwieruck Exp $
--
--  | Copyright (c) 1995-97 U.S. Robotics Access Corp., Skokie, IL 60076   |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-FR-MIB DEFINITIONS ::= BEGIN

     IMPORTS
             Counter, TimeTicks
                      FROM RFC1155-SMI
             OBJECT-TYPE
                     FROM RFC-1212
             usrFR, UsrUserName, DisplayString, UsrConfigStatus
                     FROM USR-DEFINITIONS-MIB;

     --  Frame Relay DTE MIB

     --
     --      the range of ifIndex
     --
     Index ::= INTEGER       -- 1..ifNumber

     --
     --      the range of a Data Link Connection Identifier
     --
     DLCI ::= INTEGER (16..1023)        -- 0..DLCINumber


     --
     -- The Frame Relay Base Group.
     --

     usrfrBaseCfgFileName OBJECT-TYPE
         SYNTAX   DisplayString
         ACCESS   read-write
         STATUS   mandatory
         DESCRIPTION
                 "The name of a ConfigFile to read/write
                 permanent database records. If the value of this
                 object is an empty string, then the FR process
                 uses the default name `@file://FrFile.cfg'."
         ::= { usrFR 1 }

     usrfrBaseCFMSaveStatus OBJECT-TYPE
         SYNTAX  UsrConfigStatus
         ACCESS  read-write
         STATUS  mandatory
         DESCRIPTION
                 "Setting the value of this object to `save'
                 causes the values of the FR Base Group
                 entries to be written out to the current FR
                 config file. While the new config file is being
                 written, the FR process will set the value
                 of this flag set to `saving''. Any attempts to set
                 the value while it is  not `normal' (i.e. the file
                 is currently being written to the config file)
                 while result in a badValue error being returned.
                 Setting the value to `normal' will result in no
                 action."
         ::= { usrFR 2 }


     --  Data Link Connection Management Interface
     --
     --      The variables that configure the DLC Management Interface.
     --

     usrfrDlcmiTable OBJECT-TYPE
         SYNTAX   SEQUENCE OF UsrFrDlcmiEntry
         ACCESS   not-accessible
         STATUS   obsolete
         DESCRIPTION
            "The Parameters for the Data Link Connection Management
            Interface for the frame relay service on this
            interface."
         REFERENCE
            "Draft American National Standard T1.617-1991, Annex D"
         ::= { usrFR 3 }

         usrfrDlcmiEntry OBJECT-TYPE
             SYNTAX   UsrFrDlcmiEntry
             ACCESS   not-accessible
             STATUS   obsolete
             DESCRIPTION
                "The Parameters for a particular Data Link Con-
                nection Management Interface."
            INDEX { usrfrDlcmiIfIndex }
            ::= { usrfrDlcmiTable 1 }

         UsrFrDlcmiEntry ::=
             SEQUENCE {
                 usrfrDlcmiIfIndex
                     Index,
                 usrfrDlcmiStateDetect 
                     INTEGER,
                 usrfrDlcmiState
                     INTEGER,
                 usrfrDlcmiLinkStatus
                     INTEGER,
                 usrfrDlcmiAddress
                     INTEGER,
                 usrfrDlcmiAddressLen
                     INTEGER,
                 usrfrDlcmiPollingInterval
                     INTEGER,
                 usrfrDlcmiFullEnquiryInterval
                     INTEGER,
                 usrfrDlcmiErrorThreshold
                     INTEGER,
                 usrfrDlcmiMonitoredEvents
                     INTEGER,
                 usrfrDlcmiMaxSupportedVCs
                     INTEGER,
                 usrfrDlcmiMulticast
                     INTEGER,
                 usrfrDlcmiNetworkSimulation
                     INTEGER,
                 usrfrDlcmiVerificationInterval
                     INTEGER,
                 usrfrDlcmiMaximumTransferUnit
                     INTEGER,
                 usrfrDlcmiAccessRate
                     INTEGER,
                 usrfrDlcmiNewPVCLearning
                     INTEGER,
                 usrfrDlcmiAdminLinkStatus
                     INTEGER
         }

         usrfrDlcmiIfIndex OBJECT-TYPE
             SYNTAX  Index
             ACCESS  read-only
             STATUS  obsolete
             DESCRIPTION
                 "The ifIndex value of the  corresponding  ifEn-
                 try."
             ::= { usrfrDlcmiEntry 1 }

         usrfrDlcmiStateDetect OBJECT-TYPE
             SYNTAX  INTEGER {
                 autodetect (1),
                 manual     (2)
             }
             ACCESS  read-only
             STATUS  obsolete
             DESCRIPTION
                 "This variable indicates whether to autodetect
                 the Management type that is used by the user 
                 or whether to use the type specified by
                 usrfrDlcmiState."
             ::= { usrfrDlcmiEntry 2 }

         usrfrDlcmiState OBJECT-TYPE
             SYNTAX  INTEGER {
                 noLmiConfigured (1),
                 lmiRev1         (2),
                 ansiT1-617-D    (3),  -- ANSI T1.617 Annex D
                 ansiT1-617-B    (4),  -- ANSI T1.617 Annex B
                 ituQ-933-A      (5)   -- ITU Q.933 Annex A
             }
             ACCESS  read-write
             STATUS  obsolete
             DESCRIPTION
                 "This variable states which Data Link Connec-
                 tion Management scheme is active (and by impli-
                 cation, what DLCI it uses) on the  Frame  Relay
                 interface."
             REFERENCE
                 "Draft American National Standard T1.617-1991"
             --CONFIGURABLE
             ::= { usrfrDlcmiEntry 3 }

         usrfrDlcmiLinkStatus OBJECT-TYPE
             SYNTAX  INTEGER {
                 ready         (1),
                 waitForDriver (2),
                 recovery      (3),
                 down          (4),
                 disabled      (5)
             }
             ACCESS  read-only
             STATUS  obsolete
             DESCRIPTION
                 "This variable indicates the status of the Frame 
                 Relay link. Status is determined by the success or
                 failure of the LMI message exchange with the Frame 
                 Relay switch, the WAN interface state and 
                 Administrator Link State."
             ::= { usrfrDlcmiEntry 4 }

         usrfrDlcmiAddress OBJECT-TYPE
             SYNTAX  INTEGER {
                 q921           (1),  -- 13 bit DLCI
                 q922March90    (2),  -- 11 bit DLCI
                 q922November90 (3),  -- 10 bit DLCI
                 q922           (4)   -- Final Standard
             }
             ACCESS  read-only
             STATUS  obsolete
             DESCRIPTION
                 "This variable states which address format is
                 in use on the Frame Relay interface."
             ::= { usrfrDlcmiEntry 5 }

         usrfrDlcmiAddressLen OBJECT-TYPE
             SYNTAX  INTEGER {
                 two-octets   (2),
                 three-octets (3),
                 four-octets  (4)
             }
             ACCESS  read-only
             STATUS  obsolete
             DESCRIPTION
                 "This variable states which address  length  in
                 octets.  In the case of Q922 format, the length
                 indicates the entire length of the address  in-
                 cluding the control portion."
             ::= { usrfrDlcmiEntry 6 }

         usrfrDlcmiPollingInterval OBJECT-TYPE
             SYNTAX  INTEGER (5..30)
             ACCESS  read-write
             STATUS  obsolete
             DESCRIPTION
                 "This is the number of seconds between  succes-
                 sive status enquiry messages."
             REFERENCE
                 "Draft American National  Standard  T1.617-1991,
                 Section D.7 Timer T391."
             DEFVAL { 10 }
             --CONFIGURABLE
           ::= { usrfrDlcmiEntry 7 }


         usrfrDlcmiFullEnquiryInterval OBJECT-TYPE
             SYNTAX  INTEGER (1..255)
             ACCESS  read-write
             STATUS  obsolete
             DESCRIPTION
                 "Number of status enquiry intervals  that  pass
                 before  issuance  of a full status enquiry mes-
                 sage."
             REFERENCE
                 "Draft American National  Standard  T1.617-1991,
                 Section D.7 Counter N391."
             DEFVAL { 6 }
             --CONFIGURABLE
             ::= { usrfrDlcmiEntry 8 }

         usrfrDlcmiErrorThreshold OBJECT-TYPE
             SYNTAX  INTEGER (1..10)
             ACCESS  read-write
             STATUS  obsolete
             DESCRIPTION
                 "This  is  the  maximum  number  of  unanswered
                 Status Enquiries the equipment shall accept be-
                 fore declaring the interface down."
             REFERENCE
                 "Draft American National  Standard  T1.617-1991,
                 Section D.5.1 Counter N392."
             DEFVAL { 3 }
             --CONFIGURABLE
             ::= { usrfrDlcmiEntry 9 }

         usrfrDlcmiMonitoredEvents OBJECT-TYPE
             SYNTAX  INTEGER (1..10)
             ACCESS  read-write
             STATUS  obsolete
             DESCRIPTION
                 "This is the number of status polling intervals
                 over which the error threshold is counted.  For
                 example, if within 'MonitoredEvents' number  of
                 events  the  station  receives 'ErrorThreshold'
                 number of errors, the interface  is  marked  as
                 down."
             REFERENCE
                 "Draft American National  Standard  T1.617-1991,
                 Section D.5.2 Counter N393."
             DEFVAL { 4 }              
             --CONFIGURABLE
             ::= { usrfrDlcmiEntry 10 }

         usrfrDlcmiMaxSupportedVCs OBJECT-TYPE
             SYNTAX  INTEGER
             ACCESS  read-only
             STATUS  obsolete
             DESCRIPTION
                 "The maximum number of Virtual Circuits allowed
                 for  this  interface.   Usually dictated by the
                 Frame Relay network.
                 In response to a SET, if a value less than zero
                 or  higher  than the agent's maximal capability
                 is configured, the agent  should  respond  bad-
                 Value"
             ::= { usrfrDlcmiEntry 11 }

         usrfrDlcmiMulticast OBJECT-TYPE
             SYNTAX   INTEGER {
                 nonBroadcast (1),
                 broadcast    (2)
             }
             ACCESS  read-only
             STATUS  obsolete
             DESCRIPTION
                 "This indicates whether the Frame Relay  inter-
                 face is using a multicast service."
             ::= { usrfrDlcmiEntry 12 }

         usrfrDlcmiNetworkSimulation OBJECT-TYPE
             SYNTAX  INTEGER {
                 on  (1),
                 off (2)
             }
             ACCESS  read-write
             STATUS  obsolete
             DESCRIPTION
                 "This indicates whether the Frame Relay inter-
                 face is simulating the Frame Relay network."
             DEFVAL { 1 }
             -- CONFIGURABLE
             ::= { usrfrDlcmiEntry 13 }

         usrfrDlcmiVerificationInterval OBJECT-TYPE
             SYNTAX  INTEGER (5..30)
             ACCESS  read-write
             STATUS  obsolete
             DESCRIPTION
                 "This is the number of seconds the network side
                 has to wait to consider Status Enquiry message
                 to be lost."
             REFERENCE
                 "Draft American National  Standard  T1.617-1991,
                 Section D.7 Timer T392."
             DEFVAL { 15 }
             --CONFIGURABLE
             ::= { usrfrDlcmiEntry 14 }

         usrfrDlcmiMaximumTransferUnit OBJECT-TYPE
             SYNTAX  INTEGER (260..2048)
             ACCESS  read-write
             STATUS  obsolete
             DESCRIPTION
                 "This is the largest number of bytes the DLL Layer 
                 will attempt to transmit through its phisical inter-
                 face in a single frame."
             DEFVAL { 1600 }
             --CONFIGURABLE
             ::= { usrfrDlcmiEntry 15 }

         usrfrDlcmiAccessRate OBJECT-TYPE
             SYNTAX  INTEGER (0..20480000)
             ACCESS  read-write
             STATUS  obsolete
             DESCRIPTION
                 "This is the speed of access channel, a Frame Relay
                 DLL Layer will use for data transfer. This value is
                 expressed in bits per second.
                 If value 0 is selected, then Access Rate value used
                 by Frame Relay to its calculations will be taken from
                 physical WAN driver."
             REFERENCE
                 "CCITT Recommendation I.370, Section 1.2 access rate"
             DEFVAL { 64000 }
             --CONFIGURABLE
             ::= { usrfrDlcmiEntry 16 }

         usrfrDlcmiNewPVCLearning OBJECT-TYPE
             SYNTAX  INTEGER {
                 on  (1),
                 off (2)
             }
             ACCESS  read-write
             STATUS  obsolete
             DESCRIPTION
                 "This indicates whether the Frame Relay inter-
                 face can dynamicly create a new PVC based on
                 information received in LMI Full Status message."
             DEFVAL { 2 }
             --CONFIGURABLE
             ::= { usrfrDlcmiEntry 17 }

         usrfrDlcmiAdminLinkStatus OBJECT-TYPE
             SYNTAX  INTEGER {
                 enabled  (1),
                 disabled (2)
             }
             ACCESS  read-write
             STATUS  obsolete
             DESCRIPTION
                 "This variable indicates the Administrator status
                 of the Frame Relay link. If it is disabled Frame
                 Relay Link Status will indicate disabled as well."
             DEFVAL { 2 }
             -- CONFIGURABLE
             ::= { usrfrDlcmiEntry 18 }


     -- A Frame Relay service is a multiplexing service.  Data
     -- Link Connection Identifiers enumerate virtual circuits
     -- (permanent or dynamic) which are layered onto the underlying
     -- circuit, represented by ifEntry.  Therefore, each of the entries
     -- in the Standard MIB's Interface Table with an IfType of
     -- Frame Relay represents a Q.922 interface.  Zero or more
     -- virtual circuits are layered onto this interface and provide
     -- interconnection with various remote destinations.
     -- Each such virtual circuit is represented by an entry in the
     -- circuit table.

     --   Circuit Table

     -- The table describing the use of the DLCIs attached to
     -- each Frame Relay Interface.

     usrfrCircuitTable OBJECT-TYPE
         SYNTAX   SEQUENCE OF UsrFrCircuitEntry
         ACCESS   not-accessible
         STATUS   obsolete
         DESCRIPTION
            "A table containing information about specific Data
            Link Connection Identifiers and corresponding virtual
            circuits."
         ::= { usrFR 4 }

         usrfrCircuitEntry OBJECT-TYPE
             SYNTAX   UsrFrCircuitEntry
             ACCESS   not-accessible
             STATUS   obsolete
             DESCRIPTION
                "The information regarding a single  Data  Link
                Connection Identifier."
            INDEX { usrfrCircuitIfIndex, usrfrCircuitDlci }
            ::= { usrfrCircuitTable 1 }

         UsrFrCircuitEntry ::=
             SEQUENCE {
                 usrfrCircuitIfIndex
                     Index,
                 usrfrCircuitDlci
                     DLCI,
                 usrfrCircuitAdminStatus
                     INTEGER,
                 usrfrCircuitOperStatus
                     INTEGER,
                 usrfrCircuitReceivedFECNs
                     Counter,
                 usrfrCircuitReceivedBECNs
                     Counter,
                 usrfrCircuitSentFrames
                     Counter,
                 usrfrCircuitSentOctets
                     Counter,
                 usrfrCircuitReceivedFrames
                     Counter,
                 usrfrCircuitReceivedOctets
                     Counter,
                 usrfrCircuitCreationTime
                     TimeTicks,
                 usrfrCircuitLastTimeChange
                     TimeTicks,
                 usrfrCircuitCIR
                     INTEGER,
                  usrfrCircuitCIRMinRate
                     INTEGER,
                  usrfrCircuitCIRMaxRate 
                     INTEGER,
                 usrfrCircuitUserProfile
                     UsrUserName,
                 usrfrCircuitCIRValue
                     INTEGER,
                 usrfrCircuitBcMax
                     INTEGER,
                 usrfrCircuitBcMin
                     INTEGER,
                 usrfrCircuitCurrentBc
                     INTEGER,
                 usrfrCircuitBe
                     INTEGER,
                 usrfrCircuitTc
                     INTEGER,
                 usrfrCircuitBECNMonitoring
                     INTEGER,
                 usrfrCircuitCMP
                     INTEGER,
                 usrfrCircuitTxFramesToDriver
                     Counter,
                 usrfrCircuitTxOctetsToDriver
                     Counter,
                 usrfrCircuitTxFramesCongested             
                     Counter,             
                 usrfrCircuitTxOctetsCongested
                     Counter,             
                 usrfrCircuitTxFramesDiscarded
                     Counter,             
                 usrfrCircuitTxOctetsDiscarded
                     Counter,             
                 usrfrCircuitTxFramesFromForwarder
                     Counter,             
                 usrfrCircuitTxOctetsFromForwarder    
                     Counter,             
                 usrfrCircuitRxFramesFromDriver    
                     Counter,             
                 usrfrCircuitRxOctetsFromDriver    
                     Counter,             
                 usrfrCircuitRxFramesCongested    
                     Counter,             
                 usrfrCircuitRxOctetsCongested    
                     Counter,             
                 usrfrCircuitRxFramesDiscarded    
                     Counter,             
                 usrfrCircuitRxOctetsDiscarded    
                     Counter,             
                 usrfrCircuitRxFramesByForwarder    
                     Counter,             
                 usrfrCircuitRxOctetsByForwarder    
                     Counter,             
                 usrfrCircuitTxIPProtocolFrames    
                     Counter,             
                 usrfrCircuitRxIPProtocolFrames    
                     Counter,             
                 usrfrCircuitTxIPXProtocolFrames    
                     Counter,             
                 usrfrCircuitRxIPXProtocolFrames    
                     Counter,             
                 usrfrCircuitTxATProtocolFrames    
                     Counter,             
                 usrfrCircuitRxATProtocolFrames    
                     Counter,             
                 usrfrCircuitTxBridgedFrames    
                     Counter,             
                 usrfrCircuitRxBridgedFrames    
                     Counter             
         }

         usrfrCircuitIfIndex OBJECT-TYPE
             SYNTAX  Index
             ACCESS  read-only
             STATUS  obsolete
             DESCRIPTION
                 "The ifIndex Value of the ifEntry this  virtual
                 circuit is layered onto."
             ::= { usrfrCircuitEntry 1 }

         usrfrCircuitDlci OBJECT-TYPE
             SYNTAX  DLCI
             ACCESS  read-only
             STATUS  obsolete
             DESCRIPTION
                 "The Data Link Connection Identifier  for  this
                 virtual circuit."
             REFERENCE
                 "Draft American National  Standard  T1.618-1991,
                 Section 3.3.6"
             ::= { usrfrCircuitEntry 2 }

         usrfrCircuitAdminStatus OBJECT-TYPE
             SYNTAX  INTEGER {
                 enabled  (1),  -- ready to pass packets
                 disabled (2)
             }
             ACCESS  read-write
             STATUS  obsolete
             DESCRIPTION
                 "The desired state of the FR PVC.
                 Disabled (2) state indicates that no operational packets can be
                 passed.  When a managed system initializes, all
                 interfaces start with CircuitAdminStatus in the disabled (2)
                 state.  As a result of either explicit management
                 action or per configuration information retained by
                 the managed system, CircuitAdminStatus is then changed to
                 the enabled(1) state"
             -- CONFIGURABLE
             ::= { usrfrCircuitEntry 3 }

         usrfrCircuitOperStatus OBJECT-TYPE
             SYNTAX  INTEGER {
                 up       (1),  -- ready to pass packets
                 down     (2),
                 disabled (3)
             }
             ACCESS  read-only
             STATUS  obsolete
             DESCRIPTION
                 "The current operational state of the FR PVC.  The
                 disabled(3) state indicates that no operational packets
                 can be passed through this PVC.  It reflects the fact that 
                 usrfrCircuitAdminStatus is disabled. The up(1) describes
                 a state when packets can be sent and received on the PVC.
                 The down(2) indicates that PVC is not not able to
                 operate. The up(1) and down(2) states are set up based
                 on LMI PVCS IE."
             ::= { usrfrCircuitEntry 4 }

         usrfrCircuitReceivedFECNs OBJECT-TYPE
             SYNTAX  Counter
             ACCESS  read-only
             STATUS  obsolete
             DESCRIPTION
                 "Number of frames received from the network in-
                 dicating  forward  congestion since the virtual
                 circuit was created."
             REFERENCE
                 "Draft American National  Standard  T1.618-1991,
                 Section 3.3.3"
             ::= { usrfrCircuitEntry 5 }

         usrfrCircuitReceivedBECNs OBJECT-TYPE
             SYNTAX  Counter
             ACCESS  read-only
             STATUS  obsolete
             DESCRIPTION
                 "Number of frames received from the network in-
                 dicating  backward congestion since the virtual
                 circuit was created."

             REFERENCE
                 "Draft American National  Standard  T1.618-1991,
                 Section 3.3.4"
             ::= { usrfrCircuitEntry 6 }

         usrfrCircuitSentFrames OBJECT-TYPE
             SYNTAX  Counter
             ACCESS  read-only
             STATUS  obsolete
             DESCRIPTION
                 "The number of frames sent  from  this  virtual
                 circuit since it was created."
             ::= { usrfrCircuitEntry 7 }

         usrfrCircuitSentOctets OBJECT-TYPE
             SYNTAX  Counter
             ACCESS  read-only
             STATUS  obsolete
             DESCRIPTION
                 "The number of octets sent  from  this  virtual
                 circuit since it was created."
             ::= { usrfrCircuitEntry 8 }

         usrfrCircuitReceivedFrames OBJECT-TYPE
             SYNTAX  Counter
             ACCESS  read-only
             STATUS  obsolete
             DESCRIPTION
                 "Number of frames received  over  this  virtual
                 circuit since it was created."
             ::= { usrfrCircuitEntry 9 }

         usrfrCircuitReceivedOctets OBJECT-TYPE
             SYNTAX  Counter
             ACCESS  read-only
             STATUS  obsolete
             DESCRIPTION
                 "Number of octets received  over  this  virtual
                 circuit since it was created."
             ::= { usrfrCircuitEntry 10 }

         usrfrCircuitCreationTime OBJECT-TYPE
             SYNTAX  TimeTicks
             ACCESS  read-only
             STATUS  obsolete
             DESCRIPTION
                 "The value of sysUpTime when the  virtual  cir-
                 cuit was created, whether by the Data Link Con-
                 nection Management Interface  or  by  a  SetRe-
                 quest."
             ::= { usrfrCircuitEntry 11 }

         usrfrCircuitLastTimeChange OBJECT-TYPE
             SYNTAX  TimeTicks
             ACCESS  read-only
             STATUS  obsolete
             DESCRIPTION
                 "The value of sysUpTime when last there  was  a
                 change in the virtual circuit state"
             ::= { usrfrCircuitEntry 12 }

         usrfrCircuitCIR OBJECT-TYPE
             SYNTAX  INTEGER {
                 on  (1),
                 off (2)
             }
             ACCESS  read-write
             STATUS  obsolete
             DESCRIPTION
                 "Committed Information Rate (CIR) describes how congestion
                 control is handled.  Off indicates that no attempt
                 at transmit control is made.
                 On indicates that Frame Relay is monitoring amount of
                 data transmited through the phisical interface and
                 restrict this according to CIR rules."
             DEFVAL { 2 }
             --CONFIGURABLE
             ::= { usrfrCircuitEntry 13 }

         usrfrCircuitCIRMinRate OBJECT-TYPE
             SYNTAX  INTEGER (1..56000)
             ACCESS  read-write
             STATUS  obsolete
             DESCRIPTION
                 "When the usrfrCircuitCIR is set to 'constant', 
                 CIRMinRate indicates the constant rate for 
                 transmitting data.  Its value should be the same 
                 as usrfrCircuitCIRMaxRate.  When usrfrCircuitCIR is set 
                 to 'variable', the CIRMinRate indicates the 
                 lowest rate to which to slow transmission when 
                 congestion is detected."
             ::= { usrfrCircuitEntry 14 }

         usrfrCircuitCIRMaxRate OBJECT-TYPE
             SYNTAX  INTEGER (1..56000)
             ACCESS  read-write
             STATUS  obsolete
             DESCRIPTION
                 "When the usrfrCircuitCIR is set to 'constant', 
                 CIRMaxRate indicates the constant rate for
                 transmitting data.  Its value should be the same 
                 as usrfrCircuitCIRMinRate.  When usrfrCircuitCIR is 
                 set to 'variable', the CIRMaxRate indicates
                 the rate to transmit data when congestion is not 
                 reported. After a period of congestion, the 
                 transmission rate will incrementally increase until
                 the Maximum Rate is reached."
             ::= { usrfrCircuitEntry 15 }

         usrfrCircuitUserProfile   OBJECT-TYPE
             SYNTAX  UsrUserName
             ACCESS  read-only
             STATUS  obsolete
             DESCRIPTION
                 "The name of the User Profile that is being used to 
                 contain the characteristics for this DLCI."
             ::= { usrfrCircuitEntry 16 }

         usrfrCircuitCIRValue OBJECT-TYPE
             SYNTAX  INTEGER (0..2048000)
             ACCESS  read-write
             STATUS  obsolete
             DESCRIPTION
                 "The Committed Information Rate is the information
                 transfer rate which the network is committed to
                 transfer under normal conditions. It is averaged over
                 a minimum increment of time Tc."
             REFERENCE 
                 "CCITT Recommendation I.370, Section 1.2 CIR"
             DEFVAL { 32000 }
             --CONFIGURABLE
             ::= { usrfrCircuitEntry 17 }
             
         usrfrCircuitBcMax OBJECT-TYPE
             SYNTAX  INTEGER (0..2048000)
             ACCESS  read-write
             STATUS  obsolete
             DESCRIPTION
                 "The Committed Burst Size is the maximum amount of data
                 (in bits) that the user may offer to the network, under
                 normal conditions, during a time interval Tc.
                 The BcMax value defines the upper boundary of current
                 Bc value."
             REFERENCE 
                 "CCITT Recommendation I.370, Section 1.2 Bc"
             DEFVAL { 32000 }
             --CONFIGURABLE
             ::= { usrfrCircuitEntry 18 }

         usrfrCircuitBcMin OBJECT-TYPE
             SYNTAX  INTEGER (0..2048000)
             ACCESS  read-write
             STATUS  obsolete
             DESCRIPTION
                 "The Committed Burst Size is the maximum amount of data
                 (in bits) that the user may offer to the network, under
                 normal conditions, during a time interval Tc.
                 The BcMin value defines the lower boundary of current
                 Bc value."
             REFERENCE 
                 "CCITT Recommendation I.370, Section 1.2 Bc"
             DEFVAL { 16000 }
             --CONFIGURABLE
             ::= { usrfrCircuitEntry 19 }

         usrfrCircuitCurrentBc OBJECT-TYPE
             SYNTAX  INTEGER (0..2048000)
             ACCESS  read-only
             STATUS  obsolete
             DESCRIPTION
                 "The Committed Burst Size is the maximum amount of data
                 (in bits) that the user may offer to the network, under
                 normal conditions, during a time interval Tc.
                 The CurrentBc value represents currently used Bc value."
             REFERENCE 
                 "CCITT Recommendation I.370, Section 1.2 Bc"
             ::= { usrfrCircuitEntry 20 }

         usrfrCircuitBe OBJECT-TYPE
             SYNTAX  INTEGER (0..2048000)
             ACCESS  read-write
             STATUS  obsolete
             DESCRIPTION
                 "The Excess Burst Size is the maximum allowed amount of data
                 (in bits) by which a user can exceed Bc during a time 
                 interval Tc."
             REFERENCE 
                 "CCITT Recommendation I.370, Section 1.2 Be"
             DEFVAL { 0 }
             --CONFIGURABLE
             ::= { usrfrCircuitEntry 21 }

         usrfrCircuitTc OBJECT-TYPE
             SYNTAX  INTEGER (0..2147483647)
             ACCESS  read-only
             STATUS  obsolete
             DESCRIPTION
                 "The Committed Rate Measurement Interval is
                 a time interval during which the user is allowed
                 to send only the committed amount of date (Bc) and
                 the excess amount of data (Be). This value is
                 calculated and is expressed in miliseconds."
             REFERENCE 
                 "CCITT Recommendation I.370, Section 1.2 Tc"
             ::= { usrfrCircuitEntry 22 }

         usrfrCircuitBECNMonitoring OBJECT-TYPE
             SYNTAX  INTEGER {
                 on  (1),
                 off (2)
             }
             ACCESS  read-write
             STATUS  obsolete
             DESCRIPTION
                 "BECN Monitoring describes if BECN congestion notification
                 control is handled.  Off indicates that no attempt
                 at congestion notification control is made. 
                 On indicates that the BECN bit of the Q.922 header is
                 monitored. When the BECN bit indicates that the Frame
                 Relay switch is experiencing congestion over this DLCI,
                 the transmission rate will be slowed, to value calculated
                 based on usrfrCircuitBcMin. When the bit indicates 
                 alleviation of congestion, the transmission rate will 
                 be incrementally increased back to a value calculated 
                 based on usrfrCircuitBcMax."
             DEFVAL { 2 }
             --CONFIGURABLE
             ::= { usrfrCircuitEntry 23 }

         usrfrCircuitCMP OBJECT-TYPE
             SYNTAX  INTEGER (1..100)
             ACCESS  read-write
             STATUS  obsolete
             DESCRIPTION
                 "The Congestion Monitoring Period - is a period
                 expressed in seconds, during which Frame Relay
                 monitors number of received BECN events."    
             DEFVAL { 10 }
             --CONFIGURABLE
             ::= { usrfrCircuitEntry 24 }

         -- New PVC statistics

         usrfrCircuitTxFramesToDriver OBJECT-TYPE
             SYNTAX  Counter
             ACCESS  read-only
             STATUS  obsolete
             DESCRIPTION
                 "Number of frames passed to a physical driver by
                  this PVC since it was created."
             ::= { usrfrCircuitEntry 25 }

         usrfrCircuitTxOctetsToDriver OBJECT-TYPE
             SYNTAX  Counter
             ACCESS  read-only
             STATUS  obsolete
             DESCRIPTION
                 "Number of bytes passed to a physical driver by
                  this PVC since it was created."
             ::= { usrfrCircuitEntry 26 }

         usrfrCircuitTxFramesCongested OBJECT-TYPE
             SYNTAX  Counter
             ACCESS  read-only
             STATUS  obsolete
             DESCRIPTION
                 "Number of frames congested by a physical driver
                  during transmit action taken by this PVC since 
                  it was created."
             ::= { usrfrCircuitEntry 27 }

         usrfrCircuitTxOctetsCongested OBJECT-TYPE
             SYNTAX  Counter
             ACCESS  read-only
             STATUS  obsolete
             DESCRIPTION
                 "Number of bytes congested by a physical driver
                  during transmit action taken by this PVC since 
                  it was created."
             ::= { usrfrCircuitEntry 28 }

         usrfrCircuitTxFramesDiscarded OBJECT-TYPE
             SYNTAX  Counter
             ACCESS  read-only
             STATUS  obsolete
             DESCRIPTION
                 "Number of frames discarded during transmit 
                  action by this PVC since it was created."
             ::= { usrfrCircuitEntry 29 }

         usrfrCircuitTxOctetsDiscarded OBJECT-TYPE
             SYNTAX  Counter
             ACCESS  read-only
             STATUS  obsolete
             DESCRIPTION
                 "Number of bytes discarded during transmit
                  action by this PVC since it was created."
             ::= { usrfrCircuitEntry 30 }

         usrfrCircuitTxFramesFromForwarder OBJECT-TYPE
             SYNTAX  Counter
             ACCESS  read-only
             STATUS  obsolete
             DESCRIPTION
                 "Number of frames handed down from forwarder to
                  this PVC since it was created."
             ::= { usrfrCircuitEntry 31 }

         usrfrCircuitTxOctetsFromForwarder OBJECT-TYPE
             SYNTAX  Counter
             ACCESS  read-only
             STATUS  obsolete
             DESCRIPTION
                 "Number of bytes handed down from forwarder to
                  this PVC since it was created."
             ::= { usrfrCircuitEntry 32 }

         usrfrCircuitRxFramesFromDriver OBJECT-TYPE
             SYNTAX  Counter
             ACCESS  read-only
             STATUS  obsolete
             DESCRIPTION
                 "Number of frames received from a physical driver by
                  this PVC since it was created."
             ::= { usrfrCircuitEntry 33 }

         usrfrCircuitRxOctetsFromDriver OBJECT-TYPE
             SYNTAX  Counter
             ACCESS  read-only
             STATUS  obsolete
             DESCRIPTION
                 "Number of bytes received from a physical driver by
                  this PVC since it was created."
             ::= { usrfrCircuitEntry 34 }

         usrfrCircuitRxFramesCongested OBJECT-TYPE
             SYNTAX  Counter
             ACCESS  read-only
             STATUS  obsolete
             DESCRIPTION
                 "Number of frames congested by a forwarder
                  during receive action taken by this PVC since 
                  it was created."
             ::= { usrfrCircuitEntry 35 }

         usrfrCircuitRxOctetsCongested OBJECT-TYPE
             SYNTAX  Counter
             ACCESS  read-only
             STATUS  obsolete
             DESCRIPTION
                 "Number of bytes congested by a forwarder
                  during receive action taken by this PVC since 
                  it was created."
             ::= { usrfrCircuitEntry 36 }

         usrfrCircuitRxFramesDiscarded OBJECT-TYPE
             SYNTAX  Counter
             ACCESS  read-only
             STATUS  obsolete
             DESCRIPTION
                 "Number of frames discarded during receive
                  action by this PVC since it was created."
             ::= { usrfrCircuitEntry 37 }

         usrfrCircuitRxOctetsDiscarded OBJECT-TYPE
             SYNTAX  Counter
             ACCESS  read-only
             STATUS  obsolete
             DESCRIPTION
                 "Number of bytes discarded during receive
                  action by this PVC since it was created."
             ::= { usrfrCircuitEntry 38 }

         usrfrCircuitRxFramesByForwarder OBJECT-TYPE
             SYNTAX  Counter
             ACCESS  read-only
             STATUS  obsolete
             DESCRIPTION
                 "Number of frames passed to forwarder by
                  this PVC since it was created."
             ::= { usrfrCircuitEntry 39 }

         usrfrCircuitRxOctetsByForwarder OBJECT-TYPE
             SYNTAX  Counter
             ACCESS  read-only
             STATUS  obsolete
             DESCRIPTION
                 "Number of bytes passed to forwarder by
                  this PVC since it was created."
             ::= { usrfrCircuitEntry 40 }

         usrfrCircuitTxIPProtocolFrames OBJECT-TYPE
             SYNTAX  Counter
             ACCESS  read-only
             STATUS  obsolete
             DESCRIPTION
                 "Number of IP protocol frames sent by
                  this PVC since it was created."
             ::= { usrfrCircuitEntry 41 }

         usrfrCircuitRxIPProtocolFrames OBJECT-TYPE
             SYNTAX  Counter
             ACCESS  read-only
             STATUS  obsolete
             DESCRIPTION
                 "Number of IP protocol frames received by
                  this PVC since it was created."
             ::= { usrfrCircuitEntry 42 }

         usrfrCircuitTxIPXProtocolFrames OBJECT-TYPE
             SYNTAX  Counter
             ACCESS  read-only
             STATUS  obsolete
             DESCRIPTION
                 "Number of IPX protocol frames sent by
                  this PVC since it was created."
             ::= { usrfrCircuitEntry 43 }

         usrfrCircuitRxIPXProtocolFrames OBJECT-TYPE
             SYNTAX  Counter
             ACCESS  read-only
             STATUS  obsolete
             DESCRIPTION
                 "Number of IPX protocol frames received by
                  this PVC since it was created."
             ::= { usrfrCircuitEntry 44 }

         usrfrCircuitTxATProtocolFrames OBJECT-TYPE
             SYNTAX  Counter
             ACCESS  read-only
             STATUS  obsolete
             DESCRIPTION
                 "Number of AppleTalk protocol frames sent by
                  this PVC since it was created."
             ::= { usrfrCircuitEntry 45 }

         usrfrCircuitRxATProtocolFrames OBJECT-TYPE
             SYNTAX  Counter
             ACCESS  read-only
             STATUS  obsolete
             DESCRIPTION
                 "Number of AppleTalk protocol frames received by
                  this PVC since it was created."
             ::= { usrfrCircuitEntry 46 }

         usrfrCircuitTxBridgedFrames OBJECT-TYPE
             SYNTAX  Counter
             ACCESS  read-only
             STATUS  obsolete
             DESCRIPTION
                 "Number of Bridged frames sent by
                  this PVC since it was created."
             ::= { usrfrCircuitEntry 47 }

         usrfrCircuitRxBridgedFrames OBJECT-TYPE
             SYNTAX  Counter
             ACCESS  read-only
             STATUS  obsolete
             DESCRIPTION
                 "Number of Bridged frames received by
                  this PVC since it was created."
             ::= { usrfrCircuitEntry 48 }


             
     --  Error Table

     -- The table describing errors encountered on each Frame
     -- Relay Interface.

     usrfrErrTable OBJECT-TYPE
         SYNTAX   SEQUENCE OF UsrFrErrEntry
         ACCESS   not-accessible
         STATUS   obsolete
         DESCRIPTION
            "A table containing information about Errors on the 
            Frame Relay interface."
         ::= { usrFR 5 }

         usrfrErrEntry OBJECT-TYPE
             SYNTAX   UsrFrErrEntry
             ACCESS   not-accessible
             STATUS   obsolete
             DESCRIPTION
                "The error information for a single Frame Relay
                interface."
            INDEX { usrfrErrIfIndex }
            ::= { usrfrErrTable 1 }

         UsrFrErrEntry ::=
             SEQUENCE {
                 usrfrErrIfIndex
                     Index,
                 usrfrErrUnknownError
                     Counter,
                 usrfrErrReceivedShortFrames
                     Counter,
                 usrfrErrReceivedLongFrames
                     Counter,
                 usrfrErrIllegalDlcis
                     Counter,
                 usrfrErrUnknownDlcis
                     Counter,
                 usrfrErrDlmciProtocolErrs
                     Counter,
                 usrfrErrDlmciUnknownIEs
                     Counter,
                 usrfrErrDlmciSequenceErrs
                     Counter,
                 usrfrErrDlmciUnknownRpts
                     Counter,
                 usrfrStatDLLRxFrames
                     Counter,
                 usrfrStatDLLRxOctets
                     Counter,
                 usrfrStatDLLTxFrames    
                     Counter,
                 usrfrStatDLLTxOctets    
                     Counter,
                 usrfrStatLMIRxFrames    
                     Counter,
                 usrfrStatLMITxFrames    
                     Counter,
                 usrfrStatLMIRxStatusEnquiry    
                     Counter,
                 usrfrStatLMITxStatusEnquiry    
                     Counter,
                 usrfrStatLMIRxStatus    
                     Counter,
                 usrfrStatLMITxStatus    
                     Counter,
                 usrfrStatLMIRxStatusUpdate    
                     Counter,
                 usrfrErrLMINoNetworkResponse    
                     Counter,
                 usrfrErrLMIInvQ922    
                     Counter,
                 usrfrErrLMIInvControlField    
                     Counter,
                 usrfrErrLMIInvProtocolDiscr    
                     Counter,
                 usrfrErrLMIInvCallReference    
                     Counter,
                 usrfrErrLMIInvMessageType    
                     Counter,
                 usrfrErrLMIInvLockingShift    
                     Counter,
                 usrfrErrLMIInvReportType    
                     Counter,
                 usrfrErrLMIInvLIV    
                     Counter,
                 usrfrErrLMIInvSeqNum    
                     Counter,
                 usrfrErrLMIInvPVCStatus    
                     Counter,
                 usrfrErrLMIUnsolicitedMessage    
                     Counter,
                 usrfrErrLMIUnrecognizedIE    
                     Counter,
                 usrfrErrLMIIncompleteMessage    
                     Counter,
                 usrfrErrLMIOutOfOrderIE    
                     Counter,
                 usrfrErrLMIInvSpareBits    
                     Counter,
                 usrfrErrLMIInvExtensionBit    
                     Counter,
                 usrfrErrLMIInvNADBits    
                     Counter
         }

         usrfrErrIfIndex OBJECT-TYPE
             SYNTAX   Index
             ACCESS   read-only
             STATUS   obsolete
             DESCRIPTION
                "The ifIndex Value of the ifEntry this  virtual
                circuit is layered onto."
            ::= { usrfrErrEntry 1 }

         usrfrErrUnknownError OBJECT-TYPE
             SYNTAX   Counter
             ACCESS   read-only
             STATUS   obsolete
             DESCRIPTION
                "An error which is not specified by another counter."
           ::= { usrfrErrEntry 2 }

         usrfrErrReceivedShortFrames OBJECT-TYPE
             SYNTAX   Counter
             ACCESS   read-only
             STATUS   obsolete
             DESCRIPTION
                "Number of frames discarded because they were
                too short."
           ::= { usrfrErrEntry 3 }

         usrfrErrReceivedLongFrames OBJECT-TYPE
             SYNTAX   Counter
             ACCESS   read-only
             STATUS   obsolete
             DESCRIPTION
                "Number of frames discarded because they were
                too long."
           ::= { usrfrErrEntry 4 }

         usrfrErrIllegalDlcis OBJECT-TYPE
             SYNTAX   Counter
             ACCESS   read-only
             STATUS   obsolete
             DESCRIPTION
                "Number of frames discarded because they contained
                illegal DLCIs."
           ::= { usrfrErrEntry 5 }

                 
         usrfrErrUnknownDlcis OBJECT-TYPE
             SYNTAX   Counter
             ACCESS   read-only
             STATUS   obsolete
             DESCRIPTION
                "Number of frames discarded because they contained
                unknown DLCIs."
           ::= { usrfrErrEntry 6 }

                 
         usrfrErrDlmciProtocolErrs OBJECT-TYPE
             SYNTAX   Counter
             ACCESS   read-only
             STATUS   obsolete
             DESCRIPTION
                "Number of Frame Relay protocol errors."
           ::= { usrfrErrEntry 7 }
                 
         usrfrErrDlmciUnknownIEs OBJECT-TYPE
             SYNTAX   Counter
             ACCESS   read-only
             STATUS   obsolete
             DESCRIPTION
                "Number of Frame Relay management message IE errors."
           ::= { usrfrErrEntry 8 }

                 
         usrfrErrDlmciSequenceErrs OBJECT-TYPE
             SYNTAX   Counter
             ACCESS   read-only
             STATUS   obsolete
             DESCRIPTION
                "Number of Frame Relay management message sequence errors."
           ::= { usrfrErrEntry 9 }

                 
         usrfrErrDlmciUnknownRpts OBJECT-TYPE
             SYNTAX   Counter
             ACCESS   read-only
             STATUS   obsolete
             DESCRIPTION
                "Number of Frame Relay management message unknown reports."
           ::= { usrfrErrEntry 10 }


         -- New DLL statistics / error statistics

         usrfrStatDLLRxFrames OBJECT-TYPE
             SYNTAX   Counter
             ACCESS   read-only
             STATUS   obsolete
             DESCRIPTION
                "Number of Frame Relay frames received on this DLL."
           ::= { usrfrErrEntry 11 }

         usrfrStatDLLRxOctets OBJECT-TYPE
             SYNTAX   Counter
             ACCESS   read-only
             STATUS   obsolete
             DESCRIPTION
                "Number of bytes received on this DLL."
           ::= { usrfrErrEntry 12 }

         usrfrStatDLLTxFrames OBJECT-TYPE
             SYNTAX   Counter
             ACCESS   read-only
             STATUS   obsolete
             DESCRIPTION
                "Number of Frame Relay frames transmited on this DLL."
           ::= { usrfrErrEntry 13 }

         usrfrStatDLLTxOctets OBJECT-TYPE
             SYNTAX   Counter
             ACCESS   read-only
             STATUS   obsolete
             DESCRIPTION
                "Number of Octets transmited on this DLL."
           ::= { usrfrErrEntry 14 }

         usrfrStatLMIRxFrames OBJECT-TYPE
             SYNTAX   Counter
             ACCESS   read-only
             STATUS   obsolete
             DESCRIPTION
                "Number of Frame Relay LMI frames received on this DLL."
           ::= { usrfrErrEntry 15 }

         usrfrStatLMITxFrames OBJECT-TYPE
             SYNTAX   Counter
             ACCESS   read-only
             STATUS   obsolete
             DESCRIPTION
                "Number of Frame Relay LMI frames transmited on this DLL."
           ::= { usrfrErrEntry 16 }

         usrfrStatLMIRxStatusEnquiry OBJECT-TYPE
             SYNTAX   Counter
             ACCESS   read-only
             STATUS   obsolete
             DESCRIPTION
                "Number of Frame Relay LMI Status Enquiry frames 
                 receiveded on this DLL."
           ::= { usrfrErrEntry 17 }

         usrfrStatLMITxStatusEnquiry OBJECT-TYPE
             SYNTAX   Counter
             ACCESS   read-only
             STATUS   obsolete
             DESCRIPTION
                "Number of Frame Relay LMI Status Enquiry frames 
                 transmited on this DLL."
           ::= { usrfrErrEntry 18 }

         usrfrStatLMIRxStatus OBJECT-TYPE
             SYNTAX   Counter
             ACCESS   read-only
             STATUS   obsolete
             DESCRIPTION
                "Number of Frame Relay LMI Status frames 
                 receiveded on this DLL."
           ::= { usrfrErrEntry 19 }

         usrfrStatLMITxStatus OBJECT-TYPE
             SYNTAX   Counter
             ACCESS   read-only
             STATUS   obsolete
             DESCRIPTION
                "Number of Frame Relay LMI Status frames 
                 transmited on this DLL."
           ::= { usrfrErrEntry 20 }

         usrfrStatLMIRxStatusUpdate OBJECT-TYPE
             SYNTAX   Counter
             ACCESS   read-only
             STATUS   obsolete
             DESCRIPTION
                "Number of Frame Relay LMI Status Update frames 
                 receiveded on this DLL."
           ::= { usrfrErrEntry 21 }

         usrfrErrLMINoNetworkResponse OBJECT-TYPE
             SYNTAX   Counter
             ACCESS   read-only
             STATUS   obsolete
             DESCRIPTION
                "Number of lacks of Network responses to LMI 
                 Status Enquiry frames sent on this DLL."
           ::= { usrfrErrEntry 22 }

         usrfrErrLMIInvQ922 OBJECT-TYPE
             SYNTAX   Counter
             ACCESS   read-only
             STATUS   obsolete
             DESCRIPTION
                "Number of LMI frames with invalid Q922 header
                 received on this DLL."
           ::= { usrfrErrEntry 23 }

         usrfrErrLMIInvControlField OBJECT-TYPE
             SYNTAX   Counter
             ACCESS   read-only
             STATUS   obsolete
             DESCRIPTION
                "Number of LMI frames with invalid Control Field
                 received on this DLL."
           ::= { usrfrErrEntry 24 }

         usrfrErrLMIInvProtocolDiscr OBJECT-TYPE
             SYNTAX   Counter
             ACCESS   read-only
             STATUS   obsolete
             DESCRIPTION
                "Number of LMI frames with invalid Protocol 
                 Discriominator field received on this DLL."
           ::= { usrfrErrEntry 25 }

         usrfrErrLMIInvCallReference OBJECT-TYPE
             SYNTAX   Counter
             ACCESS   read-only
             STATUS   obsolete
             DESCRIPTION
                "Number of LMI frames with invalid Call Reference
                 field received on this DLL."
           ::= { usrfrErrEntry 26 }

         usrfrErrLMIInvMessageType OBJECT-TYPE
             SYNTAX   Counter
             ACCESS   read-only
             STATUS   obsolete
             DESCRIPTION
                "Number of LMI frames with invalid Message Type
                 field received on this DLL."
           ::= { usrfrErrEntry 27 }

         usrfrErrLMIInvLockingShift OBJECT-TYPE
             SYNTAX   Counter
             ACCESS   read-only
             STATUS   obsolete
             DESCRIPTION
                "Number of LMI frames with invalid Locking Shift
                 IE received on this DLL."
           ::= { usrfrErrEntry 28 }

         usrfrErrLMIInvReportType OBJECT-TYPE
             SYNTAX   Counter
             ACCESS   read-only
             STATUS   obsolete
             DESCRIPTION
                "Number of LMI frames with invalid Report Type
                 IE received on this DLL."
           ::= { usrfrErrEntry 29 }

         usrfrErrLMIInvLIV OBJECT-TYPE
             SYNTAX   Counter
             ACCESS   read-only
             STATUS   obsolete
             DESCRIPTION
                "Number of LMI frames with invalid Link Integrity
                 Verification IE received on this DLL."
           ::= { usrfrErrEntry 30 }

         usrfrErrLMIInvSeqNum OBJECT-TYPE
             SYNTAX   Counter
             ACCESS   read-only
             STATUS   obsolete
             DESCRIPTION
                "Number of LMI frames with invalid Sequence Number
                 field received on this DLL."
           ::= { usrfrErrEntry 31 }

         usrfrErrLMIInvPVCStatus OBJECT-TYPE
             SYNTAX   Counter
             ACCESS   read-only
             STATUS   obsolete
             DESCRIPTION
                "Number of LMI frames with invalid PVC Status
                 IE received on this DLL."
           ::= { usrfrErrEntry 32 }

         usrfrErrLMIUnsolicitedMessage OBJECT-TYPE
             SYNTAX   Counter
             ACCESS   read-only
             STATUS   obsolete
             DESCRIPTION
                "Number of unsolicited LMI frames received on 
                 this DLL."
           ::= { usrfrErrEntry 33 }

         usrfrErrLMIUnrecognizedIE OBJECT-TYPE
             SYNTAX   Counter
             ACCESS   read-only
             STATUS   obsolete
             DESCRIPTION
                "Number of LMI frames with unrecognized
                 IE received on this DLL."
           ::= { usrfrErrEntry 34 }

         usrfrErrLMIIncompleteMessage OBJECT-TYPE
             SYNTAX   Counter
             ACCESS   read-only
             STATUS   obsolete
             DESCRIPTION
                "Number of LMI frames with incomplete mandatory
                 IE received on this DLL."
           ::= { usrfrErrEntry 35 }

         usrfrErrLMIOutOfOrderIE OBJECT-TYPE
             SYNTAX   Counter
             ACCESS   read-only
             STATUS   obsolete
             DESCRIPTION
                "Number of LMI frames with out_of_order IE 
                 received on this DLL."
           ::= { usrfrErrEntry 36 }

         usrfrErrLMIInvSpareBits OBJECT-TYPE
             SYNTAX   Counter
             ACCESS   read-only
             STATUS   obsolete
             DESCRIPTION
                "Number of LMI frames with invalid Spare Bits
                 values in IE received on this DLL."
           ::= { usrfrErrEntry 37 }

         usrfrErrLMIInvExtensionBit OBJECT-TYPE
             SYNTAX   Counter
             ACCESS   read-only
             STATUS   obsolete
             DESCRIPTION
                "Number of LMI frames with invalid Extension Bit
                 value in IE received on this DLL."
           ::= { usrfrErrEntry 38 }

         usrfrErrLMIInvNADBits OBJECT-TYPE
             SYNTAX   Counter
             ACCESS   read-only
             STATUS   obsolete
             DESCRIPTION
                "Number of LMI frames with invalid New, Active or
                 Delete bits in PVCS IE received on this DLL."
           ::= { usrfrErrEntry 39 }

     END
--
--	usr_tftp.mib - The usr TFTP MIB module
--
--
-- Author:         Peter Dobransky
--
-- $Id: usr_tftp.mib,v 1.1.10.2 1997/12/17 19:11:55 psd Exp $
--
--  | Copyright (c) 1996 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-TFTP-MIB DEFINITIONS ::= BEGIN

	IMPORTS
		IpAddress
                  FROM RFC1155-SMI
          OBJECT-TYPE
                  FROM RFC-1212
          DisplayString, usrTftp, UsrConfigStatus
                  FROM USR-DEFINITIONS-MIB;


   -- textual conventions
   -- 
   -- textual conventions are like pre-processor macro in 'C'
   --        (i.e. #define statements)
   -- Use them to define your own 'datatypes'

   -- memory size, expressed in units of 1024bytes


	-- A sample Table definiton.

	usrTftpConfigFileName OBJECT-TYPE
		SYNTAX      DisplayString
		ACCESS      read-write
		STATUS      mandatory
		DESCRIPTION		
		  "The name of a ConfigFile to read/write permanent database records.
		   If the value of this object is an empty string, then the
		   TFTP process uses the default name `@file://TftpProcess.cfg'. "
	::= { usrTftp 1 }

	usrTftpCFMStatusFlag  OBJECT-TYPE
	 	SYNTAX	  UsrConfigStatus
		ACCESS      read-write
		STATUS      mandatory
		DESCRIPTION
		  "Setting the value of this object to `save' causes the values
		   of the TFTP Group to be written out to the current config
		   file, which is stored in the usrTftpConfigFileName object.
		   While the new ConfigFile is being written, the TFTP process
		   will set the value of this flag to `saving''. Any
		   attempts to set the value while it is not `normal'
		   (i.e. the file is currently being written to the
		   ConfigFile) while result in a badValue error being
		   returned. Setting the value to `normal' will result in no
		   action."
	::= { usrTftp 2 }

     usrTftpAccessTable OBJECT-TYPE
		SYNTAX  SEQUENCE OF UsrTftpAccessEntry
         	ACCESS  not-accessible
         	STATUS  mandatory
         	DESCRIPTION
            "The TFTP access table"
	::= { usrTftp 3 }

	usrTftpAccessEntry OBJECT-TYPE
         	SYNTAX  UsrTftpAccessEntry
         	ACCESS  not-accessible
         	STATUS  mandatory
         	DESCRIPTION
            ""
         INDEX   { usrTftpAccessIpAddr }
	::= { usrTftpAccessTable 1 }

	UsrTftpAccessEntry ::=
         	SEQUENCE {
         	usrTftpAccessIpAddr
            IpAddress,
         	usrTftpAccessStatus
            INTEGER
         }

	usrTftpAccessIpAddr OBJECT-TYPE
         	SYNTAX  IpAddress
         	ACCESS  not-accessible
         	STATUS  mandatory
         	DESCRIPTION
            "The IP Address of the station allowed to perform TFTP file
             transfers."
	::= { usrTftpAccessEntry 1 }

	usrTftpAccessStatus OBJECT-TYPE
	 	SYNTAX   INTEGER {
			add(1),
			normal(2),
			delete(3)
			}
         	ACCESS   read-write
         	STATUS   mandatory
         	DESCRIPTION
            "The status of the entry for this address."
          --CONFIGURABLE
         ::= { usrTftpAccessEntry 2 }

     -- TFTP Client Request Table

     usrTftpClientRequestTable OBJECT-TYPE
          SYNTAX  SEQUENCE OF UsrTftpClientRequestEntry
          ACCESS  not-accessible
          STATUS  mandatory
          DESCRIPTION
            "The TFTP Client Request Table"
     ::= { usrTftp 4 }

     usrTftpClientRequestEntry OBJECT-TYPE
          SYNTAX  UsrTftpClientRequestEntry
          ACCESS  not-accessible
          STATUS  mandatory
          DESCRIPTION
            ""
         INDEX   { usrTftpClientRequestFileName }
     ::= { usrTftpClientRequestTable 1 }

     UsrTftpClientRequestEntry ::=
          SEQUENCE {
               usrTftpClientRequestFileName
                    OCTET STRING,
               usrTftpClientRequestServer
                    OCTET STRING,
               usrTftpClientRequestAction
                    INTEGER,
               usrTftpClientRequestMode
                    INTEGER,
               usrTftpClientRequestRexmtTimeout
                    INTEGER,
               usrTftpClientRequestMaxTimeout
                    INTEGER,
               usrTftpClientRequestStatus
                    INTEGER,
               usrTftpClientRequestErrorString
                    DisplayString
         }

     usrTftpClientRequestFileName OBJECT-TYPE
         	SYNTAX  OCTET STRING
         	ACCESS  not-accessible
         	STATUS  mandatory
         	DESCRIPTION
            "The name of the file which will either be requested from or
             sent to the TFTP server."
     ::= { usrTftpClientRequestEntry 1 }

     usrTftpClientRequestServer OBJECT-TYPE
          SYNTAX  OCTET STRING
          ACCESS  read-write
          STATUS  mandatory
          DESCRIPTION
            "The name or IP address of the TFTP server."
          --CONFIGURABLE
         ::= { usrTftpClientRequestEntry 2 }

     usrTftpClientRequestAction OBJECT-TYPE
          SYNTAX  INTEGER {
                    get(1),
                    put(2)
                    }
          ACCESS  read-write
          STATUS  mandatory
          DESCRIPTION
            "The type of request that will be sent to the TFTP server."
          --CONFIGURABLE
         ::= { usrTftpClientRequestEntry 3 }

     usrTftpClientRequestMode OBJECT-TYPE
          SYNTAX  INTEGER {
                    netascii(1),
                    octet(2)
                    }
          ACCESS  read-write
          STATUS  mandatory
          DESCRIPTION
            "The mode in which the file will be transferred."
          DEFVAL { netascii }
          --CONFIGURABLE
         ::= { usrTftpClientRequestEntry 4 }

     usrTftpClientRequestRexmtTimeout OBJECT-TYPE
          SYNTAX  INTEGER (1..60)
          ACCESS  read-write
          STATUS  mandatory
          DESCRIPTION
            "The retransmission time-out."
          DEFVAL { 5 }
          --CONFIGURABLE
         ::= { usrTftpClientRequestEntry 5 }

     usrTftpClientRequestMaxTimeout OBJECT-TYPE
          SYNTAX  INTEGER (1..300)
          ACCESS  read-write
          STATUS  mandatory
          DESCRIPTION
            "The maximum number of seconds to wait for a response from
             the TFTP server. If this value is reached, the TFTP request
             will be timed out."
          DEFVAL { 25 }
          --CONFIGURABLE
         ::= { usrTftpClientRequestEntry 6 }

     usrTftpClientRequestStatus OBJECT-TYPE
          SYNTAX  INTEGER {
                    normal(1),
                    enable(2),
                    getting(3),
                    putting(4),
                    delete(5),
                    error(6)
                    }
          ACCESS  read-write
          STATUS  mandatory
          DESCRIPTION
            "The status of this row. Setting this object to enable(2)
             will cause a request (defined by usrTftpClientRequestAction)
             to be sent to the TFTP server. Depending on the type of
             request, this object will then be set to either getting(3)
             or putting(4). When the request is completed, this object
             will be set to normal(1) which indicates success. If an
             error occurred, this object will be set to error(5) and
             the usrTftpClientRequestErrorString will indicate the
             type of error."
         ::= { usrTftpClientRequestEntry 7 }

     usrTftpClientRequestErrorString OBJECT-TYPE
          SYNTAX  DisplayString
          ACCESS  read-only
          STATUS  mandatory
          DESCRIPTION
            "This object will indicate what type of error occurred when
             the object usrTftpClientRequestStatus is set to error(5)."
         ::= { usrTftpClientRequestEntry 8 }

END         -- End usr TFTP MIB definitions

--
-- For the revision history to work correctly, after a new MIB file has been
-- added to the CVS repository the first time the CVS Admin person needs to
-- set the correct comment string delimter for the file.
--
-- $Log: usr_tftp.mib,v $
-- Revision 1.1.10.2  1997/12/17 19:11:55  psd
-- Added TFTP Client Request table.
--
-- Revision 1.1.10.1  1997/09/17 19:06:41  psd
-- Merged 2.0 to 3.0
--
--Revision 1.1.16.1  1997/09/05  15:09:38  psd
--Changes to MIBs so that they compile using the SimpleTester.
--
--Revision 1.1  1996/05/22  18:39:52  psd
--Initial TFTP security access MIB.
--
--
--
-- Local Variables:
-- tab-width:5
-- tab-stop-list:( 5 10 15 20 25 30 35 40 45 50 55 60 65 70 75 80)
-- End:
--
OSPF-MIB DEFINITIONS ::= BEGIN

    IMPORTS
            MODULE-IDENTITY, OBJECT-TYPE, Counter32, Gauge32,
            Integer32, IpAddress
                FROM SNMPv2-SMI
            TEXTUAL-CONVENTION, TruthValue, RowStatus
                FROM SNMPv2-TC
            MODULE-COMPLIANCE, OBJECT-GROUP          FROM SNMPv2-CONF
            mib-2                                    FROM RFC1213-MIB;

--  This MIB module uses the extended OBJECT-TYPE macro as
--  defined in [9].

ospf MODULE-IDENTITY
        LAST-UPDATED "9501201225Z" -- Fri Jan 20 12:25:50 PST 1995
        ORGANIZATION "IETF OSPF Working Group"
        CONTACT-INFO
       "       Fred Baker
       Postal: Cisco Systems
               519 Lado Drive
               Santa Barbara, California 93111
       Tel:    +1 805 681 0115
       E-Mail: fred@cisco.com

               Rob Coltun
       Postal: RainbowBridge Communications
       Tel:    (301) 340-9416
       E-Mail: rcoltun@rainbow-bridge.com"
    DESCRIPTION
       "The MIB module to describe the OSPF Version 2
       Protocol"
    ::= { mib-2 14 }

--  The Area ID, in OSPF, has the same format as an IP Address,
--  but has the function of defining a summarization point for
--  Link State Advertisements

AreaID ::= TEXTUAL-CONVENTION
    STATUS      current
    DESCRIPTION
       "An OSPF Area Identifier."
    SYNTAX      IpAddress


--  The Router ID, in OSPF, has the same format as an IP Address,
--  but identifies the router independent of its IP Address.

RouterID ::= TEXTUAL-CONVENTION
    STATUS      current
    DESCRIPTION
       "A OSPF Router Identifier."
    SYNTAX      IpAddress


--  The OSPF Metric is defined as an unsigned value in the range

Metric ::= TEXTUAL-CONVENTION
    STATUS      current
    DESCRIPTION
       "The OSPF Internal Metric."
    SYNTAX      Integer32 (0..'FFFF'h)

BigMetric ::= TEXTUAL-CONVENTION
    STATUS      current
    DESCRIPTION
       "The OSPF External Metric."
    SYNTAX      Integer32 (0..'FFFFFF'h)

--  Status Values

Status ::= TEXTUAL-CONVENTION
    STATUS      current
    DESCRIPTION
       "The status of an interface: 'enabled' indicates that
       it is willing to communicate with other OSPF Routers,
       while 'disabled' indicates that it is not."
    SYNTAX      INTEGER { enabled (1), disabled (2) }

--  Time Durations measured in seconds

PositiveInteger ::= TEXTUAL-CONVENTION
    STATUS      current
    DESCRIPTION
       "A positive integer. Values in excess are precluded as
       unnecessary and prone to interoperability issues."
    SYNTAX      Integer32 (0..'7FFFFFFF'h)

HelloRange ::= TEXTUAL-CONVENTION
    STATUS      current
    DESCRIPTION
       "The range of intervals on which hello messages are
       exchanged."
    SYNTAX      Integer32 (1..'FFFF'h)

UpToMaxAge ::= TEXTUAL-CONVENTION
    STATUS      current
    DESCRIPTION
       "The values that one might find or configure for
       variables bounded by the maximum age of an LSA."
    SYNTAX      Integer32 (0..3600)


--  The range of ifIndex

InterfaceIndex ::= TEXTUAL-CONVENTION
    STATUS      current
    DESCRIPTION
       "The range of ifIndex."
    SYNTAX      Integer32


--  Potential Priorities for the Designated Router Election

DesignatedRouterPriority ::= TEXTUAL-CONVENTION
    STATUS      current
    DESCRIPTION
       "The values defined for the priority of a system for
       becoming the designated router."
    SYNTAX      Integer32 (0..'FF'h)

TOSType ::= TEXTUAL-CONVENTION
    STATUS      current
    DESCRIPTION
       "Type of Service is defined as a mapping to the IP Type of
       Service Flags as defined in the IP Forwarding Table MIB

       +-----+-----+-----+-----+-----+-----+-----+-----+
       |                 |                       |     |
       |   PRECEDENCE    |    TYPE OF SERVICE    |  0  |
       |                 |                       |     |
       +-----+-----+-----+-----+-----+-----+-----+-----+

                IP TOS                IP TOS
           Field     Policy      Field     Policy

           Contents    Code      Contents    Code
           0 0 0 0  ==>   0      0 0 0 1  ==>   2
           0 0 1 0  ==>   4      0 0 1 1  ==>   6
           0 1 0 0  ==>   8      0 1 0 1  ==>  10
           0 1 1 0  ==>  12      0 1 1 1  ==>  14
           1 0 0 0  ==>  16      1 0 0 1  ==>  18
           1 0 1 0  ==>  20      1 0 1 1  ==>  22
           1 1 0 0  ==>  24      1 1 0 1  ==>  26
           1 1 1 0  ==>  28      1 1 1 1  ==>  30

       The remaining values are left for future definition."
    SYNTAX      Integer32 (0..30)


--  OSPF General Variables

--      These parameters apply globally to the Router's
--      OSPF Process.

ospfGeneralGroup OBJECT IDENTIFIER ::= { ospf 1 }


    ospfRouterId OBJECT-TYPE
        SYNTAX   RouterID
        MAX-ACCESS   read-write
        STATUS   current
        DESCRIPTION
           "A  32-bit  integer  uniquely  identifying  the
           router in the Autonomous System.

           By  convention,  to  ensure  uniqueness,   this
           should  default  to  the  value  of  one of the
           router's IP interface addresses."
       REFERENCE
          "OSPF Version 2, C.1 Global parameters"
       --CONFIGURABLE
      ::= { ospfGeneralGroup 1 }


    ospfAdminStat OBJECT-TYPE
        SYNTAX   Status
        MAX-ACCESS   read-write
        STATUS   current
        DESCRIPTION
           "The  administrative  status  of  OSPF  in  the
           router.   The  value 'enabled' denotes that the
           OSPF Process is active on at least  one  inter-
           face;  'disabled'  disables  it  on  all inter-
           faces."
 	--CONFIGURABLE
       ::= { ospfGeneralGroup 2 }

    ospfVersionNumber OBJECT-TYPE
        SYNTAX   INTEGER    { version2 (2) }
        MAX-ACCESS   read-only
        STATUS   current
        DESCRIPTION
           "The current version number of the OSPF  proto-
           col is 2."
       REFERENCE
          "OSPF Version 2, Title"
      ::= { ospfGeneralGroup 3 }


    ospfAreaBdrRtrStatus OBJECT-TYPE
        SYNTAX   TruthValue
        MAX-ACCESS   read-only
        STATUS   current
        DESCRIPTION
           "A flag to note whether this router is an  area
           border router."
       REFERENCE
          "OSPF Version 2, Section 3 Splitting the AS into
          Areas"
      ::= { ospfGeneralGroup 4 }


    ospfASBdrRtrStatus OBJECT-TYPE
        SYNTAX   TruthValue
        MAX-ACCESS   read-write
        STATUS   current
        DESCRIPTION
           "A flag to note whether this router is  config-
           ured as an Autonomous System border router."
       REFERENCE
          "OSPF Version 2, Section 3.3  Classification  of
          routers"
       --CONFIGURABLE
      ::= { ospfGeneralGroup 5 }

    ospfExternLsaCount OBJECT-TYPE
        SYNTAX   Gauge32
        MAX-ACCESS   read-only
        STATUS   current
        DESCRIPTION
           "The number of external (LS type 5)  link-state
           advertisements in the link-state database."
       REFERENCE
          "OSPF Version 2, Appendix A.4.5 AS external link
          advertisements"
      ::= { ospfGeneralGroup 6 }


    ospfExternLsaCksumSum OBJECT-TYPE
        SYNTAX   Integer32
        MAX-ACCESS   read-only
        STATUS   current
        DESCRIPTION
           "The 32-bit unsigned sum of the LS checksums of
           the  external  link-state  advertisements  con-
           tained in the link-state  database.   This  sum
           can  be  used  to determine if there has been a
           change in a router's link state  database,  and
           to  compare  the  link-state  database  of  two
           routers."
       ::= { ospfGeneralGroup 7 }


    ospfTOSSupport OBJECT-TYPE
        SYNTAX   TruthValue
        MAX-ACCESS   read-write
        STATUS   current
        DESCRIPTION
           "The router's support for type-of-service rout-
           ing."
       REFERENCE
          "OSPF Version 2,  Appendix  F.1.2  Optional  TOS
          support"
      ::= { ospfGeneralGroup 8 }

    ospfOriginateNewLsas OBJECT-TYPE
        SYNTAX   Counter32
        MAX-ACCESS   read-only
        STATUS   current
        DESCRIPTION
           "The number of  new  link-state  advertisements
           that  have been originated.  This number is in-
           cremented each time the router originates a new
           LSA."
       ::= { ospfGeneralGroup 9 }


    ospfRxNewLsas OBJECT-TYPE
        SYNTAX   Counter32
        MAX-ACCESS   read-only
        STATUS   current
        DESCRIPTION
           "The number of  link-state  advertisements  re-
           ceived  determined  to  be  new instantiations.
           This number does not include  newer  instantia-
           tions  of self-originated link-state advertise-
           ments."
       ::= { ospfGeneralGroup 10 }

    ospfExtLsdbLimit OBJECT-TYPE
        SYNTAX   Integer32 (-1..'7FFFFFFF'h)
        MAX-ACCESS   read-write
        STATUS   current
        DESCRIPTION
           "The  maximum   number   of   non-default   AS-
           external-LSAs entries that can be stored in the
           link-state database.  If the value is -1,  then
           there is no limit.

           When the number of non-default AS-external-LSAs
           in   a  router's  link-state  database  reaches
           ospfExtLsdbLimit, the router  enters  Overflow-
           State.   The   router  never  holds  more  than
           ospfExtLsdbLimit  non-default  AS-external-LSAs
           in  its  database. OspfExtLsdbLimit MUST be set
           identically in all routers attached to the OSPF
           backbone  and/or  any regular OSPF area. (i.e.,
           OSPF stub areas and NSSAs are excluded)."
       DEFVAL { -1 }
       --CONFIGURABLE
       ::= { ospfGeneralGroup 11 }

    ospfMulticastExtensions OBJECT-TYPE
        SYNTAX   Integer32
        MAX-ACCESS   read-write
        STATUS   current
        DESCRIPTION
           "A Bit Mask indicating whether  the  router  is
           forwarding  IP  multicast  (Class  D) datagrams
           based on the algorithms defined in  the  Multi-
           cast Extensions to OSPF.

           Bit 0, if set, indicates that  the  router  can
           forward  IP multicast datagrams in the router's
           directly attached areas (called intra-area mul-
           ticast routing).

           Bit 1, if set, indicates that  the  router  can
           forward  IP  multicast  datagrams  between OSPF
           areas (called inter-area multicast routing).

           Bit 2, if set, indicates that  the  router  can
           forward  IP  multicast  datagrams between Auto-
           nomous Systems (called inter-AS multicast rout-
           ing).

           Only certain combinations of bit  settings  are
           allowed,  namely: 0 (no multicast forwarding is
           enabled), 1 (intra-area multicasting  only),  3
           (intra-area  and  inter-area  multicasting),  5
           (intra-area and inter-AS  multicasting)  and  7
           (multicasting  everywhere). By default, no mul-
           ticast forwarding is enabled."
       DEFVAL { 0 }
       ::= { ospfGeneralGroup 12 }

    ospfExitOverflowInterval OBJECT-TYPE
        SYNTAX   PositiveInteger
        MAX-ACCESS   read-write
        STATUS   current
        DESCRIPTION
           "The number of  seconds  that,  after  entering
           OverflowState,  a  router will attempt to leave
           OverflowState. This allows the router to  again
           originate  non-default  AS-external-LSAs.  When
           set to 0, the router will not  leave  Overflow-
           State until restarted."
       DEFVAL { 0 }
       --CONFIGURABLE
       ::= { ospfGeneralGroup 13 }


    ospfDemandExtensions OBJECT-TYPE
        SYNTAX   TruthValue
        MAX-ACCESS   read-write
        STATUS   current
        DESCRIPTION
           "The router's support for demand routing."
       REFERENCE
          "OSPF Version 2, Appendix on Demand Routing"
      ::= { ospfGeneralGroup 14 }


--      The OSPF Area Data Structure contains information
--      regarding the various areas. The interfaces and
--      virtual links are configured as part of these areas.
--      Area 0.0.0.0, by definition, is the Backbone Area


    ospfAreaTable OBJECT-TYPE
        SYNTAX   SEQUENCE OF OspfAreaEntry
        MAX-ACCESS   not-accessible
        STATUS   current
        DESCRIPTION
           "Information describing the configured  parame-
           ters  and cumulative statistics of the router's
           attached areas."
       REFERENCE
          "OSPF Version 2, Section 6  The Area Data Struc-
          ture"
      ::= { ospf 2 }


    ospfAreaEntry OBJECT-TYPE
        SYNTAX   OspfAreaEntry
        MAX-ACCESS   not-accessible
        STATUS   current
        DESCRIPTION
           "Information describing the configured  parame-
           ters  and  cumulative  statistics of one of the
           router's attached areas."
       INDEX { ospfAreaId }
       ::= { ospfAreaTable 1 }

OspfAreaEntry ::=
    SEQUENCE {
        ospfAreaId
            AreaID,
        ospfAuthType
            Integer32,
        ospfImportAsExtern
            INTEGER,
        ospfSpfRuns
            Counter32,
        ospfAreaBdrRtrCount
            Gauge32,
        ospfAsBdrRtrCount
            Gauge32,
        ospfAreaLsaCount
            Gauge32,
        ospfAreaLsaCksumSum
            Integer32,
        ospfAreaSummary
            INTEGER,
        ospfAreaStatus
            RowStatus
              }

    ospfAreaId OBJECT-TYPE
        SYNTAX   AreaID
        MAX-ACCESS   read-only
        STATUS   current
        DESCRIPTION
           "A 32-bit integer uniquely identifying an area.
           Area ID 0.0.0.0 is used for the OSPF backbone."
       REFERENCE
          "OSPF Version 2, Appendix C.2 Area parameters"
       --CONFIGURABLE
      ::= { ospfAreaEntry 1 }


    ospfAuthType OBJECT-TYPE
        SYNTAX   Integer32
                    -- none (0),
                    -- simplePassword (1)
                    -- md5 (2)
                    -- reserved for specification by IANA (> 2)
        MAX-ACCESS   read-create
        STATUS   obsolete
        DESCRIPTION
           "The authentication type specified for an area.
           Additional authentication types may be assigned
           locally on a per Area basis."
       REFERENCE
          "OSPF Version 2, Appendix E Authentication"
      DEFVAL { 0 }        -- no authentication, by default
      ::= { ospfAreaEntry 2 }

    ospfImportAsExtern OBJECT-TYPE
        SYNTAX   INTEGER    {
                    importExternal (1),
                    importNoExternal (2),
                    importNssa (3)
                  }
        MAX-ACCESS   read-create
        STATUS   current
        DESCRIPTION
           "The area's support for importing  AS  external
           link- state advertisements."
       REFERENCE
          "OSPF Version 2, Appendix C.2 Area parameters"
      DEFVAL { importExternal }
       --CONFIGURABLE
      ::= { ospfAreaEntry 3 }


    ospfSpfRuns OBJECT-TYPE
        SYNTAX   Counter32
        MAX-ACCESS   read-only
        STATUS   current
        DESCRIPTION
           "The number of times that the intra-area  route
           table  has  been  calculated  using this area's
           link-state database.  This  is  typically  done
           using Dijkstra's algorithm."
       ::= { ospfAreaEntry 4 }


    ospfAreaBdrRtrCount OBJECT-TYPE
        SYNTAX   Gauge32
        MAX-ACCESS   read-only
        STATUS   current
        DESCRIPTION
           "The total number of area border routers reach-
           able within this area.  This is initially zero,
           and is calculated in each SPF Pass."
       ::= { ospfAreaEntry 5 }

    ospfAsBdrRtrCount OBJECT-TYPE
        SYNTAX   Gauge32
        MAX-ACCESS   read-only
        STATUS   current
        DESCRIPTION
           "The total number of Autonomous  System  border
           routers  reachable  within  this area.  This is
           initially zero, and is calculated in  each  SPF
           Pass."
       ::= { ospfAreaEntry 6 }


    ospfAreaLsaCount OBJECT-TYPE
        SYNTAX   Gauge32
        MAX-ACCESS   read-only
        STATUS   current
        DESCRIPTION
           "The total number of link-state  advertisements
           in  this  area's link-state database, excluding
           AS External LSA's."
       ::= { ospfAreaEntry 7 }


    ospfAreaLsaCksumSum OBJECT-TYPE
        SYNTAX   Integer32
        MAX-ACCESS   read-only
        STATUS   current
        DESCRIPTION
           "The 32-bit unsigned sum of the link-state  ad-
           vertisements'  LS  checksums  contained in this
           area's link-state database.  This sum  excludes
           external (LS type 5) link-state advertisements.
           The sum can be used to determine if  there  has
           been  a  change  in a router's link state data-
           base, and to compare the link-state database of
           two routers."
       DEFVAL   { 0 }
       ::= { ospfAreaEntry 8 }

    ospfAreaSummary OBJECT-TYPE
        SYNTAX   INTEGER    {
                    noAreaSummary (1),
                    sendAreaSummary (2)
                  }
        MAX-ACCESS   read-create
        STATUS   current
        DESCRIPTION
           "The variable ospfAreaSummary controls the  im-
           port  of  summary LSAs into stub areas.  It has
           no effect on other areas.

           If it is noAreaSummary, the router will neither
           originate  nor  propagate summary LSAs into the
           stub area.  It will rely entirely  on  its  de-
           fault route.

           If it is sendAreaSummary, the router will  both
           summarize and propagate summary LSAs."
       DEFVAL   { noAreaSummary }
       ::= { ospfAreaEntry 9 }


    ospfAreaStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
 	--CONFIGURABLE
       ::= { ospfAreaEntry 10 }


--  OSPF Area Default Metric Table

--      The OSPF Area Default Metric Table describes the metrics
--      that a default Area Border Router will advertise into a
--      Stub area.


    ospfStubAreaTable OBJECT-TYPE
        SYNTAX   SEQUENCE OF OspfStubAreaEntry
        MAX-ACCESS   not-accessible
        STATUS   current
        DESCRIPTION
           "The set of metrics that will be advertised  by
           a default Area Border Router into a stub area."
       REFERENCE
          "OSPF Version 2, Appendix C.2, Area Parameters"
      ::= { ospf 3 }


    ospfStubAreaEntry OBJECT-TYPE
        SYNTAX   OspfStubAreaEntry
        MAX-ACCESS   not-accessible
        STATUS   current
        DESCRIPTION
           "The metric for a given Type  of  Service  that
           will  be  advertised  by  a default Area Border
           Router into a stub area."
       REFERENCE
          "OSPF Version 2, Appendix C.2, Area Parameters"
      INDEX { ospfStubAreaId, ospfStubTOS }
      ::= { ospfStubAreaTable 1 }

OspfStubAreaEntry ::=
    SEQUENCE {
        ospfStubAreaId
            AreaID,
        ospfStubTOS
            TOSType,
        ospfStubMetric
            BigMetric,
        ospfStubStatus
            RowStatus,
        ospfStubMetricType
            INTEGER
              }

    ospfStubAreaId OBJECT-TYPE
        SYNTAX   AreaID
        MAX-ACCESS   read-only
        STATUS   current
        DESCRIPTION
           "The 32 bit identifier for the Stub  Area.   On
           creation,  this  can  be  derived  from the in-
           stance."
       ::= { ospfStubAreaEntry 1 }

    ospfStubTOS OBJECT-TYPE
        SYNTAX   TOSType
        MAX-ACCESS   read-only
        STATUS   current
        DESCRIPTION
           "The  Type  of  Service  associated  with   the
           metric.   On creation, this can be derived from
           the instance."
       ::= { ospfStubAreaEntry 2 }


    ospfStubMetric OBJECT-TYPE
        SYNTAX   BigMetric
        MAX-ACCESS   read-create
        STATUS   current
        DESCRIPTION
           "The metric value applied at the indicated type
           of  service.  By default, this equals the least
           metric at the type of service among the  inter-
           faces to other areas."
       ::= { ospfStubAreaEntry 3 }


    ospfStubStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
 	--CONFIGURABLE
       ::= { ospfStubAreaEntry 4 }

    ospfStubMetricType OBJECT-TYPE
        SYNTAX   INTEGER    {
                    ospfMetric (1),                -- OSPF Metric
                    comparableCost (2),        -- external type 1
                    nonComparable  (3)        -- external type 2
                  }
        MAX-ACCESS   read-create
        STATUS   current
        DESCRIPTION
           "This variable displays the type of metric  ad-
           vertised as a default route."
       DEFVAL   { ospfMetric }
       ::= { ospfStubAreaEntry 5 }

--  OSPF Link State Database

--      The Link State Database contains the Link State
--      Advertisements from throughout the areas that the
--      device is attached to.


    ospfLsdbTable OBJECT-TYPE
        SYNTAX   SEQUENCE OF OspfLsdbEntry
        MAX-ACCESS   not-accessible
        STATUS   current
        DESCRIPTION
           "The OSPF Process's Link State Database."
       REFERENCE
          "OSPF Version 2, Section 12  Link  State  Adver-
          tisements"
      ::= { ospf 4 }


    ospfLsdbEntry OBJECT-TYPE
        SYNTAX   OspfLsdbEntry
        MAX-ACCESS   not-accessible
        STATUS   current
        DESCRIPTION
           "A single Link State Advertisement."
       INDEX { ospfLsdbAreaId, ospfLsdbType,
               ospfLsdbLsid, ospfLsdbRouterId }
       ::= { ospfLsdbTable 1 }

OspfLsdbEntry ::=
    SEQUENCE {
        ospfLsdbAreaId
            AreaID,
        ospfLsdbType
            INTEGER,
        ospfLsdbLsid
            IpAddress,
        ospfLsdbRouterId
            RouterID,
        ospfLsdbSequence
            Integer32,
        ospfLsdbAge
            Integer32,
        ospfLsdbChecksum
            Integer32,
        ospfLsdbAdvertisement
            OCTET STRING
              }

    ospfLsdbAreaId OBJECT-TYPE
        SYNTAX   AreaID
        MAX-ACCESS   read-only
        STATUS   current
        DESCRIPTION
           "The 32 bit identifier of the Area  from  which
           the LSA was received."
       REFERENCE
          "OSPF Version 2, Appendix C.2 Area parameters"
      ::= { ospfLsdbEntry 1 }

-- External Link State Advertisements are permitted
-- for backward compatibility, but should be displayed in
-- the ospfExtLsdbTable rather than here.

    ospfLsdbType OBJECT-TYPE
        SYNTAX   INTEGER    {
                    routerLink (1),
                    networkLink (2),
                    summaryLink (3),
                    asSummaryLink (4),
                    asExternalLink (5), -- but see ospfExtLsdbTable
                    multicastLink (6),
                    nssaExternalLink (7)
                  }
        MAX-ACCESS   read-only
        STATUS   current
        DESCRIPTION
           "The type  of  the  link  state  advertisement.
           Each  link state type has a separate advertise-
           ment format."
       REFERENCE
          "OSPF Version 2, Appendix A.4.1 The  Link  State
          Advertisement header"
      ::= { ospfLsdbEntry 2 }

    ospfLsdbLsid OBJECT-TYPE
        SYNTAX   IpAddress
        MAX-ACCESS   read-only
        STATUS   current
        DESCRIPTION
           "The Link State ID is an LS Type Specific field
           containing either a Router ID or an IP Address;
           it identifies the piece of the  routing  domain
           that is being described by the advertisement."
       REFERENCE
          "OSPF Version 2, Section 12.1.4 Link State ID"
      ::= { ospfLsdbEntry 3 }

    ospfLsdbRouterId OBJECT-TYPE
        SYNTAX   RouterID
        MAX-ACCESS   read-only
        STATUS   current
        DESCRIPTION
           "The 32 bit number that uniquely identifies the
           originating router in the Autonomous System."
       REFERENCE
          "OSPF Version 2, Appendix C.1 Global parameters"
      ::= { ospfLsdbEntry 4 }

--  Note that the OSPF Sequence Number is a 32 bit signed
--  integer.  It starts with the value '80000001'h,
--  or -'7FFFFFFF'h, and increments until '7FFFFFFF'h
--  Thus, a typical sequence number will be very negative.

    ospfLsdbSequence OBJECT-TYPE
        SYNTAX   Integer32
        MAX-ACCESS   read-only
        STATUS   current
        DESCRIPTION
           "The sequence number field is a  signed  32-bit
           integer.   It  is used to detect old and dupli-
           cate link state advertisements.  The  space  of
           sequence  numbers  is  linearly  ordered.   The
           larger the sequence number the more recent  the
           advertisement."
       REFERENCE
          "OSPF Version  2,  Section  12.1.6  LS  sequence
          number"
      ::= { ospfLsdbEntry 5 }


    ospfLsdbAge OBJECT-TYPE
        SYNTAX   Integer32    -- Should be 0..MaxAge
        MAX-ACCESS   read-only
        STATUS   current
        DESCRIPTION
           "This field is the age of the link state adver-
           tisement in seconds."
       REFERENCE
          "OSPF Version 2, Section 12.1.1 LS age"
      ::= { ospfLsdbEntry 6 }

    ospfLsdbChecksum OBJECT-TYPE
        SYNTAX   Integer32
        MAX-ACCESS   read-only
        STATUS   current
        DESCRIPTION
           "This field is the  checksum  of  the  complete
           contents  of  the  advertisement, excepting the
           age field.  The age field is excepted  so  that
           an   advertisement's  age  can  be  incremented
           without updating the  checksum.   The  checksum
           used  is  the same that is used for ISO connec-
           tionless datagrams; it is commonly referred  to
           as the Fletcher checksum."
       REFERENCE
          "OSPF Version 2, Section 12.1.7 LS checksum"
      ::= { ospfLsdbEntry 7 }


    ospfLsdbAdvertisement OBJECT-TYPE
        SYNTAX   OCTET STRING (SIZE (1..65535))
        MAX-ACCESS   read-only
        STATUS   current
        DESCRIPTION
           "The entire Link State Advertisement, including
           its header."
       REFERENCE
          "OSPF Version 2, Section 12  Link  State  Adver-
          tisements"
      ::= { ospfLsdbEntry 8 }


--  Address Range Table

--      The Address Range Table acts as an adjunct to the Area
--      Table; It describes those Address Range Summaries that
--      are configured to be propagated from an Area to reduce
--      the amount of information about it which is known beyond
--      its borders.

    ospfAreaRangeTable OBJECT-TYPE
        SYNTAX   SEQUENCE OF OspfAreaRangeEntry
        MAX-ACCESS   not-accessible
        STATUS   obsolete
        DESCRIPTION
           "A range if IP addresses  specified  by  an  IP
           address/IP  network  mask  pair.   For example,
           class B address range of X.X.X.X with a network
           mask  of  255.255.0.0 includes all IP addresses
           from X.X.0.0 to X.X.255.255"
       REFERENCE
          "OSPF Version 2, Appendix C.2  Area parameters"
      ::= { ospf 5 }

    ospfAreaRangeEntry OBJECT-TYPE
        SYNTAX   OspfAreaRangeEntry
        MAX-ACCESS   not-accessible
        STATUS   obsolete
        DESCRIPTION
           "A range if IP addresses  specified  by  an  IP
           address/IP  network  mask  pair.   For example,
           class B address range of X.X.X.X with a network
           mask  of  255.255.0.0 includes all IP addresses
           from X.X.0.0 to X.X.255.255"
       REFERENCE
          "OSPF Version 2, Appendix C.2  Area parameters"
      INDEX { ospfAreaRangeAreaId, ospfAreaRangeNet }
      ::= { ospfAreaRangeTable 1 }

OspfAreaRangeEntry ::=
    SEQUENCE {
        ospfAreaRangeAreaId
            AreaID,
        ospfAreaRangeNet
            IpAddress,
        ospfAreaRangeMask
            IpAddress,
        ospfAreaRangeStatus
            RowStatus,
        ospfAreaRangeEffect
            INTEGER
              }

    ospfAreaRangeAreaId OBJECT-TYPE
        SYNTAX   AreaID
        MAX-ACCESS   read-only
        STATUS   obsolete
        DESCRIPTION
           "The Area the Address  Range  is  to  be  found
           within."
       REFERENCE
          "OSPF Version 2, Appendix C.2 Area parameters"
      ::= { ospfAreaRangeEntry 1 }


    ospfAreaRangeNet OBJECT-TYPE
        SYNTAX   IpAddress
        MAX-ACCESS   read-only
        STATUS   obsolete
        DESCRIPTION
           "The IP Address of the Net or Subnet  indicated
           by the range."
       REFERENCE
          "OSPF Version 2, Appendix C.2 Area parameters"
      ::= { ospfAreaRangeEntry 2 }


    ospfAreaRangeMask OBJECT-TYPE
        SYNTAX   IpAddress
        MAX-ACCESS   read-create
        STATUS   obsolete
        DESCRIPTION
           "The Subnet Mask that pertains to  the  Net  or
           Subnet."
       REFERENCE
          "OSPF Version 2, Appendix C.2 Area parameters"
      ::= { ospfAreaRangeEntry 3 }

    ospfAreaRangeStatus OBJECT-TYPE
        SYNTAX   RowStatus
        MAX-ACCESS   read-create
        STATUS   obsolete
        DESCRIPTION
           "This variable displays the status of  the  en-
           try.  Setting it to 'invalid' has the effect of
           rendering it inoperative.  The internal  effect
           (row removal) is implementation dependent."
       ::= { ospfAreaRangeEntry 4 }


    ospfAreaRangeEffect OBJECT-TYPE
        SYNTAX   INTEGER    {
                    advertiseMatching (1),
                    doNotAdvertiseMatching (2)
                  }
        MAX-ACCESS   read-create
        STATUS   obsolete
        DESCRIPTION
           "Subnets subsumed by ranges either trigger  the
           advertisement  of the indicated summary (adver-
           tiseMatching), or result in  the  subnet's  not
           being advertised at all outside the area."
       DEFVAL   { advertiseMatching }
       ::= { ospfAreaRangeEntry 5 }



--  OSPF Host Table

--      The Host/Metric Table indicates what hosts are directly
--      attached to the Router, and what metrics and types of
--      service should be advertised for them.

    ospfHostTable OBJECT-TYPE
        SYNTAX   SEQUENCE OF OspfHostEntry
        MAX-ACCESS   not-accessible
        STATUS   current
        DESCRIPTION
           "The list of Hosts, and their metrics, that the
           router will advertise as host routes."
       REFERENCE
          "OSPF Version 2, Appendix C.6  Host route param-
          eters"
      ::= { ospf 6 }


    ospfHostEntry OBJECT-TYPE
        SYNTAX   OspfHostEntry
        MAX-ACCESS   not-accessible
        STATUS   current
        DESCRIPTION
           "A metric to be advertised, for a given type of
           service, when a given host is reachable."
       INDEX { ospfHostIpAddress, ospfHostTOS }
       ::= { ospfHostTable 1 }

OspfHostEntry ::=
    SEQUENCE {
        ospfHostIpAddress
            IpAddress,
        ospfHostTOS
            TOSType,
        ospfHostMetric
            Metric,
        ospfHostStatus
            RowStatus,
        ospfHostAreaID
            AreaID
              }

    ospfHostIpAddress OBJECT-TYPE
        SYNTAX   IpAddress
        MAX-ACCESS   read-only
        STATUS   current
        DESCRIPTION
           "The IP Address of the Host."
       REFERENCE
          "OSPF Version 2, Appendix C.6 Host route parame-
          ters"
      ::= { ospfHostEntry 1 }


    ospfHostTOS OBJECT-TYPE
        SYNTAX   TOSType
        MAX-ACCESS   read-only
        STATUS   current
        DESCRIPTION
           "The Type of Service of the route being config-
           ured."
       REFERENCE
          "OSPF Version 2, Appendix C.6 Host route parame-
          ters"
      ::= { ospfHostEntry 2 }


    ospfHostMetric OBJECT-TYPE
        SYNTAX   Metric
        MAX-ACCESS   read-create
        STATUS   current
        DESCRIPTION
           "The Metric to be advertised."
       REFERENCE
          "OSPF Version 2, Appendix C.6 Host route parame-
          ters"
      ::= { ospfHostEntry 3 }

    ospfHostStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
       ::= { ospfHostEntry 4 }


    ospfHostAreaID OBJECT-TYPE
        SYNTAX   AreaID
        MAX-ACCESS   read-only
        STATUS   current
        DESCRIPTION
           "The Area the Host Entry is to be found within.
           By  default, the area that a subsuming OSPF in-
           terface is in, or 0.0.0.0"
       REFERENCE
          "OSPF Version 2, Appendix C.2 Area parameters"
      ::= { ospfHostEntry 5 }


--  OSPF Interface Table

--      The OSPF Interface Table augments the ipAddrTable
--             with OSPF specific information.

    ospfIfTable OBJECT-TYPE
        SYNTAX   SEQUENCE OF OspfIfEntry
        MAX-ACCESS   not-accessible
        STATUS   current
        DESCRIPTION
           "The OSPF Interface Table describes the  inter-
           faces from the viewpoint of OSPF."
       REFERENCE
          "OSPF Version 2, Appendix C.3  Router  interface
          parameters"
      ::= { ospf 7 }


    ospfIfEntry OBJECT-TYPE
        SYNTAX   OspfIfEntry
        MAX-ACCESS   not-accessible
        STATUS   current
        DESCRIPTION
           "The OSPF Interface Entry describes one  inter-
           face from the viewpoint of OSPF."
       INDEX { ospfIfIpAddress, ospfAddressLessIf }
       ::= { ospfIfTable 1 }

OspfIfEntry ::=
    SEQUENCE {
        ospfIfIpAddress
            IpAddress,
        ospfAddressLessIf
            Integer32,
        ospfIfAreaId
            AreaID,
        ospfIfType
            INTEGER,
        ospfIfAdminStat
            Status,
        ospfIfRtrPriority
            DesignatedRouterPriority,
        ospfIfTransitDelay
            UpToMaxAge,
        ospfIfRetransInterval
            UpToMaxAge,
        ospfIfHelloInterval
            HelloRange,
        ospfIfRtrDeadInterval
            PositiveInteger,
        ospfIfPollInterval
            PositiveInteger,
        ospfIfState
            INTEGER,
        ospfIfDesignatedRouter
            IpAddress,
        ospfIfBackupDesignatedRouter
            IpAddress,
        ospfIfEvents
            Counter32,
        ospfIfAuthType
            INTEGER,
        ospfIfAuthKey
            OCTET STRING,
        ospfIfStatus
            RowStatus,
        ospfIfMulticastForwarding
            INTEGER,
        ospfIfDemand
            TruthValue
              }

    ospfIfIpAddress OBJECT-TYPE
        SYNTAX   IpAddress
        MAX-ACCESS   read-only
        STATUS   current
        DESCRIPTION
           "The IP address of this OSPF interface."
       ::= { ospfIfEntry 1 }

    ospfAddressLessIf OBJECT-TYPE
        SYNTAX   Integer32
        MAX-ACCESS   read-only
        STATUS   current
        DESCRIPTION
           "For the purpose of easing  the  instancing  of
           addressed   and  addressless  interfaces;  This
           variable takes the value 0 on  interfaces  with
           IP  Addresses,  and  the corresponding value of
           ifIndex for interfaces having no IP Address."
       ::= { ospfIfEntry 2 }

    ospfIfAreaId OBJECT-TYPE
        SYNTAX   AreaID
        MAX-ACCESS   read-create
        STATUS   current
        DESCRIPTION
           "A 32-bit integer uniquely identifying the area
           to  which  the  interface  connects.   Area  ID
           0.0.0.0 is used for the OSPF backbone."
       DEFVAL   { '00000000'H }    -- 0.0.0.0
       --CONFIGURABLE
       ::= { ospfIfEntry 3 }

    ospfIfType OBJECT-TYPE
        SYNTAX   INTEGER    {
                    broadcast (1),
                    nbma (2),
                    pointToPoint (3),
                    pointToMultipoint (5)
                  }
        MAX-ACCESS   read-create
        STATUS   current
        DESCRIPTION
           "The OSPF interface type.

           By way of a default, this field may be intuited
           from the corresponding value of ifType.  Broad-
           cast LANs, such as  Ethernet  and  IEEE  802.5,
           take  the  value  'broadcast', X.25 and similar
           technologies take the value 'nbma',  and  links
           that  are  definitively point to point take the
           value 'pointToPoint'."
       --CONFIGURABLE
       ::= { ospfIfEntry 4 }


    ospfIfAdminStat OBJECT-TYPE
        SYNTAX   Status
        MAX-ACCESS   read-create
        STATUS   current
        DESCRIPTION
           "The OSPF  interface's  administrative  status.
           The  value formed on the interface, and the in-
           terface will be advertised as an internal route
           to  some  area.   The  value 'disabled' denotes
           that the interface is external to OSPF."
       DEFVAL { enabled }
       --CONFIGURABLE
       ::= { ospfIfEntry 5 }

    ospfIfRtrPriority OBJECT-TYPE
        SYNTAX   DesignatedRouterPriority
        MAX-ACCESS   read-create
        STATUS   current
        DESCRIPTION
           "The  priority  of  this  interface.   Used  in
           multi-access  networks,  this  field is used in
           the designated router election algorithm.   The
           value 0 signifies that the router is not eligi-
           ble to become the  designated  router  on  this
           particular  network.   In the event of a tie in
           this value, routers will use their Router ID as
           a tie breaker."
       DEFVAL { 1 }
       --CONFIGURABLE
       ::= { ospfIfEntry 6 }


    ospfIfTransitDelay OBJECT-TYPE
        SYNTAX   UpToMaxAge
        MAX-ACCESS   read-create
        STATUS   current
        DESCRIPTION
           "The estimated number of seconds  it  takes  to
           transmit  a  link state update packet over this
           interface."
       DEFVAL { 1 }
       --CONFIGURABLE
       ::= { ospfIfEntry 7 }


    ospfIfRetransInterval OBJECT-TYPE
        SYNTAX   UpToMaxAge
        MAX-ACCESS   read-create
        STATUS   current
        DESCRIPTION
           "The number of seconds between  link-state  ad-
           vertisement  retransmissions,  for  adjacencies
           belonging to this  interface.   This  value  is
           also used when retransmitting database descrip-
           tion and link-state request packets."
       DEFVAL { 5 }
       --CONFIGURABLE
       ::= { ospfIfEntry 8 }


    ospfIfHelloInterval OBJECT-TYPE
        SYNTAX   HelloRange
        MAX-ACCESS   read-create
        STATUS   current
        DESCRIPTION
           "The length of time, in  seconds,  between  the
           Hello  packets that the router sends on the in-
           terface.  This value must be the same  for  all
           routers attached to a common network."
       DEFVAL { 10 }
       --CONFIGURABLE
       ::= { ospfIfEntry 9 }


    ospfIfRtrDeadInterval OBJECT-TYPE
        SYNTAX   PositiveInteger
        MAX-ACCESS   read-create
        STATUS   current
        DESCRIPTION
           "The number of seconds that  a  router's  Hello
           packets  have  not been seen before it's neigh-
           bors declare the router down.  This  should  be
           some  multiple  of  the  Hello  interval.  This
           value must be the same for all routers attached
           to a common network."
       DEFVAL { 40 }
       --CONFIGURABLE
       ::= { ospfIfEntry 10 }


    ospfIfPollInterval OBJECT-TYPE
        SYNTAX   PositiveInteger
        MAX-ACCESS   read-create
        STATUS   current
        DESCRIPTION
           "The larger time interval, in seconds,  between
           the  Hello  packets  sent  to  an inactive non-
           broadcast multi- access neighbor."
       DEFVAL { 120 }
       ::= { ospfIfEntry 11 }


    ospfIfState OBJECT-TYPE
        SYNTAX   INTEGER    {
                    down (1),
                    loopback (2),
                    waiting (3),
                    pointToPoint (4),
                    designatedRouter (5),
                    backupDesignatedRouter (6),
                    otherDesignatedRouter (7)
                  }
        MAX-ACCESS   read-only
        STATUS   current
        DESCRIPTION
           "The OSPF Interface State."
       DEFVAL { down }
       ::= { ospfIfEntry 12 }


    ospfIfDesignatedRouter OBJECT-TYPE
        SYNTAX   IpAddress
        MAX-ACCESS   read-only
        STATUS   current
        DESCRIPTION
           "The IP Address of the Designated Router."
       DEFVAL   { '00000000'H }    -- 0.0.0.0
       ::= { ospfIfEntry 13 }


    ospfIfBackupDesignatedRouter OBJECT-TYPE
        SYNTAX   IpAddress
        MAX-ACCESS   read-only
        STATUS   current
        DESCRIPTION
           "The  IP  Address  of  the  Backup   Designated
           Router."
       DEFVAL   { '00000000'H }    -- 0.0.0.0
       ::= { ospfIfEntry 14 }

    ospfIfEvents OBJECT-TYPE
        SYNTAX   Counter32
        MAX-ACCESS   read-only
        STATUS   current
        DESCRIPTION
           "The number of times this  OSPF  interface  has
           changed its state, or an error has occurred."
       ::= { ospfIfEntry 15 }


    ospfIfAuthKey OBJECT-TYPE
        SYNTAX   OCTET STRING (SIZE (0..256))
        MAX-ACCESS   read-create
        STATUS   current
        DESCRIPTION
           "The Authentication Key.  If the Area's Author-
           ization  Type  is  simplePassword,  and the key
           length is shorter than 8 octets, the agent will
           left adjust and zero fill to 8 octets.

           Note that unauthenticated  interfaces  need  no
           authentication key, and simple password authen-
           tication cannot use a key of more  than  8  oc-
           tets.  Larger keys are useful only with authen-
           tication mechanisms not specified in this docu-
           ment.

           When read, ospfIfAuthKey always returns an  Oc-
           tet String of length zero."
       REFERENCE
          "OSPF Version 2, Section 9  The  Interface  Data
          Structure"
      DEFVAL   { '0000000000000000'H }    -- 0.0.0.0.0.0.0.0
       --CONFIGURABLE
      ::= { ospfIfEntry 16 }

    ospfIfStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
       --CONFIGURABLE
       ::= { ospfIfEntry 17 }


    ospfIfMulticastForwarding OBJECT-TYPE
        SYNTAX   INTEGER    {
                            blocked (1),        -- no multicast forwarding
                            multicast (2),        -- using multicast address
                            unicast (3)        -- to each OSPF neighbor
                  }
        MAX-ACCESS   read-create
        STATUS   current
        DESCRIPTION
           "The way multicasts should  forwarded  on  this
           interface;  not  forwarded,  forwarded  as data
           link multicasts, or forwarded as data link uni-
           casts.   Data link multicasting is not meaning-
           ful on point to point and NBMA interfaces,  and
           setting ospfMulticastForwarding to 0 effective-
           ly disables all multicast forwarding."
       DEFVAL { blocked }
       ::= { ospfIfEntry 18 }


    ospfIfDemand OBJECT-TYPE
        SYNTAX   TruthValue
        MAX-ACCESS   read-create
        STATUS   current
        DESCRIPTION
           "Indicates whether Demand OSPF procedures (hel-
           lo supression to FULL neighbors and setting the
           DoNotAge flag on proogated LSAs) should be per-
           formed on this interface."
       DEFVAL { false }
       ::= { ospfIfEntry 19 }


    ospfIfAuthType OBJECT-TYPE
        SYNTAX   INTEGER (0..255)
                    -- none (0),
                    -- simplePassword (1)
                    -- md5 (2)
                    -- reserved for specification by IANA (> 2)
        MAX-ACCESS   read-create
        STATUS   current
        DESCRIPTION
           "The authentication type specified for  an  in-
           terface.   Additional  authentication types may
           be assigned locally."
       REFERENCE
          "OSPF Version 2, Appendix E Authentication"
      DEFVAL { 0 }        -- no authentication, by default
       --CONFIGURABLE
      ::= { ospfIfEntry 20 }


--  OSPF Interface Metric Table

--      The Metric Table describes the metrics to be advertised
--      for a specified interface at the various types of service.
--      As such, this table is an adjunct of the OSPF Interface
--      Table.

-- Types of service, as defined by RFC 791, have the ability
-- to request low delay, high bandwidth, or reliable linkage.

-- For the purposes of this specification, the measure of
-- bandwidth

--      Metric = 10^8 / ifSpeed

-- is the default value.  For multiple link interfaces, note
-- that ifSpeed is the sum of the individual link speeds.
-- This yields a number having the following typical values:

--      Network Type/bit rate   Metric

--      >= 100 MBPS                 1
--      Ethernet/802.3             10
--      E1                         48
--      T1 (ESF)                   65
--       64 KBPS                 1562
--       56 KBPS                 1785
--       19.2 KBPS               5208
--        9.6 KBPS              10416

-- Routes that are not specified use the default (TOS 0) metric

    ospfIfMetricTable OBJECT-TYPE
        SYNTAX   SEQUENCE OF OspfIfMetricEntry
        MAX-ACCESS   not-accessible
        STATUS   current
        DESCRIPTION
           "The TOS metrics for  a  non-virtual  interface
           identified by the interface index."
       REFERENCE
          "OSPF Version 2, Appendix C.3  Router  interface
          parameters"
      ::= { ospf 8 }

    ospfIfMetricEntry OBJECT-TYPE
        SYNTAX   OspfIfMetricEntry
        MAX-ACCESS   not-accessible
        STATUS   current
        DESCRIPTION
           "A particular TOS metric for a non-virtual  in-
           terface identified by the interface index."
       REFERENCE
          "OSPF Version 2, Appendix C.3  Router  interface
          parameters"
      INDEX { ospfIfMetricIpAddress,
  ospfIfMetricAddressLessIf,
  ospfIfMetricTOS }
      ::= { ospfIfMetricTable 1 }

OspfIfMetricEntry ::=
    SEQUENCE {
        ospfIfMetricIpAddress
            IpAddress,
        ospfIfMetricAddressLessIf
            Integer32,
        ospfIfMetricTOS
            TOSType,
        ospfIfMetricValue
            Metric,
        ospfIfMetricStatus
            RowStatus
              }

    ospfIfMetricIpAddress OBJECT-TYPE
        SYNTAX   IpAddress
        MAX-ACCESS   read-only
        STATUS   current
        DESCRIPTION
           "The IP address of this OSPF interface.  On row
           creation,  this  can  be  derived  from the in-
           stance."
       ::= { ospfIfMetricEntry 1 }

    ospfIfMetricAddressLessIf OBJECT-TYPE
        SYNTAX   Integer32
        MAX-ACCESS   read-only
        STATUS   current
        DESCRIPTION
           "For the purpose of easing  the  instancing  of
           addressed   and  addressless  interfaces;  This
           variable takes the value 0 on  interfaces  with
           IP  Addresses, and the value of ifIndex for in-
           terfaces having no IP Address.   On  row  crea-
           tion, this can be derived from the instance."
       ::= { ospfIfMetricEntry 2 }


    ospfIfMetricTOS OBJECT-TYPE
        SYNTAX   TOSType
        MAX-ACCESS   read-only
        STATUS   current
        DESCRIPTION
           "The type of service metric  being  referenced.
           On  row  creation, this can be derived from the
           instance."
       ::= { ospfIfMetricEntry 3 }


    ospfIfMetricValue OBJECT-TYPE
        SYNTAX   Metric
        MAX-ACCESS   read-create
        STATUS   current
        DESCRIPTION
           "The metric of using this type  of  service  on
           this interface.  The default value of the TOS 0
           Metric is 10^8 / ifSpeed."
       --CONFIGURABLE
       ::= { ospfIfMetricEntry 4 }

    ospfIfMetricStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
       ::= { ospfIfMetricEntry 5 }


--  OSPF Virtual Interface Table

--      The Virtual Interface Table describes the virtual
--      links that the OSPF Process is configured to
--      carry on.

    ospfVirtIfTable OBJECT-TYPE
        SYNTAX   SEQUENCE OF OspfVirtIfEntry
        MAX-ACCESS   not-accessible
        STATUS   current
        DESCRIPTION
           "Information about this router's virtual inter-
           faces."
       REFERENCE
          "OSPF Version  2,  Appendix  C.4   Virtual  link
          parameters"
      ::= { ospf 9 }


    ospfVirtIfEntry OBJECT-TYPE
        SYNTAX   OspfVirtIfEntry
        MAX-ACCESS   not-accessible
        STATUS   current
        DESCRIPTION
           "Information about a single Virtual Interface."
       INDEX { ospfVirtIfAreaId, ospfVirtIfNeighbor }
       ::= { ospfVirtIfTable 1 }

OspfVirtIfEntry ::=
    SEQUENCE {
        ospfVirtIfAreaId
            AreaID,
        ospfVirtIfNeighbor
            RouterID,
        ospfVirtIfTransitDelay
            UpToMaxAge,
        ospfVirtIfRetransInterval
            UpToMaxAge,
        ospfVirtIfHelloInterval
            HelloRange,
        ospfVirtIfRtrDeadInterval
            PositiveInteger,
        ospfVirtIfState
            INTEGER,
        ospfVirtIfEvents
            Counter32,
        ospfVirtIfAuthType
            INTEGER,
        ospfVirtIfAuthKey
            OCTET STRING,
        ospfVirtIfStatus
            RowStatus
              }

    ospfVirtIfAreaId OBJECT-TYPE
        SYNTAX   AreaID
        MAX-ACCESS   read-only
        STATUS   current
        DESCRIPTION
           "The  Transit  Area  that  the   Virtual   Link
           traverses.  By definition, this is not 0.0.0.0"
       ::= { ospfVirtIfEntry 1 }


    ospfVirtIfNeighbor OBJECT-TYPE
        SYNTAX   RouterID
        MAX-ACCESS   read-only
        STATUS   current
        DESCRIPTION
           "The Router ID of the Virtual Neighbor."
       ::= { ospfVirtIfEntry 2 }


    ospfVirtIfTransitDelay OBJECT-TYPE
        SYNTAX   UpToMaxAge
        MAX-ACCESS   read-create
        STATUS   current
        DESCRIPTION
           "The estimated number of seconds  it  takes  to
           transmit  a link- state update packet over this
           interface."
       DEFVAL { 1 }
       ::= { ospfVirtIfEntry 3 }

    ospfVirtIfRetransInterval OBJECT-TYPE
        SYNTAX   UpToMaxAge
        MAX-ACCESS   read-create
        STATUS   current
        DESCRIPTION
           "The number of seconds between  link-state  ad-
           vertisement  retransmissions,  for  adjacencies
           belonging to this  interface.   This  value  is
           also used when retransmitting database descrip-
           tion  and  link-state  request  packets.   This
           value  should  be well over the expected round-
           trip time."
       DEFVAL { 5 }
       ::= { ospfVirtIfEntry 4 }


    ospfVirtIfHelloInterval OBJECT-TYPE
        SYNTAX   HelloRange
        MAX-ACCESS   read-create
        STATUS   current
        DESCRIPTION
           "The length of time, in  seconds,  between  the
           Hello  packets that the router sends on the in-
           terface.  This value must be the same  for  the
           virtual neighbor."
       DEFVAL { 10 }
       ::= { ospfVirtIfEntry 5 }


    ospfVirtIfRtrDeadInterval OBJECT-TYPE
        SYNTAX   PositiveInteger
        MAX-ACCESS   read-create
        STATUS   current
        DESCRIPTION
           "The number of seconds that  a  router's  Hello
           packets  have  not been seen before it's neigh-
           bors declare the router down.  This  should  be
           some  multiple  of  the  Hello  interval.  This
           value must be the same for the  virtual  neigh-
           bor."
       DEFVAL { 60 }
       ::= { ospfVirtIfEntry 6 }


    ospfVirtIfState OBJECT-TYPE
        SYNTAX   INTEGER    {
                    down (1),            -- these use the same encoding
                    pointToPoint (4)     -- as the ospfIfTable
                  }
        MAX-ACCESS   read-only
        STATUS   current
        DESCRIPTION
           "OSPF virtual interface states."
       DEFVAL   { down }
       ::= { ospfVirtIfEntry 7 }


    ospfVirtIfEvents OBJECT-TYPE
        SYNTAX   Counter32
        MAX-ACCESS   read-only
        STATUS   current
        DESCRIPTION
           "The number of state changes or error events on
           this Virtual Link"
       ::= { ospfVirtIfEntry 8 }


    ospfVirtIfAuthKey OBJECT-TYPE
        SYNTAX   OCTET STRING (SIZE(0..256))
        MAX-ACCESS   read-create
        STATUS   current
        DESCRIPTION
           "If Authentication Type is simplePassword,  the
           device  will left adjust and zero fill to 8 oc-
           tets.

           Note that unauthenticated  interfaces  need  no
           authentication key, and simple password authen-
           tication cannot use a key of more  than  8  oc-
           tets.  Larger keys are useful only with authen-
           tication mechanisms not specified in this docu-
           ment.

           When  read,  ospfVifAuthKey  always  returns  a
           string of length zero."
       REFERENCE
          "OSPF Version 2, Section 9  The  Interface  Data
          Structure"
      DEFVAL   { '0000000000000000'H }    -- 0.0.0.0.0.0.0.0
      ::= { ospfVirtIfEntry 9 }


    ospfVirtIfStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
       ::= { ospfVirtIfEntry 10 }


    ospfVirtIfAuthType OBJECT-TYPE
        SYNTAX   INTEGER (0..255)
                    -- none (0),
                    -- simplePassword (1)
                    -- md5 (2)
                    -- reserved for specification by IANA (> 2)
        MAX-ACCESS   read-create
        STATUS   current
        DESCRIPTION
           "The authentication type specified for a virtu-
           al  interface.  Additional authentication types
           may be assigned locally."
       REFERENCE
          "OSPF Version 2, Appendix E Authentication"
      DEFVAL { 0 }        -- no authentication, by default
      ::= { ospfVirtIfEntry 11 }


--  OSPF Neighbor Table

--      The OSPF Neighbor Table describes all neighbors in
--      the locality of the subject router.

    ospfNbrTable OBJECT-TYPE
        SYNTAX   SEQUENCE OF OspfNbrEntry
        MAX-ACCESS   not-accessible
        STATUS   current
        DESCRIPTION
           "A table of non-virtual neighbor information."
       REFERENCE
          "OSPF Version 2, Section 10  The  Neighbor  Data
          Structure"
      ::= { ospf 10 }


    ospfNbrEntry OBJECT-TYPE
        SYNTAX   OspfNbrEntry
        MAX-ACCESS   not-accessible
        STATUS   current
        DESCRIPTION
           "The information regarding a single neighbor."
       REFERENCE
          "OSPF Version 2, Section 10  The  Neighbor  Data
          Structure"
      INDEX { ospfNbrIpAddr, ospfNbrAddressLessIndex }
      ::= { ospfNbrTable 1 }

OspfNbrEntry ::=
    SEQUENCE {
        ospfNbrIpAddr
            IpAddress,
        ospfNbrAddressLessIndex
            InterfaceIndex,
        ospfNbrRtrId
            RouterID,
        ospfNbrOptions
            Integer32,
        ospfNbrPriority
            DesignatedRouterPriority,
        ospfNbrState
            INTEGER,
        ospfNbrEvents
            Counter32,
        ospfNbrLsRetransQLen
            Gauge32,
        ospfNbmaNbrStatus
            RowStatus,
        ospfNbmaNbrPermanence
            INTEGER,
        ospfNbrHelloSuppressed
            TruthValue
              }

    ospfNbrIpAddr OBJECT-TYPE
        SYNTAX   IpAddress
        MAX-ACCESS   read-only
        STATUS   current
        DESCRIPTION
           "The IP address this neighbor is using  in  its
           IP  Source  Address.  Note that, on addressless
           links, this will not be 0.0.0.0,  but  the  ad-
           dress of another of the neighbor's interfaces."
       ::= { ospfNbrEntry 1 }


    ospfNbrAddressLessIndex OBJECT-TYPE
        SYNTAX   InterfaceIndex
        MAX-ACCESS   read-only
        STATUS   current
        DESCRIPTION
           "On an interface having an  IP  Address,  zero.
           On  addressless  interfaces,  the corresponding
           value of ifIndex in the Internet Standard  MIB.
           On  row  creation, this can be derived from the
           instance."
       ::= { ospfNbrEntry 2 }


    ospfNbrRtrId OBJECT-TYPE
        SYNTAX   RouterID
        MAX-ACCESS   read-only
        STATUS   current
        DESCRIPTION
           "A 32-bit integer (represented as a type  IpAd-
           dress)  uniquely  identifying  the  neighboring
           router in the Autonomous System."
       DEFVAL   { '00000000'H }    -- 0.0.0.0
       ::= { ospfNbrEntry 3 }


    ospfNbrOptions OBJECT-TYPE
        SYNTAX   Integer32
        MAX-ACCESS   read-only
        STATUS   current
        DESCRIPTION
           "A Bit Mask corresponding to the neighbor's op-
           tions field.

           Bit 0, if set, indicates that the  system  will
           operate  on  Type of Service metrics other than
           TOS 0.  If zero, the neighbor will  ignore  all
           metrics except the TOS 0 metric.

           Bit 1, if set, indicates  that  the  associated
           area  accepts and operates on external informa-
           tion; if zero, it is a stub area.

           Bit 2, if set, indicates that the system is ca-
           pable  of routing IP Multicast datagrams; i.e.,
           that it implements the Multicast Extensions  to
           OSPF.

           Bit 3, if set, indicates  that  the  associated
           area  is  an  NSSA.  These areas are capable of
           carrying type 7 external advertisements,  which
           are  translated into type 5 external advertise-
           ments at NSSA borders."
       REFERENCE
          "OSPF Version 2, Section 12.1.2 Options"
      DEFVAL { 0 }
      ::= { ospfNbrEntry 4 }


    ospfNbrPriority OBJECT-TYPE
        SYNTAX   DesignatedRouterPriority
        MAX-ACCESS   read-create
        STATUS   current
        DESCRIPTION
           "The priority of this neighbor in the designat-
           ed router election algorithm.  The value 0 sig-
           nifies that the neighbor is not eligible to be-
           come  the  designated router on this particular
           network."
       DEFVAL { 1 }
       ::= { ospfNbrEntry 5 }


    ospfNbrState OBJECT-TYPE
        SYNTAX   INTEGER    {
                    down (1),
                    attempt (2),
                    init (3),
                    twoWay (4),
                    exchangeStart (5),
                    exchange (6),
                    loading (7),
                    full (8)
                  }
        MAX-ACCESS   read-only
        STATUS   current
        DESCRIPTION
           "The State of the relationship with this Neigh-
           bor."
       REFERENCE
          "OSPF Version 2, Section 10.1 Neighbor States"
      DEFVAL   { down }
      ::= { ospfNbrEntry 6 }


    ospfNbrEvents OBJECT-TYPE
        SYNTAX   Counter32
        MAX-ACCESS   read-only
        STATUS   current
        DESCRIPTION
           "The number of times this neighbor relationship
           has changed state, or an error has occurred."
       ::= { ospfNbrEntry 7 }


    ospfNbrLsRetransQLen OBJECT-TYPE
        SYNTAX   Gauge32
        MAX-ACCESS   read-only
        STATUS   current
        DESCRIPTION
           "The  current  length  of  the   retransmission
           queue."
       ::= { ospfNbrEntry 8 }


    ospfNbmaNbrStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
       ::= { ospfNbrEntry 9 }


    ospfNbmaNbrPermanence OBJECT-TYPE
        SYNTAX   INTEGER    {
                    dynamic (1),        -- learned through protocol
                    permanent (2)       -- configured address
                  }
        MAX-ACCESS   read-only
        STATUS   current
        DESCRIPTION
           "This variable displays the status of  the  en-
           try.   'dynamic'  and  'permanent' refer to how
           the neighbor became known."
       DEFVAL { permanent }
       ::= { ospfNbrEntry 10 }


    ospfNbrHelloSuppressed OBJECT-TYPE
        SYNTAX   TruthValue
        MAX-ACCESS   read-only
        STATUS   current
        DESCRIPTION
           "Indicates whether Hellos are being  suppressed
           to the neighbor"
       ::= { ospfNbrEntry 11 }


--  OSPF Virtual Neighbor Table

--      This table describes all virtual neighbors.
--      Since Virtual Links are configured in the
--      virtual interface table, this table is read-only.

    ospfVirtNbrTable OBJECT-TYPE
        SYNTAX   SEQUENCE OF OspfVirtNbrEntry
        MAX-ACCESS   not-accessible
        STATUS   current
        DESCRIPTION
           "A table of virtual neighbor information."
       REFERENCE
          "OSPF Version 2, Section 15  Virtual Links"
      ::= { ospf 11 }


    ospfVirtNbrEntry OBJECT-TYPE
        SYNTAX   OspfVirtNbrEntry
        MAX-ACCESS   not-accessible
        STATUS   current
        DESCRIPTION
           "Virtual neighbor information."
       INDEX { ospfVirtNbrArea, ospfVirtNbrRtrId }
       ::= { ospfVirtNbrTable 1 }

OspfVirtNbrEntry ::=
    SEQUENCE {
        ospfVirtNbrArea
            AreaID,
        ospfVirtNbrRtrId
            RouterID,
        ospfVirtNbrIpAddr
            IpAddress,
        ospfVirtNbrOptions
            Integer32,
        ospfVirtNbrState
            INTEGER,
        ospfVirtNbrEvents
            Counter32,
        ospfVirtNbrLsRetransQLen
            Gauge32,
        ospfVirtNbrHelloSuppressed
                TruthValue
              }

    ospfVirtNbrArea OBJECT-TYPE
        SYNTAX   AreaID
        MAX-ACCESS   read-only
        STATUS   current
        DESCRIPTION
           "The Transit Area Identifier."
       ::= { ospfVirtNbrEntry 1 }


    ospfVirtNbrRtrId OBJECT-TYPE
        SYNTAX   RouterID
        MAX-ACCESS   read-only
        STATUS   current
        DESCRIPTION
           "A  32-bit  integer  uniquely  identifying  the
           neighboring router in the Autonomous System."
       ::= { ospfVirtNbrEntry 2 }


    ospfVirtNbrIpAddr OBJECT-TYPE
        SYNTAX   IpAddress
        MAX-ACCESS   read-only
        STATUS   current
        DESCRIPTION
           "The IP address this Virtual  Neighbor  is  us-
           ing."
       ::= { ospfVirtNbrEntry 3 }


    ospfVirtNbrOptions OBJECT-TYPE
        SYNTAX   Integer32
        MAX-ACCESS   read-only
        STATUS   current
        DESCRIPTION
           "A Bit Mask corresponding to the neighbor's op-
           tions field.

           Bit 1, if set, indicates that the  system  will
           operate  on  Type of Service metrics other than
           TOS 0.  If zero, the neighbor will  ignore  all
           metrics except the TOS 0 metric.

           Bit 2, if set, indicates  that  the  system  is
           Network  Multicast  capable; ie, that it imple-
           ments OSPF Multicast Routing."
       ::= { ospfVirtNbrEntry 4 }

    ospfVirtNbrState OBJECT-TYPE
        SYNTAX   INTEGER    {
                    down (1),
                    attempt (2),
                    init (3),
                    twoWay (4),
                    exchangeStart (5),
                    exchange (6),
                    loading (7),
                    full (8)
                  }
        MAX-ACCESS   read-only
        STATUS   current
        DESCRIPTION
           "The state of the  Virtual  Neighbor  Relation-
           ship."
       ::= { ospfVirtNbrEntry 5 }


    ospfVirtNbrEvents OBJECT-TYPE
        SYNTAX   Counter32
        MAX-ACCESS   read-only
        STATUS   current
        DESCRIPTION
           "The number of  times  this  virtual  link  has
           changed its state, or an error has occurred."
       ::= { ospfVirtNbrEntry 6 }


    ospfVirtNbrLsRetransQLen OBJECT-TYPE
        SYNTAX   Gauge32
        MAX-ACCESS   read-only
        STATUS   current
        DESCRIPTION
           "The  current  length  of  the   retransmission
           queue."
       ::= { ospfVirtNbrEntry 7 }


    ospfVirtNbrHelloSuppressed OBJECT-TYPE
        SYNTAX   TruthValue
        MAX-ACCESS   read-only
        STATUS   current
        DESCRIPTION
           "Indicates whether Hellos are being  suppressed
           to the neighbor"
       ::= { ospfVirtNbrEntry 8 }

--  OSPF Link State Database, External

--      The Link State Database contains the Link State
--      Advertisements from throughout the areas that the
--      device is attached to.

--             This table is identical to the OSPF LSDB Table in
--      format, but contains only External Link State
--             Advertisements.  The purpose is to allow external
--      LSAs to be displayed once for the router rather
--      than once in each non-stub area.

    ospfExtLsdbTable OBJECT-TYPE
        SYNTAX   SEQUENCE OF OspfExtLsdbEntry
        MAX-ACCESS   not-accessible
        STATUS   current
        DESCRIPTION
           "The OSPF Process's Links State Database."
       REFERENCE
          "OSPF Version 2, Section 12  Link  State  Adver-
          tisements"
      ::= { ospf 12 }


    ospfExtLsdbEntry OBJECT-TYPE
        SYNTAX   OspfExtLsdbEntry
        MAX-ACCESS   not-accessible
        STATUS   current
        DESCRIPTION
           "A single Link State Advertisement."
       INDEX { ospfExtLsdbType, ospfExtLsdbLsid, ospfExtLsdbRouterId }
       ::= { ospfExtLsdbTable 1 }

OspfExtLsdbEntry ::=
    SEQUENCE {
        ospfExtLsdbType
            INTEGER,
        ospfExtLsdbLsid
            IpAddress,
        ospfExtLsdbRouterId
            RouterID,
        ospfExtLsdbSequence
            Integer32,
        ospfExtLsdbAge
            Integer32,
        ospfExtLsdbChecksum
            Integer32,
        ospfExtLsdbAdvertisement
            OCTET STRING
              }

    ospfExtLsdbType OBJECT-TYPE
        SYNTAX   INTEGER    {
                    asExternalLink (5)
                  }
        MAX-ACCESS   read-only
        STATUS   current
        DESCRIPTION
           "The type  of  the  link  state  advertisement.
           Each  link state type has a separate advertise-
           ment format."
       REFERENCE
          "OSPF Version 2, Appendix A.4.1 The  Link  State
          Advertisement header"
      ::= { ospfExtLsdbEntry 1 }


    ospfExtLsdbLsid OBJECT-TYPE
        SYNTAX   IpAddress
        MAX-ACCESS   read-only
        STATUS   current
        DESCRIPTION
           "The Link State ID is an LS Type Specific field
           containing either a Router ID or an IP Address;
           it identifies the piece of the  routing  domain
           that is being described by the advertisement."
       REFERENCE
          "OSPF Version 2, Section 12.1.4 Link State ID"
      ::= { ospfExtLsdbEntry 2 }


    ospfExtLsdbRouterId OBJECT-TYPE
        SYNTAX   RouterID
        MAX-ACCESS   read-only
        STATUS   current
        DESCRIPTION
           "The 32 bit number that uniquely identifies the
           originating router in the Autonomous System."
       REFERENCE
          "OSPF Version 2, Appendix C.1 Global parameters"
      ::= { ospfExtLsdbEntry 3 }

--  Note that the OSPF Sequence Number is a 32 bit signed
--  integer.  It starts with the value '80000001'h,
--  or -'7FFFFFFF'h, and increments until '7FFFFFFF'h
--  Thus, a typical sequence number will be very negative.

    ospfExtLsdbSequence OBJECT-TYPE
        SYNTAX   Integer32
        MAX-ACCESS   read-only
        STATUS   current
        DESCRIPTION
           "The sequence number field is a  signed  32-bit
           integer.   It  is used to detect old and dupli-
           cate link state advertisements.  The  space  of
           sequence  numbers  is  linearly  ordered.   The
           larger the sequence number the more recent  the
           advertisement."
       REFERENCE
          "OSPF Version  2,  Section  12.1.6  LS  sequence
          number"
      ::= { ospfExtLsdbEntry 4 }


    ospfExtLsdbAge OBJECT-TYPE
        SYNTAX   Integer32    -- Should be 0..MaxAge
        MAX-ACCESS   read-only
        STATUS   current
        DESCRIPTION
           "This field is the age of the link state adver-
           tisement in seconds."
       REFERENCE
          "OSPF Version 2, Section 12.1.1 LS age"
      ::= { ospfExtLsdbEntry 5 }


    ospfExtLsdbChecksum OBJECT-TYPE
        SYNTAX   Integer32
        MAX-ACCESS   read-only
        STATUS   current
        DESCRIPTION
           "This field is the  checksum  of  the  complete
           contents  of  the  advertisement, excepting the
           age field.  The age field is excepted  so  that
           an   advertisement's  age  can  be  incremented
           without updating the  checksum.   The  checksum
           used  is  the same that is used for ISO connec-
           tionless datagrams; it is commonly referred  to
           as the Fletcher checksum."
       REFERENCE
          "OSPF Version 2, Section 12.1.7 LS checksum"
      ::= { ospfExtLsdbEntry 6 }


    ospfExtLsdbAdvertisement OBJECT-TYPE
        SYNTAX   OCTET STRING (SIZE(36))
        MAX-ACCESS   read-only
        STATUS   current
        DESCRIPTION
           "The entire Link State Advertisement, including
           its header."
       REFERENCE
          "OSPF Version 2, Section 12  Link  State  Adver-
          tisements"
      ::= { ospfExtLsdbEntry 7 }


--  OSPF Use of the CIDR Route Table

ospfRouteGroup           OBJECT IDENTIFIER ::= { ospf 13 }

-- The IP Forwarding Table defines a number of objects for use by
-- the routing protocol to externalize its information.  Most of
-- the variables (ipForwardDest, ipForwardMask, ipForwardPolicy,
-- ipForwardNextHop, ipForwardIfIndex, ipForwardType,
-- ipForwardProto, ipForwardAge, and ipForwardNextHopAS) are
-- defined there.

-- Those that leave some discretion are defined here.

-- ipCidrRouteProto is, of course, ospf (13).

-- ipCidrRouteAge is the time since the route was first calculated,
-- as opposed to the time since the last SPF run.

-- ipCidrRouteInfo is an OBJECT IDENTIFIER for use by the routing
-- protocol.  The following values shall be found there depending
-- on the way the route was calculated.

ospfIntraArea      OBJECT IDENTIFIER ::= { ospfRouteGroup 1 }
ospfInterArea      OBJECT IDENTIFIER ::= { ospfRouteGroup 2 }
ospfExternalType1  OBJECT IDENTIFIER ::= { ospfRouteGroup 3 }
ospfExternalType2  OBJECT IDENTIFIER ::= { ospfRouteGroup 4 }

-- ipCidrRouteMetric1 is, by definition, the primary routing
-- metric.  Therefore, it should be the metric that route
-- selection is based on.  For intra-area and inter-area routes,
-- it is an OSPF metric.  For External Type 1 (comparable value)
-- routes, it is an OSPF metric plus the External Metric.  For
-- external Type 2 (non-comparable value) routes, it is the
-- external metric.

-- ipCidrRouteMetric2 is, by definition, a secondary routing
-- metric.  Therefore, it should be the metric that breaks a tie
-- among routes having equal metric1 values and the same
-- calculation rule.  For intra-area, inter-area routes, and
-- External Type 1 (comparable value) routes, it is unused.  For
-- external Type 2 (non-comparable value) routes, it is the metric
-- to the AS border router.

-- ipCidrRouteMetric3, ipCidrRouteMetric4, and ipCidrRouteMetric5 are
-- unused.

--
--      The OSPF Area Aggregate Table
--
--      This table replaces the OSPF Area Summary Table, being an
--      extension of that for CIDR routers.

    ospfAreaAggregateTable OBJECT-TYPE
        SYNTAX   SEQUENCE OF OspfAreaAggregateEntry
        MAX-ACCESS   not-accessible
        STATUS   current
        DESCRIPTION
           "A range of IP addresses  specified  by  an  IP
           address/IP  network  mask  pair.   For example,
           class B address range of X.X.X.X with a network
           mask  of  255.255.0.0 includes all IP addresses
           from X.X.0.0  to  X.X.255.255.   Note  that  if
           ranges  are configured such that one range sub-
           sumes  another  range  (e.g.,   10.0.0.0   mask
           255.0.0.0  and  10.1.0.0 mask 255.255.0.0), the
           most specific match is the preferred one."
       REFERENCE
          "OSPF Version 2, Appendix C.2  Area parameters"
      ::= { ospf 14 }


    ospfAreaAggregateEntry OBJECT-TYPE
        SYNTAX   OspfAreaAggregateEntry
        MAX-ACCESS   not-accessible
        STATUS   current
        DESCRIPTION
           "A range of IP addresses  specified  by  an  IP
           address/IP  network  mask  pair.   For example,
           class B address range of X.X.X.X with a network
           mask  of  255.255.0.0 includes all IP addresses
           from X.X.0.0  to  X.X.255.255.   Note  that  if
           ranges are range configured such that one range
           subsumes another  range  (e.g.,  10.0.0.0  mask
           255.0.0.0  and  10.1.0.0 mask 255.255.0.0), the
           most specific match is the preferred one."
       REFERENCE
          "OSPF Version 2, Appendix C.2  Area parameters"
      INDEX { ospfAreaAggregateAreaID, ospfAreaAggregateLsdbType,
              ospfAreaAggregateNet, ospfAreaAggregateMask }
      ::= { ospfAreaAggregateTable 1 }


OspfAreaAggregateEntry ::=
    SEQUENCE {
        ospfAreaAggregateAreaID
            AreaID,
        ospfAreaAggregateLsdbType
            INTEGER,
        ospfAreaAggregateNet
            IpAddress,
        ospfAreaAggregateMask
            IpAddress,
        ospfAreaAggregateStatus
            RowStatus,
        ospfAreaAggregateEffect
            INTEGER
              }

    ospfAreaAggregateAreaID OBJECT-TYPE
        SYNTAX   AreaID
        MAX-ACCESS   read-only
        STATUS   current
        DESCRIPTION
           "The Area the Address Aggregate is to be  found
           within."
       REFERENCE
          "OSPF Version 2, Appendix C.2 Area parameters"
      ::= { ospfAreaAggregateEntry 1 }


    ospfAreaAggregateLsdbType OBJECT-TYPE
        SYNTAX   INTEGER    {
                    summaryLink (3),
                    nssaExternalLink (7)
                  }
        MAX-ACCESS   read-only
        STATUS   current
        DESCRIPTION
           "The type of the Address Aggregate.  This field
           specifies  the  Lsdb type that this Address Ag-
           gregate applies to."
       REFERENCE
          "OSPF Version 2, Appendix A.4.1 The  Link  State
          Advertisement header"
      ::= { ospfAreaAggregateEntry 2 }


    ospfAreaAggregateNet OBJECT-TYPE
        SYNTAX   IpAddress
        MAX-ACCESS   read-only
        STATUS   current
        DESCRIPTION
           "The IP Address of the Net or Subnet  indicated
           by the range."
       REFERENCE
          "OSPF Version 2, Appendix C.2 Area parameters"
      ::= { ospfAreaAggregateEntry 3 }


    ospfAreaAggregateMask OBJECT-TYPE
        SYNTAX   IpAddress
        MAX-ACCESS   read-only
        STATUS   current
        DESCRIPTION
           "The Subnet Mask that pertains to  the  Net  or
           Subnet."
       REFERENCE
          "OSPF Version 2, Appendix C.2 Area parameters"
      ::= { ospfAreaAggregateEntry 4 }


    ospfAreaAggregateStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
       ::= { ospfAreaAggregateEntry 5 }


    ospfAreaAggregateEffect OBJECT-TYPE
        SYNTAX   INTEGER    {
                    advertiseMatching (1),
                    doNotAdvertiseMatching (2)
                  }
        MAX-ACCESS   read-create
        STATUS   current
        DESCRIPTION
           "Subnets subsumed by ranges either trigger  the
           advertisement  of  the indicated aggregate (ad-
           vertiseMatching), or result in the subnet's not
           being advertised at all outside the area."
       DEFVAL   { advertiseMatching }
       ::= { ospfAreaAggregateEntry 6 }


-- conformance information

ospfConformance OBJECT IDENTIFIER ::= { ospf 15 }

ospfGroups      OBJECT IDENTIFIER ::= { ospfConformance 1 }
ospfCompliances OBJECT IDENTIFIER ::= { ospfConformance 2 }

-- compliance statements

    ospfCompliance MODULE-COMPLIANCE
        STATUS  current
        DESCRIPTION
           "The compliance statement "
       MODULE  -- this module
       MANDATORY-GROUPS {
                    ospfBasicGroup,
                    ospfAreaGroup,
                    ospfStubAreaGroup,
                    ospfIfGroup,
                    ospfIfMetricGroup,
                    ospfVirtIfGroup,
                    ospfNbrGroup,
                    ospfVirtNbrGroup,
                    ospfAreaAggregateGroup
           }
       ::= { ospfCompliances 1 }


-- units of conformance

    ospfBasicGroup    OBJECT-GROUP
        OBJECTS {
                    ospfRouterId,
                    ospfAdminStat,
                    ospfVersionNumber,
                    ospfAreaBdrRtrStatus,
                    ospfASBdrRtrStatus,
                    ospfExternLsaCount,
                    ospfExternLsaCksumSum,
                    ospfTOSSupport,
                    ospfOriginateNewLsas,
                    ospfRxNewLsas,
                    ospfExtLsdbLimit,
                    ospfMulticastExtensions,
                    ospfExitOverflowInterval,
                    ospfDemandExtensions
        }
        STATUS  current
        DESCRIPTION
           "These objects are required for OSPF systems."
       ::= { ospfGroups 1 }


    ospfAreaGroup    OBJECT-GROUP
        OBJECTS {
                    ospfAreaId,
                    ospfImportAsExtern,
                    ospfSpfRuns,
                    ospfAreaBdrRtrCount,
                    ospfAsBdrRtrCount,
                    ospfAreaLsaCount,
                    ospfAreaLsaCksumSum,
                    ospfAreaSummary,
                    ospfAreaStatus
        }
        STATUS  current
        DESCRIPTION
           "These objects are required  for  OSPF  systems
           supporting areas."
       ::= { ospfGroups 2 }


    ospfStubAreaGroup    OBJECT-GROUP
        OBJECTS {
                    ospfStubAreaId,
                    ospfStubTOS,
                    ospfStubMetric,
                    ospfStubStatus,
                    ospfStubMetricType
        }
        STATUS  current
        DESCRIPTION
           "These objects are required  for  OSPF  systems
           supporting stub areas."
       ::= { ospfGroups 3 }

    ospfLsdbGroup    OBJECT-GROUP
        OBJECTS {
                    ospfLsdbAreaId,
                    ospfLsdbType,
                    ospfLsdbLsid,
                    ospfLsdbRouterId,
                    ospfLsdbSequence,
                    ospfLsdbAge,
                    ospfLsdbChecksum,
                    ospfLsdbAdvertisement
        }
        STATUS  current
        DESCRIPTION
           "These objects are required  for  OSPF  systems
           that display their link state database."
       ::= { ospfGroups 4 }


    ospfAreaRangeGroup    OBJECT-GROUP
        OBJECTS {
                    ospfAreaRangeAreaId,
                    ospfAreaRangeNet,
                    ospfAreaRangeMask,
                    ospfAreaRangeStatus,
                    ospfAreaRangeEffect
        }
        STATUS  obsolete
        DESCRIPTION
           "These objects are required for  non-CIDR  OSPF
           systems that support multiple areas."
       ::= { ospfGroups 5 }


    ospfHostGroup    OBJECT-GROUP
        OBJECTS {
                    ospfHostIpAddress,
                    ospfHostTOS,
                    ospfHostMetric,
                    ospfHostStatus,
                    ospfHostAreaID
        }
        STATUS  current
        DESCRIPTION
           "These objects are required  for  OSPF  systems
           that support attached hosts."
       ::= { ospfGroups 6 }

    ospfIfGroup    OBJECT-GROUP
        OBJECTS {
                    ospfIfIpAddress,
                    ospfAddressLessIf,
                    ospfIfAreaId,
                    ospfIfType,
                    ospfIfAdminStat,
                    ospfIfRtrPriority,
                    ospfIfTransitDelay,
                    ospfIfRetransInterval,
                    ospfIfHelloInterval,
                    ospfIfRtrDeadInterval,
                    ospfIfPollInterval,
                    ospfIfState,
                    ospfIfDesignatedRouter,
                    ospfIfBackupDesignatedRouter,
                    ospfIfEvents,
                    ospfIfAuthType,
                    ospfIfAuthKey,
                    ospfIfStatus,
                    ospfIfMulticastForwarding,
                    ospfIfDemand
        }
        STATUS  current
        DESCRIPTION
           "These objects are required for OSPF systems."
       ::= { ospfGroups 7 }


    ospfIfMetricGroup    OBJECT-GROUP
        OBJECTS {
                    ospfIfMetricIpAddress,
                    ospfIfMetricAddressLessIf,
                    ospfIfMetricTOS,
                    ospfIfMetricValue,
                    ospfIfMetricStatus
        }
        STATUS  current
        DESCRIPTION
           "These objects are required for OSPF systems."
       ::= { ospfGroups 8 }


    ospfVirtIfGroup    OBJECT-GROUP
        OBJECTS {
                    ospfVirtIfAreaId,
                    ospfVirtIfNeighbor,
                    ospfVirtIfTransitDelay,
                    ospfVirtIfRetransInterval,
                    ospfVirtIfHelloInterval,
                    ospfVirtIfRtrDeadInterval,
                    ospfVirtIfState,
                    ospfVirtIfEvents,
                    ospfVirtIfAuthType,
                    ospfVirtIfAuthKey,
                    ospfVirtIfStatus
        }
        STATUS  current
        DESCRIPTION
           "These objects are required for OSPF systems."
       ::= { ospfGroups 9 }


    ospfNbrGroup    OBJECT-GROUP
        OBJECTS {
                    ospfNbrIpAddr,
                    ospfNbrAddressLessIndex,
                    ospfNbrRtrId,
                    ospfNbrOptions,
                    ospfNbrPriority,
                    ospfNbrState,
                    ospfNbrEvents,
                    ospfNbrLsRetransQLen,
                    ospfNbmaNbrStatus,
                    ospfNbmaNbrPermanence,
                    ospfNbrHelloSuppressed
        }
        STATUS  current
        DESCRIPTION
           "These objects are required for OSPF systems."
       ::= { ospfGroups 10 }


    ospfVirtNbrGroup    OBJECT-GROUP
        OBJECTS {
                    ospfVirtNbrArea,
                    ospfVirtNbrRtrId,
                    ospfVirtNbrIpAddr,
                    ospfVirtNbrOptions,
                    ospfVirtNbrState,
                    ospfVirtNbrEvents,
                    ospfVirtNbrLsRetransQLen,
                    ospfVirtNbrHelloSuppressed
        }
        STATUS  current
        DESCRIPTION
           "These objects are required for OSPF systems."
       ::= { ospfGroups 11 }


    ospfExtLsdbGroup    OBJECT-GROUP
        OBJECTS {
                    ospfExtLsdbType,
                    ospfExtLsdbLsid,
                    ospfExtLsdbRouterId,
                    ospfExtLsdbSequence,
                    ospfExtLsdbAge,
                    ospfExtLsdbChecksum,
                    ospfExtLsdbAdvertisement
        }
        STATUS  current
        DESCRIPTION
           "These objects are required  for  OSPF  systems
           that display their link state database."
       ::= { ospfGroups 12 }


    ospfAreaAggregateGroup    OBJECT-GROUP
        OBJECTS {
                    ospfAreaAggregateAreaID,
                    ospfAreaAggregateLsdbType,
                    ospfAreaAggregateNet,
                    ospfAreaAggregateMask,
                    ospfAreaAggregateStatus,
                    ospfAreaAggregateEffect
        }
        STATUS  current
        DESCRIPTION
           "These objects are required for OSPF systems."
       ::= { ospfGroups 13 }

END

OSPF-TRAP-MIB DEFINITIONS ::= BEGIN

    IMPORTS
            MODULE-IDENTITY, OBJECT-TYPE, NOTIFICATION-TYPE, IpAddress
                FROM SNMPv2-SMI
            MODULE-COMPLIANCE, OBJECT-GROUP
                FROM SNMPv2-CONF
            ospfRouterId, ospfIfIpAddress, ospfAddressLessIf, ospfIfState,
            ospfVirtIfAreaId, ospfVirtIfNeighbor, ospfVirtIfState,
            ospfNbrIpAddr, ospfNbrAddressLessIndex, ospfNbrRtrId,
            ospfNbrState, ospfVirtNbrArea, ospfVirtNbrRtrId, ospfVirtNbrState,
            ospfLsdbType, ospfLsdbLsid, ospfLsdbRouterId, ospfLsdbAreaId,
            ospfExtLsdbLimit, ospf
                FROM OSPF-MIB;

    ospfTrap MODULE-IDENTITY
           LAST-UPDATED "9501201225Z" -- Fri Jan 20 12:25:50 PST 1995
           ORGANIZATION "IETF OSPF Working Group"
           CONTACT-INFO
           "                      Fred Baker
           Postal:                Cisco Systems
                                  519 Lado Drive
                                  Santa Barbara, California 93111
           Tel:                   +1 805 681 0115
           E-Mail:                fred@cisco.com

                                  Rob Coltun
           Postal:                RainbowBridge Communications
           Tel:                   (301) 340-9416
           E-Mail:                rcoltun@rainbow-bridge.com"
       DESCRIPTION
          "The MIB module to describe traps for  the  OSPF
          Version 2 Protocol."
      ::= { ospf 16 }

-- Trap Support Objects

--         The following are support objects for the OSPF traps.

ospfTrapControl OBJECT IDENTIFIER ::= { ospfTrap 1 }
ospfTraps OBJECT IDENTIFIER ::= { ospfTrap 2 }

    ospfSetTrap OBJECT-TYPE
        SYNTAX   OCTET STRING (SIZE(4))
        MAX-ACCESS   read-write
        STATUS   current
        DESCRIPTION
           "A four-octet string serving as a bit  map  for
           the trap events defined by the OSPF traps. This
           object is used to enable and  disable  specific
           OSPF   traps   where  a  1  in  the  bit  field
           represents enabled.  The right-most bit  (least
           significant) represents trap 0."
       --CONFIGURABLE
       ::= { ospfTrapControl 1 }


    ospfConfigErrorType OBJECT-TYPE
        SYNTAX   INTEGER   {
                    badVersion (1),
                    areaMismatch (2),
                    unknownNbmaNbr (3), -- Router is Dr eligible
                    unknownVirtualNbr (4),
                    authTypeMismatch(5),
                    authFailure (6),
                    netMaskMismatch (7),
                    helloIntervalMismatch (8),
                    deadIntervalMismatch (9),
                    optionMismatch (10) }
        MAX-ACCESS   read-only
        STATUS   current
        DESCRIPTION
           "Potential types  of  configuration  conflicts.
           Used  by the ospfConfigError and ospfConfigVir-
           tError traps."
   ::= { ospfTrapControl 2 }


    ospfPacketType OBJECT-TYPE
        SYNTAX   INTEGER   {
                    hello (1),
                    dbDescript (2),
                    lsReq (3),
                    lsUpdate (4),
                    lsAck (5) }
        MAX-ACCESS   read-only
        STATUS   current
        DESCRIPTION
           "OSPF packet types."
   ::= { ospfTrapControl 3 }


    ospfPacketSrc OBJECT-TYPE
        SYNTAX   IpAddress
        MAX-ACCESS   read-only
        STATUS   current
        DESCRIPTION
           "The IP address of an inbound packet that  can-
           not be identified by a neighbor instance."
       ::= { ospfTrapControl 4 }


-- Traps



    ospfVirtIfStateChange NOTIFICATION-TYPE
        OBJECTS {
                    ospfRouterId, -- The originator of the trap
                    ospfVirtIfAreaId,
                    ospfVirtIfNeighbor,
                    ospfVirtIfState  -- The new state
                  }
        STATUS             current
        DESCRIPTION
           "An ospfIfStateChange trap signifies that there
           has  been a change in the state of an OSPF vir-
           tual interface.
           This trap should be generated when  the  inter-
           face  state  regresses  (e.g., goes from Point-
           to-Point to Down) or progresses to  a  terminal
           state (i.e., Point-to-Point)."
   ::= { ospfTraps 1 }


    ospfNbrStateChange NOTIFICATION-TYPE
        OBJECTS {
                    ospfRouterId, -- The originator of the trap
                    ospfNbrIpAddr,
                    ospfNbrAddressLessIndex,
                    ospfNbrRtrId,
                    ospfNbrState  -- The new state
                  }
        STATUS             current
        DESCRIPTION
           "An  ospfNbrStateChange  trap  signifies   that
           there  has been a change in the state of a non-
           virtual OSPF neighbor.   This  trap  should  be
           generated  when  the  neighbor  state regresses
           (e.g., goes from Attempt or Full  to  1-Way  or
           Down)  or progresses to a terminal state (e.g.,
           2-Way or Full).  When an  neighbor  transitions
           from  or  to Full on non-broadcast multi-access
           and broadcast networks, the trap should be gen-
           erated  by the designated router.  A designated
           router transitioning to Down will be  noted  by
           ospfIfStateChange."
   ::= { ospfTraps 2 }


    ospfVirtNbrStateChange NOTIFICATION-TYPE
        OBJECTS {
                    ospfRouterId, -- The originator of the trap
                    ospfVirtNbrArea,
                    ospfVirtNbrRtrId,
                    ospfVirtNbrState  -- The new state
                  }
        STATUS             current
        DESCRIPTION
           "An ospfIfStateChange trap signifies that there
           has  been a change in the state of an OSPF vir-
           tual neighbor.  This trap should  be  generated
           when  the  neighbor state regresses (e.g., goes
           from Attempt or  Full  to  1-Way  or  Down)  or
           progresses to a terminal state (e.g., Full)."
   ::= { ospfTraps 3 }

    ospfIfConfigError NOTIFICATION-TYPE
        OBJECTS {
                    ospfRouterId, -- The originator of the trap
                    ospfIfIpAddress,
                    ospfAddressLessIf,
                    ospfPacketSrc,  -- The source IP address
                    ospfConfigErrorType, -- Type of error
                    ospfPacketType
                  }
        STATUS             current
        DESCRIPTION
           "An ospfIfConfigError  trap  signifies  that  a
           packet  has  been received on a non-virtual in-
           terface  from  a  router  whose   configuration
           parameters  conflict  with this router's confi-
           guration parameters.  Note that the  event  op-
           tionMismatch  should  cause  a  trap only if it
           prevents an adjacency from forming."
                  ::= { ospfTraps 4 }


    ospfVirtIfConfigError NOTIFICATION-TYPE
        OBJECTS {
                    ospfRouterId, -- The originator of the trap
                    ospfVirtIfAreaId,
                    ospfVirtIfNeighbor,
                    ospfConfigErrorType, -- Type of error
                    ospfPacketType
                  }
        STATUS             current
        DESCRIPTION
           "An ospfConfigError trap signifies that a pack-
           et  has  been  received  on a virtual interface
           from a router  whose  configuration  parameters
           conflict   with   this  router's  configuration
           parameters.  Note that the event optionMismatch
           should  cause a trap only if it prevents an ad-
           jacency from forming."
   ::= { ospfTraps 5 }


    ospfIfAuthFailure NOTIFICATION-TYPE
        OBJECTS {
                    ospfRouterId, -- The originator of the trap
                    ospfIfIpAddress,
                    ospfAddressLessIf,
                    ospfPacketSrc,  -- The source IP address
                    ospfConfigErrorType, -- authTypeMismatch or
                    ospfPacketType
                  }
        STATUS             current
        DESCRIPTION
           "An ospfIfAuthFailure  trap  signifies  that  a
           packet  has  been received on a non-virtual in-
           terface from a router whose authentication  key
           or  authentication  type  conflicts  with  this
           router's authentication key  or  authentication
           type."
   ::= { ospfTraps 6 }


    ospfVirtIfAuthFailure NOTIFICATION-TYPE
        OBJECTS {
                    ospfRouterId, -- The originator of the trap
                    ospfVirtIfAreaId,
                    ospfVirtIfNeighbor,
                    ospfConfigErrorType, -- authTypeMismatch or
                                         -- authFailure
                    ospfPacketType
                  }
        STATUS             current
        DESCRIPTION
           "An ospfVirtIfAuthFailure trap signifies that a
           packet has been received on a virtual interface
           from a router whose authentication key  or  au-
           thentication  type conflicts with this router's
           authentication key or authentication type."
   ::= { ospfTraps 7 }


    ospfIfRxBadPacket NOTIFICATION-TYPE
        OBJECTS {
                    ospfRouterId, -- The originator of the trap
                    ospfIfIpAddress,
                    ospfAddressLessIf,
                    ospfPacketSrc,  -- The source IP address
                    ospfPacketType
                  }
        STATUS             current
        DESCRIPTION
           "An ospfIfRxBadPacket trap  signifies  that  an
           OSPF  packet has been received on a non-virtual
           interface that cannot be parsed."
   ::= { ospfTraps 8 }

    ospfVirtIfRxBadPacket NOTIFICATION-TYPE
        OBJECTS {
                    ospfRouterId, -- The originator of the trap
                    ospfVirtIfAreaId,
                    ospfVirtIfNeighbor,
                    ospfPacketType
                  }
        STATUS             current
        DESCRIPTION
           "An ospfRxBadPacket trap signifies that an OSPF
           packet has been received on a virtual interface
           that cannot be parsed."
   ::= { ospfTraps 9 }


    ospfTxRetransmit NOTIFICATION-TYPE
        OBJECTS {
                    ospfRouterId, -- The originator of the trap
                    ospfIfIpAddress,
                    ospfAddressLessIf,
                    ospfNbrRtrId, -- Destination
                    ospfPacketType,
                    ospfLsdbType,
                    ospfLsdbLsid,
                    ospfLsdbRouterId
                  }
        STATUS             current
        DESCRIPTION
           "An ospfTxRetransmit  trap  signifies  than  an
           OSPF  packet  has  been retransmitted on a non-
           virtual interface.  All packets that may be re-
           transmitted  are associated with an LSDB entry.
           The LS type, LS ID, and Router ID are  used  to
           identify the LSDB entry."
   ::= { ospfTraps 10 }


    ospfVirtIfTxRetransmit NOTIFICATION-TYPE
        OBJECTS {
                    ospfRouterId, -- The originator of the trap
                    ospfVirtIfAreaId,
                    ospfVirtIfNeighbor,
                    ospfPacketType,
                    ospfLsdbType,
                    ospfLsdbLsid,
                    ospfLsdbRouterId
                  }
        STATUS             current
        DESCRIPTION
           "An ospfTxRetransmit  trap  signifies  than  an
           OSPF packet has been retransmitted on a virtual
           interface.  All packets that may be retransmit-
           ted  are  associated with an LSDB entry. The LS
           type, LS ID, and Router ID are used to identify
           the LSDB entry."
   ::= { ospfTraps 11 }


    ospfOriginateLsa NOTIFICATION-TYPE
        OBJECTS {
                    ospfRouterId, -- The originator of the trap
                    ospfLsdbAreaId,  -- 0.0.0.0 for AS Externals
                    ospfLsdbType,
                    ospfLsdbLsid,
                    ospfLsdbRouterId
                  }
        STATUS             current
        DESCRIPTION
           "An ospfOriginateLsa trap signifies that a  new
           LSA  has  been originated by this router.  This
           trap should not be invoked for simple refreshes
           of  LSAs  (which happesn every 30 minutes), but
           instead will only be invoked  when  an  LSA  is
           (re)originated due to a topology change.  Addi-
           tionally, this trap does not include LSAs  that
           are  being  flushed  because  they have reached
           MaxAge."
   ::= { ospfTraps 12 }


    ospfMaxAgeLsa NOTIFICATION-TYPE
        OBJECTS {
                    ospfRouterId, -- The originator of the trap
                    ospfLsdbAreaId,  -- 0.0.0.0 for AS Externals
                    ospfLsdbType,
                    ospfLsdbLsid,
                    ospfLsdbRouterId
                  }
        STATUS             current
        DESCRIPTION
           "An ospfMaxAgeLsa trap signifies  that  one  of
           the LSA in the router's link-state database has
           aged to MaxAge."
   ::= { ospfTraps 13 }

    ospfLsdbOverflow NOTIFICATION-TYPE
        OBJECTS {
                    ospfRouterId, -- The originator of the trap
                    ospfExtLsdbLimit
                  }
        STATUS             current
        DESCRIPTION
           "An ospfLsdbOverflow trap  signifies  that  the
           number of LSAs in the router's link-state data-
           base has exceeded ospfExtLsdbLimit."
   ::= { ospfTraps 14 }


    ospfLsdbApproachingOverflow NOTIFICATION-TYPE
        OBJECTS {
                    ospfRouterId, -- The originator of the trap
                    ospfExtLsdbLimit
                  }
        STATUS             current
        DESCRIPTION
           "An ospfLsdbApproachingOverflow trap  signifies
           that  the  number of LSAs in the router's link-
           state database has exceeded ninety  percent  of
           ospfExtLsdbLimit."
   ::= { ospfTraps 15 }

    ospfIfStateChange NOTIFICATION-TYPE
        OBJECTS {
                    ospfRouterId, -- The originator of the trap
                    ospfIfIpAddress,
                    ospfAddressLessIf,
                    ospfIfState   -- The new state
                  }
        STATUS             current
        DESCRIPTION
           "An ospfIfStateChange trap signifies that there
           has been a change in the state of a non-virtual
           OSPF interface. This trap should  be  generated
           when  the interface state regresses (e.g., goes
           from Dr to Down) or progresses  to  a  terminal
           state  (i.e.,  Point-to-Point, DR Other, Dr, or
           Backup)."
   ::= { ospfTraps 16 }



-- conformance information

ospfTrapConformance OBJECT IDENTIFIER ::= { ospfTrap 3 }

ospfTrapGroups      OBJECT IDENTIFIER ::= { ospfTrapConformance 1 }
ospfTrapCompliances OBJECT IDENTIFIER ::= { ospfTrapConformance 2 }

-- compliance statements

    ospfTrapCompliance MODULE-COMPLIANCE
        STATUS  current
        DESCRIPTION
           "The compliance statement "
       MODULE  -- this module
       MANDATORY-GROUPS { ospfTrapControlGroup }


        GROUP       ospfTrapControlGroup
        DESCRIPTION
           "This group is optional but recommended for all
           OSPF systems"
       ::= { ospfTrapCompliances 1 }


-- units of conformance

    ospfTrapControlGroup    OBJECT-GROUP
        OBJECTS {
                           ospfSetTrap,
                           ospfConfigErrorType,
                           ospfPacketType,
                           ospfPacketSrc
        }
        STATUS  current
        DESCRIPTION
           "These objects are required  to  control  traps
           from OSPF systems."
       ::= { ospfTrapGroups 1 }


END

   IF-MIB DEFINITIONS ::= BEGIN

   IMPORTS
       MODULE-IDENTITY, OBJECT-TYPE, Counter32, Gauge32,
       Integer32, TimeTicks, Counter64          FROM SNMPv2-SMI
       TEXTUAL-CONVENTION, DisplayString,
       PhysAddress, TruthValue, RowStatus,
       AutonomousType, TestAndIncr              FROM SNMPv2-TC
       MODULE-COMPLIANCE, OBJECT-GROUP          FROM SNMPv2-CONF
       IANAifType                               FROM IANAifType-MIB
       mib-2, interfaces                        FROM RFC1213-MIB
       InterfaceIndex                           FROM USR-DEFINITIONS-MIB;

   ifMIB MODULE-IDENTITY
       LAST-UPDATED "9311082155Z"
       ORGANIZATION "IETF Interfaces MIB Working Group"
       CONTACT-INFO

                  "        Keith McCloghrie

                   Postal: Hughes LAN Systems
                           1225 Charleston Road, Mountain View, CA 94043

                   Tel:    +1 415 966 7934
                   E-Mail: kzm@hls.com


                           Frank Kastenholz

                   Postal: FTP Software
                           2 High Street, North Andover, MA 01845

                   Tel:    +1 508 685 4000
                   E-Mail: kasten@ftp.com"
       DESCRIPTION
               "The MIB module to describe generic objects for
               network interface sub-layers.  This MIB is an updated
               version of MIB-II's ifTable, and incorporates the
               extensions defined in RFC 1229."
       ::= { mib-2 31 }

   ifMIBObjects OBJECT IDENTIFIER ::= { ifMIB 1 }

   -- OwnerString has the same semantics as used in RFC 1271

   OwnerString ::= TEXTUAL-CONVENTION
       DISPLAY-HINT "255a"
       STATUS       current
       DESCRIPTION
               "This data type is used to model an administratively
               assigned name of the owner of a resource.  This
               information is taken from the NVT ASCII character set.
               It is suggested that this name contain one or more of
               the following: ASCII form of the manager station's
               transport address, management station name (e.g.,
               domain name), network management personnel's name,
               location, or phone number.  In some cases the agent
               itself will be the owner of an entry.  In these cases,
               this string shall be set to a string starting with
               'agent'."
       SYNTAX       OCTET STRING (SIZE(0..255))
   -- InterfaceIndex contains the semantics of ifIndex and
   -- should be used for any objects defined on other mib
   -- modules that need these semantics.

   ifNumber  OBJECT-TYPE
       SYNTAX      Integer32
       MAX-ACCESS  read-only
       STATUS      current
       DESCRIPTION
               "The number of network interfaces (regardless of their
               current state) present on this system."
       ::= { interfaces 1 }


   -- the Interfaces table

   -- The Interfaces table contains information on the entity's
   -- interfaces.  Each sub-layer below the internetwork-layer
   -- of a network interface is considered to be an interface.

   ifTable OBJECT-TYPE
       SYNTAX      SEQUENCE OF IfEntry
       MAX-ACCESS  not-accessible
       STATUS      current
       DESCRIPTION
               "A list of interface entries.  The number of entries
               is given by the value of ifNumber."
       ::= { interfaces 2 }

   ifEntry OBJECT-TYPE
       SYNTAX      IfEntry
       MAX-ACCESS  not-accessible
       STATUS      current
       DESCRIPTION
               "An entry containing management information applicable
               to a particular interface."
       INDEX   { ifIndex }
       ::= { ifTable 1 }

   IfEntry ::=
       SEQUENCE {
           ifIndex                 InterfaceIndex,
           ifDescr                 DisplayString,
           ifType                  IANAifType,
           ifMtu                   Integer32,
           ifSpeed                 Gauge32,
           ifPhysAddress           PhysAddress,
           ifAdminStatus           INTEGER,
           ifOperStatus            INTEGER,
           ifLastChange            TimeTicks,
           ifInOctets              Counter32,
           ifInUcastPkts           Counter32,
           ifInNUcastPkts          Counter32,  -- deprecated
           ifInDiscards            Counter32,
           ifInErrors              Counter32,
           ifInUnknownProtos       Counter32,
           ifOutOctets             Counter32,
           ifOutUcastPkts          Counter32,
           ifOutNUcastPkts         Counter32,  -- deprecated
           ifOutDiscards           Counter32,
           ifOutErrors             Counter32,
           ifOutQLen               Gauge32,    -- deprecated
           ifSpecific              OBJECT IDENTIFIER -- deprecated
       }


   ifIndex OBJECT-TYPE
       SYNTAX      InterfaceIndex
       MAX-ACCESS  read-only
       STATUS      current
       DESCRIPTION
               "A unique value, greater than zero, for each
               interface.  It is recommended that values are assigned
               contiguously starting from 1.  The value for each
               interface sub-layer must remain constant at least from
               one re-initialization of the entity's network
               management system to the next re-initialization."
       ::= { ifEntry 1 }

   ifDescr OBJECT-TYPE
       SYNTAX      DisplayString (SIZE (0..255))
       MAX-ACCESS  read-only
       STATUS      current
       DESCRIPTION
               "A textual string containing information about the
               interface.  This string should include the name of the
               manufacturer, the product name and the version of the
               interface hardware/software."
       ::= { ifEntry 2 }

   ifType OBJECT-TYPE
       SYNTAX      IANAifType
       MAX-ACCESS  read-only
       STATUS      current
       DESCRIPTION
               "The type of interface.  Additional values for ifType
               are assigned by the Internet Assigned Numbers
               Authority (IANA), through updating the syntax of the
               IANAifType textual convention."
       ::= { ifEntry 3 }

   ifMtu OBJECT-TYPE
       SYNTAX      Integer32
       MAX-ACCESS  read-only
       STATUS      current
       DESCRIPTION
               "The size of the largest packet which can be
               sent/received on the interface, specified in octets.
               For interfaces that are used for transmitting network
               datagrams, this is the size of the largest network
               datagram that can be sent on the interface."
       ::= { ifEntry 4 }

   ifSpeed OBJECT-TYPE
       SYNTAX      Gauge32
       MAX-ACCESS  read-only
       STATUS      current
       DESCRIPTION
               "An estimate of the interface's current bandwidth in
               bits per second.  For interfaces which do not vary in
               bandwidth or for those where no accurate estimation
               can be made, this object should contain the nominal
               bandwidth.  If the bandwidth of the interface is
               greater than the maximum value reportable by this
               object then this object should report its maximum
               value (4,294,967,295) and ifHighSpeed must be used to
               report the interace's speed.  For a sub-layer which
               has no concept of bandwidth, this object should be
               zero."
       ::= { ifEntry 5 }

   ifPhysAddress OBJECT-TYPE
       SYNTAX      PhysAddress
       MAX-ACCESS  read-only
       STATUS      current
       DESCRIPTION
               "The interface's address at its protocol sub-layer.
               The interface's media-specific MIB must define the bit
               and byte ordering and format of the value contained by
               this object.  For interfaces which do not have such an
               address (e.g., a serial line), this object should
               contain an octet string of zero length."
       ::= { ifEntry 6 }

   ifAdminStatus OBJECT-TYPE
       SYNTAX  INTEGER {
                   up(1),       -- ready to pass packets
                   down(2),
                   testing(3)   -- in some test mode
               }
       MAX-ACCESS  read-write
       STATUS      current
       DESCRIPTION
               "The desired state of the interface.  The testing(3)
               state indicates that no operational packets can be
               passed.  When a managed system initializes, all
               interfaces start with ifAdminStatus in the down(2)
               state.  As a result of either explicit management
               action or per configuration information retained by
               the managed system, ifAdminStatus is then changed to
               either the up(1) or testing(3) states (or remains in
               the down(2) state)."
       ::= { ifEntry 7 }

   ifOperStatus OBJECT-TYPE
       SYNTAX  INTEGER {
                   up(1),       -- ready to pass packets
                   down(2),
                   testing(3),  -- in some test mode
                   unknown(4),  -- status can not be determined
                                -- for some reason.
                   dormant(5)
               }
       MAX-ACCESS  read-only
       STATUS      current
       DESCRIPTION
               "The current operational state of the interface.  The
               testing(3) state indicates that no operational packets
               can be passed.  If ifAdminStatus is down(2) then
               ifOperStatus should be down(2).  If ifAdminStatus is
               changed to up(1) then ifOperStatus should change to
               up(1) if the interface is ready to transmit and
               receive network traffic; it should change to
               dormant(5) if the interface is waiting for external
               actions (such as a serial line waiting for an
               incomming connection); it should remain in the down(2)
               state if and only if there is a fault that prevents if
               from going to the up(1) state."
       ::= { ifEntry 8 }

   ifLastChange OBJECT-TYPE
       SYNTAX      TimeTicks
       MAX-ACCESS  read-only
       STATUS      current
       DESCRIPTION
               "The value of sysUpTime at the time the interface
               entered its current operational state.  If the current
               state was entered prior to the last re-initialization
               of the local network management subsystem, then this
               object contains a zero value."
       ::= { ifEntry 9 }

   ifInOctets OBJECT-TYPE
       SYNTAX      Counter32
       MAX-ACCESS  read-only
       STATUS      current
       DESCRIPTION
               "The total number of octets received on the interface,
               including framing characters."
       ::= { ifEntry 10 }

   ifInUcastPkts OBJECT-TYPE
       SYNTAX      Counter32
       MAX-ACCESS  read-only
       STATUS      current
       DESCRIPTION
               "The number of packets, delivered by this sub-layer to
               a higher (sub-)layer, which were not addressed to a
               multicast or broadcast address at this sub-layer."
       ::= { ifEntry 11 }

   ifInNUcastPkts OBJECT-TYPE
       SYNTAX  Counter32
       MAX-ACCESS  read-only
       STATUS      deprecated
       DESCRIPTION
               "The number of packets, delivered by this sub-layer to
               a higher (sub-)layer, which were addressed to a
               multicast or broadcast address at this sub-layer.
               This object is deprecated in favour of
               ifInMulticastPkts and ifInBroadcastPkts."
       ::= { ifEntry 12 }

   ifInDiscards OBJECT-TYPE
       SYNTAX      Counter32
       MAX-ACCESS  read-only
       STATUS      current
       DESCRIPTION
               "The number of inbound packets which were chosen to be
               discarded even though no errors had been detected to
               prevent their being deliverable to a higher-layer
               protocol.  One possible reason for discarding such a
               packet could be to free up buffer space."
       ::= { ifEntry 13 }

   ifInErrors OBJECT-TYPE
       SYNTAX      Counter32
       MAX-ACCESS  read-only
       STATUS      current
       DESCRIPTION
               "For packet-oriented interfaces, the number of inbound
               packets that contained errors preventing them from
               being deliverable to a higher-layer protocol.  For
               character-oriented or fixed-length interfaces, the
               number of inbound transmission units that contained
               errors preventing them from being deliverable to a
               higher-layer protocol."
       ::= { ifEntry 14 }

   ifInUnknownProtos OBJECT-TYPE
       SYNTAX      Counter32
       MAX-ACCESS  read-only
       STATUS      current
       DESCRIPTION
               "For packet-oriented interfaces, the number of packets
               received via the interface which were discarded
               because of an unknown or unsupported protocol.  For
               character-oriented or fixed-length interfaces which
               support protocol multiplexing the number of
               transmission units received via the interface which
               were discarded because of an unknown or unsupported
               protocol.  For any interface which does not support
               protocol multiplexing, this counter will always be 0."
       ::= { ifEntry 15 }

   ifOutOctets OBJECT-TYPE
       SYNTAX      Counter32
       MAX-ACCESS  read-only
       STATUS      current
       DESCRIPTION
               "The total number of octets transmitted out of the
               interface, including framing characters."
       ::= { ifEntry 16 }

   ifOutUcastPkts OBJECT-TYPE
       SYNTAX      Counter32
       MAX-ACCESS  read-only
       STATUS      current
       DESCRIPTION

               "The total number of packets that higher-level
               protocols requested be transmitted, and which were not
               addressed to a multicast or broadcast address at this
               sub-layer, including those that were discarded or not
               sent."
       ::= { ifEntry 17 }

   ifOutNUcastPkts OBJECT-TYPE
       SYNTAX      Counter32
       MAX-ACCESS  read-only
       STATUS      deprecated
       DESCRIPTION
               "The total number of packets that higher-level
               protocols requested be transmitted, and which were
               addressed to a multicast or broadcast address at this
               sub-layer, including those that were discarded or not
               sent.

               This object is deprecated in favour of
               ifOutMulticastPkts and ifOutBroadcastPkts."
       ::= { ifEntry 18 }

   ifOutDiscards OBJECT-TYPE
       SYNTAX      Counter32
       MAX-ACCESS  read-only
       STATUS      current
       DESCRIPTION
               "The number of outbound packets which were chosen to
               be discarded even though no errors had been detected
               to prevent their being transmitted.  One possible
               reason for discarding such a packet could be to free
               up buffer space."
       ::= { ifEntry 19 }

   ifOutErrors OBJECT-TYPE
       SYNTAX      Counter32
       MAX-ACCESS  read-only
       STATUS      current
       DESCRIPTION
               "For packet-oriented interfaces, the number of
               outbound packets that could not be transmitted because
               of errors.  For character-oriented or fixed-length
               interfaces, the number of outbound transmission units
               that could not be transmitted because of errors."
       ::= { ifEntry 20 }

   ifOutQLen OBJECT-TYPE
       SYNTAX      Gauge32
       MAX-ACCESS  read-only
       STATUS      deprecated
       DESCRIPTION
               "The length of the output packet queue (in packets)."
       ::= { ifEntry 21 }

   ifSpecific OBJECT-TYPE
       SYNTAX      OBJECT IDENTIFIER
       MAX-ACCESS  read-only
       STATUS      deprecated
       DESCRIPTION
               "A reference to MIB definitions specific to the
               particular media being used to realize the interface.
               It is recommended that this value point to an instance
               of a MIB object in the media-specific MIB, i.e., that
               this object have the semantics associated with the
               InstancePointer textual convention defined in RFC
               1443.  In fact, it is recommended that the media-
               specific MIB specify what value ifSpecific should/can
               take for values of ifType.  If no MIB definitions
               specific to the particular media are available, the
               value should be set to the OBJECT IDENTIFIER { 0 0 }."
       ::= { ifEntry 22 }


   --
   --   Extension to the interface table
   --
   -- This table replaces the ifExtnsTable table.
   --

   ifXTable        OBJECT-TYPE
       SYNTAX      SEQUENCE OF IfXEntry
       MAX-ACCESS  not-accessible
       STATUS      current
       DESCRIPTION
               "A list of interface entries.  The number of entries
               is given by the value of ifNumber.  This table
               contains additional objects for the interface table."
       ::= { ifMIBObjects 1 }

   ifXEntry        OBJECT-TYPE
       SYNTAX      IfXEntry
       MAX-ACCESS  not-accessible
       STATUS      current
       DESCRIPTION
               "An entry containing additional management information
               applicable to a particular interface."
       AUGMENTS    { ifEntry }
       ::= { ifXTable 1 }

   IfXEntry ::=
       SEQUENCE {
           ifName                  DisplayString,
           ifInMulticastPkts       Counter32,
           ifInBroadcastPkts       Counter32,
           ifOutMulticastPkts      Counter32,
           ifOutBroadcastPkts      Counter32,
           ifHCInOctets            Counter64,
           ifHCInUcastPkts         Counter64,
           ifHCInMulticastPkts     Counter64,
           ifHCInBroadcastPkts     Counter64,
           ifHCOutOctets           Counter64,
           ifHCOutUcastPkts        Counter64,
           ifHCOutMulticastPkts    Counter64,
           ifHCOutBroadcastPkts    Counter64,
           ifLinkUpDownTrapEnable  INTEGER,
           ifHighSpeed             Gauge32,
           ifPromiscuousMode       TruthValue,
           ifConnectorPresent      TruthValue
       }


   ifName OBJECT-TYPE
       SYNTAX      DisplayString
       MAX-ACCESS  read-only
       STATUS      current
       DESCRIPTION
               "The textual name of the interface.  The value of this
               object should be the name of the interface as assigned
               by the local device and should be suitable for use in
               commands entered at the device's `console'.  This
               might be a text name, such as `le0' or a simple port
               number, such as `1', depending on the interface naming
               syntax of the device.  If several entries in the
               ifTable together represent a single interface as named
               by the device, then each will have the same value of
               ifName.  If there is no local name, or this object is
               otherwise not applicable, then this object contains a
               0-length string."
       ::= { ifXEntry 1 }

   ifInMulticastPkts OBJECT-TYPE
       SYNTAX      Counter32
       MAX-ACCESS  read-only
       STATUS      current
       DESCRIPTION
               "The number of packets, delivered by this sub-layer to
               a higher (sub-)layer, which were addressed to a
               multicast address at this sub-layer.  For a MAC layer
               protocol, this includes both Group and Functional
               addresses."
       ::= { ifXEntry 2 }

   ifInBroadcastPkts OBJECT-TYPE
       SYNTAX      Counter32
       MAX-ACCESS  read-only
       STATUS      current
       DESCRIPTION
               "The number of packets, delivered by this sub-layer to
               a higher (sub-)layer, which were addressed to a
               broadcast address at this sub-layer."
       ::= { ifXEntry 3 }

   ifOutMulticastPkts OBJECT-TYPE
       SYNTAX      Counter32
       MAX-ACCESS  read-only
       STATUS      current
       DESCRIPTION
               "The total number of packets that higher-level
               protocols requested be transmitted, and which were
               addressed to a multicast address at this sub-layer,
               including those that were discarded or not sent.  For
               a MAC layer protocol, this includes both Group and
               Functional addresses."
       ::= { ifXEntry 4 }

   ifOutBroadcastPkts OBJECT-TYPE
       SYNTAX      Counter32
       MAX-ACCESS  read-only
       STATUS      current
       DESCRIPTION
               "The total number of packets that higher-level
               protocols requested be transmitted, and which were
               addressed to a broadcast address at this sub-layer,
               including those that were discarded or not sent."
       ::= { ifXEntry 5 }

   --
   -- High Capacity Counter objects.  These objects are all

   -- 64 bit versions of the "basic" ifTable counters.  These
   -- objects all have the same basic semantics as their 32-bit
   -- counterparts, however, their syntax has been extended
   -- to 64 bits.
   --

   ifHCInOctets OBJECT-TYPE
       SYNTAX      Counter64
       MAX-ACCESS  read-only
       STATUS      current
       DESCRIPTION
               "The total number of octets received on the interface,
               including framing characters.  This object is a 64-bit
               version of ifInOctets."
       ::= { ifXEntry 6 }

   ifHCInUcastPkts OBJECT-TYPE
       SYNTAX      Counter64
       MAX-ACCESS  read-only
       STATUS      current
       DESCRIPTION
               "The number of packets, delivered by this sub-layer to
               a higher (sub-)layer, which were not addressed to a
               multicast or broadcast address at this sub-layer.
               This object is a 64-bit version of ifInUcastPkts."
       ::= { ifXEntry 7 }

   ifHCInMulticastPkts OBJECT-TYPE
       SYNTAX      Counter64
       MAX-ACCESS  read-only
       STATUS      current
       DESCRIPTION
               "The number of packets, delivered by this sub-layer to
               a higher (sub-)layer, which were addressed to a
               multicast address at this sub-layer.  For a MAC layer
               protocol, this includes both Group and Functional
               addresses.  This object is a 64-bit version of
               ifInMulticastPkts."
       ::= { ifXEntry 8 }

   ifHCInBroadcastPkts OBJECT-TYPE
       SYNTAX      Counter64
       MAX-ACCESS  read-only
       STATUS      current
       DESCRIPTION
               "The number of packets, delivered by this sub-layer to
               a higher (sub-)layer, which were addressed to a
               broadcast address at this sub-layer.  This object is a
               64-bit version of ifInBroadcastPkts."
       ::= { ifXEntry 9 }

   ifHCOutOctets OBJECT-TYPE
       SYNTAX      Counter64
       MAX-ACCESS  read-only
       STATUS      current
       DESCRIPTION
               "The total number of octets transmitted out of the
               interface, including framing characters.  This object
               is a 64-bit version of ifOutOctets."
       ::= { ifXEntry 10 }

   ifHCOutUcastPkts OBJECT-TYPE
       SYNTAX      Counter64
       MAX-ACCESS  read-only
       STATUS      current
       DESCRIPTION
               "The total number of packets that higher-level
               protocols requested be transmitted, and which were not
               addressed to a multicast or broadcast address at this
               sub-layer, including those that were discarded or not
               sent.  This object is a 64-bit version of
               ifOutUcastPkts."
       ::= { ifXEntry 11 }

   ifHCOutMulticastPkts OBJECT-TYPE
       SYNTAX      Counter64
       MAX-ACCESS  read-only
       STATUS      current
       DESCRIPTION
               "The total number of packets that higher-level
               protocols requested be transmitted, and which were
               addressed to a multicast address at this sub-layer,
               including those that were discarded or not sent.  For
               a MAC layer protocol, this includes both Group and
               Functional addresses.  This object is a 64-bit version
               of ifOutMulticastPkts."
       ::= { ifXEntry 12 }

   ifHCOutBroadcastPkts OBJECT-TYPE
       SYNTAX      Counter64
       MAX-ACCESS  read-only
       STATUS      current
       DESCRIPTION
               "The total number of packets that higher-level
               protocols requested be transmitted, and which were
               addressed to a broadcast address at this sub-layer,
               including those that were discarded or not sent.  This
               object is a 64-bit version of ifOutBroadcastPkts."
       ::= { ifXEntry 13 }

   ifLinkUpDownTrapEnable  OBJECT-TYPE
       SYNTAX      INTEGER { enabled(1), disabled(2) }
       MAX-ACCESS  read-write
       STATUS      current
       DESCRIPTION
               "Indicates whether linkUp/linkDown traps should be
               generated for this interface.

               By default, this object should have the value
               enabled(1) for interfaces which do not operate on
               'top' of any other interface (as defined in the
               ifStackTable), and disabled(2) otherwise."
       ::= { ifXEntry 14 }

   ifHighSpeed OBJECT-TYPE
       SYNTAX      Gauge32
       MAX-ACCESS  read-only
       STATUS      current
       DESCRIPTION
               "An estimate of the interface's current bandwidth in
               units of 1,000,000 bits per second.  If this object
               reports a value of `n' then the speed of the interface
               is somewhere in the range of `n-500,000' to
               `n+499,999'.  For interfaces which do not vary in
               bandwidth or for those where no accurate estimation
               can be made, this object should contain the nominal
               bandwidth.  For a sub-layer which has no concept of
               bandwidth, this object should be zero."
       ::= { ifXEntry 15 }

   ifPromiscuousMode  OBJECT-TYPE
       SYNTAX      TruthValue
       MAX-ACCESS  read-write
       STATUS      current
       DESCRIPTION
               "This object has a value of false(2) if this interface
               only accepts packets/frames that are addressed to this
               station.  This object has a value of true(1) when the
               station accepts all packets/frames transmitted on the
               media.  The value true(1) is only legal on certain
               types of media.  If legal, setting this object to a
               value of true(1) may require the interface to be reset
               before becoming effective.

               The value of ifPromiscuousMode does not affect the
               reception of broadcast and multicast packets/frames by
               the interface."
       ::= { ifXEntry 16 }

   ifConnectorPresent   OBJECT-TYPE
       SYNTAX      TruthValue
       MAX-ACCESS  read-only
       STATUS      current
       DESCRIPTION
               "This object has the value 'true(1)' if the interface
               sublayer has a physical connector and the value
               'false(2)' otherwise."
       ::= { ifXEntry 17 }


   --           The Interface Stack Group
   --
   -- Implementation of this group is mandatory for all systems
   --

   ifStackTable  OBJECT-TYPE
        SYNTAX        SEQUENCE OF IfStackEntry
        MAX-ACCESS    not-accessible
        STATUS        current
        DESCRIPTION
               "The table containing information on the relationships
               between the multiple sub-layers of network interfaces.
               In particular, it contains information on which sub-
               layers run 'on top of' which other sub-layers.  Each
               sub-layer corresponds to a conceptual row in the
               ifTable."
        ::= { ifMIBObjects 2 }


   ifStackEntry  OBJECT-TYPE
        SYNTAX        IfStackEntry
        MAX-ACCESS    not-accessible
        STATUS        current
        DESCRIPTION
               "Information on a particular relationship between two
               sub-layers, specifying that one sub-layer runs on
               'top' of the other sub-layer.  Each sub-layer
               corresponds to a conceptual row in the ifTable."
        INDEX { ifStackHigherLayer, ifStackLowerLayer }
        ::= { ifStackTable 1 }


   IfStackEntry ::=
       SEQUENCE {
           ifStackHigherLayer  Integer32,
           ifStackLowerLayer   Integer32,
           ifStackStatus       RowStatus
        }


   ifStackHigherLayer  OBJECT-TYPE
        SYNTAX        Integer32
        MAX-ACCESS    not-accessible
        STATUS        current
        DESCRIPTION
               "The value of ifIndex corresponding to the higher
               sub-layer of the relationship, i.e., the sub-layer
               which runs on 'top' of the sub-layer identified by the
               corresponding instance of ifStackLowerLayer.  If there
               is no higher sub-layer (below the internetwork layer),
               then this object has the value 0."
        ::= { ifStackEntry 1 }


   ifStackLowerLayer  OBJECT-TYPE
        SYNTAX        Integer32
        MAX-ACCESS    not-accessible
        STATUS        current
        DESCRIPTION
               "The value of ifIndex corresponding to the lower sub-
               layer of the relationship, i.e., the sub-layer which
               runs 'below' the sub-layer identified by the
               corresponding instance of ifStackHigherLayer.  If
               there is no lower sub-layer, then this object has the
               value 0."
        ::= { ifStackEntry 2 }


   ifStackStatus  OBJECT-TYPE
       SYNTAX         RowStatus
       MAX-ACCESS     read-write
       STATUS         current
       DESCRIPTION
               "The status of the relationship between two sub-
               layers.

               Changing the value of this object from 'active' to
               'notInService' or 'destroy' will likely have
               consequences up and down the interface stack.  Thus,
               write access to this object is likely to be
               inappropriate for some types of interfaces, and many
               implementations will choose not to support write-
               access for any type of interface."
       ::= { ifStackEntry 3 }


   --
   --    The Interface Test Table
   --
   -- This group of objects is optional.  However, a media-specific
   -- MIB may make implementation of this group mandatory.
   --
   -- This table replaces the ifExtnsTestTable
   --

   ifTestTable   OBJECT-TYPE
       SYNTAX      SEQUENCE OF IfTestEntry
       MAX-ACCESS  not-accessible
       STATUS      current
       DESCRIPTION
               "This table contains one entry per interface.  It
               defines objects which allow a network manager to
               instruct an agent to test an interface for various
               faults.  Tests for an interface are defined in the
               media-specific MIB for that interface.  After invoking
               a test, the object ifTestResult can be read to
               determine the outcome.  If an agent can not perform
               the test, ifTestResult is set to so indicate.  The
               object ifTestCode can be used to provide further
               test-specific or interface-specific (or even
               enterprise-specific) information concerning the
               outcome of the test.  Only one test can be in progress
               on each interface at any one time.  If one test is in
               progress when another test is invoked, the second test
               is rejected.  Some agents may reject a test when a
               prior test is active on another interface.
               Before starting a test, a manager-station must first
               obtain 'ownership' of the entry in the ifTestTable for
               the interface to be tested.  This is accomplished with
               the ifTestId and ifTestStatus objects as follows:

            try_again:
                get (ifTestId, ifTestStatus)
                while (ifTestStatus != notInUse)
                    /*
                     * Loop while a test is running or some other
                     * manager is configuring a test.
                     */
                    short delay
                    get (ifTestId, ifTestStatus)
                }

                /*
                 * Is not being used right now -- let's compete
                 * to see who gets it.
                 */
                lock_value = ifTestId

                if ( set(ifTestId = lock_value, ifTestStatus = inUse,
                         ifTestOwner = 'my-IP-address') == FAILURE)
                    /*
                     * Another manager got the ifTestEntry -- go
                     * try again
                     */
                    goto try_again;

                /*
                 * I have the lock
                 */
                set up any test parameters.

                /*
                 * This starts the test
                 */
                set(ifTestType = test_to_run);

                wait for test completion by polling ifTestResult

                when test completes, agent sets ifTestResult
                     agent also sets ifTestStatus = 'notInUse'

                retrieve any additional test results, and ifTestId

                if (ifTestId == lock_value+1) results are valid
              A manager station first retrieves the value of the
              appropriate ifTestId and ifTestStatus objects,
              periodically repeating the retrieval if necessary,
              until the value of ifTestStatus is 'notInUse'.  The
              manager station then tries to set the same ifTestId
              object to the value it just retrieved, the same
              ifTestStatus object to 'inUse', and the corresponding
              ifTestOwner object to a value indicating itself.  If
              the set operation succeeds then the manager has
              obtained ownership of the ifTestEntry, and the value of
              the ifTestId object is incremented by the agent (per
              the semantics of TestAndIncr).  Failure of the set
              operation indicates that some other manager has
              obtained ownership of the ifTestEntry.

              Once ownership is obtained, any test parameters can be
              setup, and then the test is initiated by setting
              ifTestType.  On completion of the test, the agent sets
              ifTestStatus to 'notInUse'.  Once this occurs, the
              manager can retrieve the results.  In the (rare) event
              that the invocation of tests by two network managers
              were to overlap, then there would be a possibility that
              the first test's results might be overwritten by the
              second test's results prior to the first results being
              read.  This unlikely circumstance can be detected by a
              network manager retrieving ifTestId at the same time as
              retrieving the test results, and ensuring that the
              results are for the desired request.

              If ifTestType is not set within an abnormally long
              period of time after ownership is obtained, the agent
              should time-out the manager, and reset the value of the
              ifTestStatus object back to 'notInUse'.  It is
              suggested that this time-out period be 5 minutes.

              In general, a management station must not retransmit a
              request to invoke a test for which it does not receive
              a response; instead, it properly inspects an agent's
              MIB to determine if the invocation was successful.
              Only if the invocation was unsuccessful, is the
              invocation request retransmitted.

              Some tests may require the interface to be taken off-
              line in order to execute them, or may even require the
              agent to reboot after completion of the test.  In these
              circumstances, communication with the management
              station invoking the test may be lost until after
              completion of the test.  An agent is not required to
              support such tests.  However, if such tests are
              supported, then the agent should make every effort to
              transmit a response to the request which invoked the
              test prior to losing communication.  When the agent is
              restored to normal service, the results of the test are
              properly made available in the appropriate objects.
              Note that this requires that the ifIndex value assigned
              to an interface must be unchanged even if the test
              causes a reboot.  An agent must reject any test for
              which it cannot, perhaps due to resource constraints,
              make available at least the minimum amount of
              information after that test completes."
       ::= { ifMIBObjects 3 }

   ifTestEntry OBJECT-TYPE
       SYNTAX       IfTestEntry
       MAX-ACCESS   not-accessible
       STATUS       current
       DESCRIPTION
               "An entry containing objects for invoking tests on an
               interface."
       AUGMENTS  { ifEntry }
       ::= { ifTestTable 1 }

   IfTestEntry ::=
       SEQUENCE {
           ifTestId           TestAndIncr,
           ifTestStatus       INTEGER,
           ifTestType         AutonomousType,
           ifTestResult       INTEGER,
           ifTestCode         OBJECT IDENTIFIER,
           ifTestOwner        OwnerString
       }

   ifTestId         OBJECT-TYPE
       SYNTAX       TestAndIncr
       MAX-ACCESS   read-write
       STATUS       current
       DESCRIPTION
               "This object identifies the current invocation of the
               interface's test."
       ::= { ifTestEntry 1 }

   ifTestStatus     OBJECT-TYPE
       SYNTAX       INTEGER { notInUse(1), inUse(2) }
       MAX-ACCESS   read-write
       STATUS       current
       DESCRIPTION
               "This object indicates whether or not some manager
               currently has the necessary 'ownership' required to
               invoke a test on this interface.  A write to this
               object is only successful when it changes its value
               from 'notInUse(1)' to 'inUse(2)'.  After completion of
               a test, the agent resets the value back to
               'notInUse(1)'."
       ::= { ifTestEntry 2 }

   ifTestType       OBJECT-TYPE
       SYNTAX       AutonomousType
       MAX-ACCESS   read-write
       STATUS       current
       DESCRIPTION
               "A control variable used to start and stop operator-
               initiated interface tests.  Most OBJECT IDENTIFIER
               values assigned to tests are defined elsewhere, in
               association with specific types of interface.
               However, this document assigns a value for a full-
               duplex loopback test, and defines the special meanings
               of the subject identifier:

                   noTest  OBJECT IDENTIFIER ::= { 0 0 }

               When the value noTest is written to this object, no
               action is taken unless a test is in progress, in which
               case the test is aborted.  Writing any other value to
               this object is only valid when no test is currently in
               progress, in which case the indicated test is
               initiated.

               When read, this object always returns the most recent
               value that ifTestType was set to.  If it has not been
               set since the last initialization of the network
               management subsystem on the agent, a value of noTest
               is returned."
       ::= { ifTestEntry 3 }

   ifTestResult  OBJECT-TYPE
       SYNTAX       INTEGER {
                        none(1),          -- no test yet requested
                        success(2),
                        inProgress(3),
                        notSupported(4),
                        unAbleToRun(5),   -- due to state of system
                        aborted(6),
                        failed(7)
                    }
       MAX-ACCESS   read-only
       STATUS       current
       DESCRIPTION
               "This object contains the result of the most recently
               requested test, or the value none(1) if no tests have
               been requested since the last reset.  Note that this
               facility provides no provision for saving the results
               of one test when starting another, as could be
               required if used by multiple managers concurrently."
       ::= { ifTestEntry 4 }

   ifTestCode  OBJECT-TYPE
       SYNTAX       OBJECT IDENTIFIER
       MAX-ACCESS   read-only
       STATUS       current
       DESCRIPTION
               "This object contains a code which contains more
               specific information on the test result, for example
               an error-code after a failed test.  Error codes and
               other values this object may take are specific to the
               type of interface and/or test.  The value may have the
               semantics of either the AutonomousType or
               InstancePointer textual conventions as defined in RFC
               1443.  The identifier:

                   testCodeUnknown  OBJECT IDENTIFIER ::= { 0 0 }

               is defined for use if no additional result code is
               available."
       ::= { ifTestEntry 5 }

   ifTestOwner      OBJECT-TYPE
       SYNTAX       OwnerString
       MAX-ACCESS   read-write
       STATUS       current
       DESCRIPTION
               "The entity which currently has the 'ownership'
               required to invoke a test on this interface."
       ::= { ifTestEntry 6 }


   --   Generic Receive Address Table
   --
   -- This group of objects is mandatory for all types of
   -- interfaces which can receive packets/frames addressed to
   -- more than one address.
   --
   -- This table replaces the ifExtnsRcvAddr table.  The main
   -- difference is that this table makes use of the RowStatus
   -- textual convention, while ifExtnsRcvAddr did not.

   ifRcvAddressTable  OBJECT-TYPE
       SYNTAX      SEQUENCE OF IfRcvAddressEntry
       MAX-ACCESS  not-accessible
       STATUS      current
       DESCRIPTION
               "This table contains an entry for each address
               (broadcast, multicast, or uni-cast) for which the
               system will receive packets/frames on a particular
               interface, except as follows:

               - for an interface operating in promiscuous mode,
               entries are only required for those addresses for
               which the system would receive frames were it not
               operating in promiscuous mode.

               - for 802.5 functional addresses, only one entry is
               required, for the address which has the functional
               address bit ANDed with the bit mask of all functional
               addresses for which the interface will accept frames."
       ::= { ifMIBObjects 4 }

   ifRcvAddressEntry  OBJECT-TYPE
       SYNTAX      IfRcvAddressEntry
       MAX-ACCESS  not-accessible
       STATUS      current
       DESCRIPTION
               "A list of objects identifying an address for which
               the system will accept packets/frames on the
               particular interface identified by the index value
               ifIndex."
       INDEX  { ifIndex, ifRcvAddressAddress }
       ::= { ifRcvAddressTable 1 }

   IfRcvAddressEntry ::=
       SEQUENCE {
           ifRcvAddressAddress   PhysAddress,
           ifRcvAddressStatus    RowStatus,
           ifRcvAddressType      INTEGER
       }

   ifRcvAddressAddress OBJECT-TYPE
       SYNTAX      PhysAddress
       MAX-ACCESS  read-create
       STATUS      current
       DESCRIPTION
               "An address for which the system will accept
               packets/frames on this entry's interface."
       ::= { ifRcvAddressEntry 1 }

   ifRcvAddressStatus OBJECT-TYPE
       SYNTAX      RowStatus
       MAX-ACCESS  read-write
       STATUS      current
       DESCRIPTION
               "This object is used to create and delete rows in the
               ifRcvAddressTable."

       ::= { ifRcvAddressEntry 2 }

   ifRcvAddressType OBJECT-TYPE
       SYNTAX      INTEGER {
                       other(1),
                       volatile(2),
                       nonVolatile(3)
                   }

       MAX-ACCESS  read-create
       STATUS      current
       DESCRIPTION
               "This object has the value nonVolatile(3) for those
               entries in the table which are valid and will not be
               deleted by the next restart of the managed system.
               Entries having the value volatile(2) are valid and
               exist, but have not been saved, so that will not exist
               after the next restart of the managed system.  Entries
               having the value other(1) are valid and exist but are
               not classified as to whether they will continue to
               exist after the next restart."

       DEFVAL  { volatile }

       ::= { ifRcvAddressEntry 3 }


   -- conformance information

   ifConformance OBJECT IDENTIFIER ::= { ifMIB 2 }

   ifGroups      OBJECT IDENTIFIER ::= { ifConformance 1 }
   ifCompliances OBJECT IDENTIFIER ::= { ifConformance 2 }


   -- compliance statements

   ifCompliance MODULE-COMPLIANCE
       STATUS  current
       DESCRIPTION
               "The compliance statement for SNMPv2 entities which
               have network interfaces."

       MODULE  -- this module
           MANDATORY-GROUPS { ifGeneralGroup, ifStackGroup }

           GROUP       ifFixedLengthGroup
           DESCRIPTION
               "This group is mandatory for all network interfaces
               which are character-oriented or transmit data in
               fixed-length transmission units."

           GROUP       ifHCFixedLengthGroup
           DESCRIPTION
               "This group is mandatory only for those network
               interfaces which are character-oriented or transmit
               data in fixed-length transmission units, and for which
               the value of the corresponding instance of ifSpeed is
               greater than 20,000,000 bits/second."

           GROUP       ifPacketGroup
           DESCRIPTION
               "This group is mandatory for all network interfaces
               which are packet-oriented."

           GROUP       ifHCPacketGroup
           DESCRIPTION
               "This group is mandatory only for those network
               interfaces which are packet-oriented and for which the
               value of the corresponding instance of ifSpeed is
               greater than 650,000,000 bits/second."
           GROUP       ifTestGroup
           DESCRIPTION
               "This group is optional.  Media-specific MIBs which
               require interface tests are strongly encouraged to use
               this group for invoking tests and reporting results.
               A medium specific MIB which has mandatory tests may
               make implementation of this group mandatory."

           GROUP       ifRcvAddressGroup
           DESCRIPTION
               "The applicability of this group MUST be defined by
               the media-specific MIBs.  Media-specific MIBs must
               define the exact meaning, use, and semantics of the
               addresses in this group."

           OBJECT      ifLinkUpDownTrapEnable
           MIN-ACCESS  read-only
           DESCRIPTION
               "Write access is not required."

           OBJECT      ifPromiscuousMode
           MIN-ACCESS  read-only
           DESCRIPTION
               "Write access is not required."

           OBJECT      ifStackStatus
           SYNTAX      INTEGER { active(1) } -- subset of RowStatus
           MIN-ACCESS  read-only
           DESCRIPTION
               "Write access is not required, and only one of the six
               enumerated values for the RowStatus textual convention
               need be supported, specifically: active(1)."

           OBJECT       ifAdminStatus
           SYNTAX       INTEGER { up(1), down(2) }
           MIN-ACCESS   read-only
           DESCRIPTION
               "Write access is not required, nor is support for the
               value testing(3)."
       ::= { ifCompliances 1 }


   -- units of conformance

   ifGeneralGroup    OBJECT-GROUP
       OBJECTS { ifDescr, ifType, ifSpeed, ifPhysAddress,
                 ifAdminStatus, ifOperStatus, ifLastChange,
                 ifLinkUpDownTrapEnable, ifConnectorPresent,
                 ifHighSpeed, ifName }
       STATUS  current
       DESCRIPTION
               "A collection of objects providing information
               applicable to all network interfaces."
       ::= { ifGroups 1 }

   -- the following five groups are mutually exclusive; at most
   -- one of these groups is implemented for any interface

   ifFixedLengthGroup    OBJECT-GROUP
       OBJECTS { ifInOctets, ifOutOctets, ifInUnknownProtos,
                 ifInErrors, ifOutErrors }
       STATUS  current
       DESCRIPTION
               "A collection of objects providing information
               specific to non-high speed, character-oriented or
               fixed-length-transmission network interfaces.  (Non-
               high speed interfaces transmit and receive at speeds
               less than or equal to 20,000,000 bits/second.)"
       ::= { ifGroups 2 }

   ifHCFixedLengthGroup    OBJECT-GROUP
       OBJECTS { ifHCInOctets, ifHCOutOctets,
                 ifInOctets, ifOutOctets, ifInUnknownProtos,
                 ifInErrors, ifOutErrors }
       STATUS  current
       DESCRIPTION
               "A collection of objects providing information
               specific to high speed (greater than 20,000,000
               bits/second) character-oriented or fixed-length-
               transmission network interfaces."
       ::= { ifGroups 3 }

   ifPacketGroup    OBJECT-GROUP
       OBJECTS { ifInOctets, ifOutOctets, ifInUnknownProtos,
                 ifInErrors, ifOutErrors,
                 ifMtu, ifInUcastPkts, ifInMulticastPkts,
                 ifInBroadcastPkts, ifInDiscards,
                 ifOutUcastPkts, ifOutMulticastPkts,
                 ifOutBroadcastPkts, ifOutDiscards,
                 ifPromiscuousMode }
       STATUS  current
       DESCRIPTION
               "A collection of objects providing information
               specific to non-high speed, packet-oriented network
               interfaces.  (Non-high speed interfaces transmit and
               receive at speeds less than or equal to 20,000,000
               bits/second.)"
       ::= { ifGroups 4 }

   ifHCPacketGroup    OBJECT-GROUP
       OBJECTS { ifHCInOctets, ifHCOutOctets,
                 ifInOctets, ifOutOctets, ifInUnknownProtos,
                 ifInErrors, ifOutErrors,
                 ifMtu, ifInUcastPkts, ifInMulticastPkts,
                 ifInBroadcastPkts, ifInDiscards,
                 ifOutUcastPkts, ifOutMulticastPkts,
                 ifOutBroadcastPkts, ifOutDiscards,
                 ifPromiscuousMode }
       STATUS  current
       DESCRIPTION
               "A collection of objects providing information
               specific to high speed (greater than 20,000,000
               bits/second but less than or equal to 650,000,000
               bits/second) packet-oriented network interfaces."
       ::= { ifGroups 5 }

   ifVHCPacketGroup    OBJECT-GROUP
       OBJECTS { ifHCInUcastPkts, ifHCInMulticastPkts,
                 ifHCInBroadcastPkts, ifHCOutUcastPkts,
                 ifHCOutMulticastPkts, ifHCOutBroadcastPkts,
                 ifHCInOctets, ifHCOutOctets,
                 ifInOctets, ifOutOctets, ifInUnknownProtos,
                 ifInErrors, ifOutErrors,
                 ifMtu, ifInUcastPkts, ifInMulticastPkts,
                 ifInBroadcastPkts, ifInDiscards,
                 ifOutUcastPkts, ifOutMulticastPkts,
                 ifOutBroadcastPkts, ifOutDiscards,
                 ifPromiscuousMode }
       STATUS  current
       DESCRIPTION
               "A collection of objects providing information
               specific to higher speed (greater than 650,000,000
               bits/second) packet-oriented network interfaces."
       ::= { ifGroups 6 }

   ifRcvAddressGroup    OBJECT-GROUP
       OBJECTS { ifRcvAddressStatus, ifRcvAddressType }
       STATUS  current
       DESCRIPTION
               "A collection of objects providing information on the
               multiple addresses which an interface receives."
       ::= { ifGroups 7 }

   ifTestGroup    OBJECT-GROUP
       OBJECTS { ifTestId, ifTestStatus, ifTestType,
                 ifTestResult, ifTestCode, ifTestOwner }
       STATUS  current
       DESCRIPTION
               "A collection of objects providing the ability to
               invoke tests on an interface."
       ::= { ifGroups 8 }

   ifStackGroup    OBJECT-GROUP
       OBJECTS { ifStackStatus }
       STATUS  current
       DESCRIPTION
               "A collection of objects providing information on the
               layering of MIB-II interfaces."
       ::= { ifGroups 9 }

   END
--
--	usr_dialout.mib - The USR Dial-out MIB module
--
--
-- Author:         Peter Dobransky
--
-- $Id: usr_dialout.mib,v 1.6.8.2 1998/01/06 14:26:03 psd Exp $
--
--  | Copyright (c) 1996 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-DIALOUT-MIB DEFINITIONS ::= BEGIN

     IMPORTS
          IpAddress
                  FROM RFC1155-SMI
          OBJECT-TYPE
                  FROM RFC-1212
          DisplayString, usrDialout, UsrConfigStatus
                  FROM USR-DEFINITIONS-MIB;


-- textual conventions
-- 
-- textual conventions are like pre-processor macro in 'C'
--        (i.e. #define statements)
-- Use them to define your own 'datatypes'

-- memory size, expressed in units of 1024bytes


usrDialoutConfigFileName OBJECT-TYPE
     SYNTAX DisplayString
     ACCESS read-write
     STATUS mandatory
     DESCRIPTION
       "The name of a ConfigFile to read/write permanent database
        records. If the value of this object is an empty string,
        then the Dial-out process uses the default name
        `@file://DialOutProcess.cfg'."
::= { usrDialout 1 }

usrDialoutCFMStatusFlag  OBJECT-TYPE
     SYNTAX UsrConfigStatus
     ACCESS read-write
     STATUS mandatory
     DESCRIPTION
       "Setting the value of this object to `save' causes the values
        of the Dial-out Group to be written out to the current config
        file, which is stored in the usrDialoutConfigFileName object.
        While the new ConfigFile is being written, the Dial-out process
        will set the value of this flag to `saving''. Any
        attempts to set the value while it is not `normal'
        (i.e. the file is currently being written to the
        ConfigFile) while result in a badValue error being
        returned. Setting the value to `normal' will result in no
        action."
::= { usrDialout 2 }

usrDialoutSecurity OBJECT-TYPE
	SYNTAX      INTEGER {
                    no(1),
                    yes(2)
                    }
	ACCESS      read-write
	STATUS      mandatory
	DESCRIPTION
       "Setting the value of this object to yes(2) will instruct the
        Dial-out process to authenticate all network users who attempt to
        connect to a virtual port. Setting the value of this object to
        no(1) will instruct the Dial-out process to bypass the user
        authentication process."
     DEFVAL { yes }
     --CONFIGURABLE
::= { usrDialout 3 }

usrDialoutWorkstationTimeout OBJECT-TYPE
	SYNTAX      INTEGER (0..180)
	ACCESS      read-write
	STATUS      mandatory
	DESCRIPTION
       "Even when it appears there is no activity on a connected virtual
        port, the client and server are still actively sending and
        receiving messages. If the client is re-booted, or if the client
        experiences a system error that interrupts this activity, the
        server will wait a certain amount of time before terminating the
        connection. Depending on what caused the interruption, this
        period of time may allow the client to restore the connection.
        This time-out value is specified in minutes. The default is 5
        minutes. To disable workstation time-out, set this object to 0."
     DEFVAL { 5 }
     --CONFIGURABLE
::= { usrDialout 4 }

usrDialoutUserTimeout OBJECT-TYPE
	SYNTAX      INTEGER (0..180)
	ACCESS      read-write
	STATUS      mandatory
	DESCRIPTION
       "The User time-out is provided so that a virtual port will be
        freed for use by others when the current user is not actively
        using the virtual port. If the server does not receive any
        transmit data requests from the client for the period of the
        time-out, the session is disconnected. The time-out value is
        specified in minutes. The default is 5 minutes. To disable
        user time-out, set this object to 0."
     DEFVAL { 5 }
     --CONFIGURABLE
::= { usrDialout 5 }

usrDialoutPortTable OBJECT-TYPE
     SYNTAX     SEQUENCE OF UsrDialoutPortEntry
     ACCESS     not-accessible
     STATUS     mandatory
     DESCRIPTION
       "A list of virtual ports available for dial-out."
::= { usrDialout 6 }

usrDialoutPortEntry OBJECT-TYPE
     SYNTAX      UsrDialoutPortEntry
     ACCESS      not-accessible
     STATUS      mandatory
     DESCRIPTION
       "An entry containing management information applicable to a
        particular virtual port."
     INDEX { usrDialoutPortNumber }
::= { usrDialoutPortTable 1}

UsrDialoutPortEntry ::=
     SEQUENCE {
          usrDialoutPortNumber INTEGER,
          usrDialoutPortGeneralName DisplayString,
          usrDialoutPortSpecificName DisplayString,
          usrDialoutPortState INTEGER,
          usrDialoutPortClientType INTEGER,
          usrDialoutPortIpxClientAddress OCTET STRING,
          usrDialoutPortIpClientAddress IpAddress
          }

usrDialoutPortNumber OBJECT-TYPE
	SYNTAX      INTEGER
	ACCESS      not-accessible
	STATUS      mandatory
	DESCRIPTION
       "The virtual port number of the dial-out port."
::= { usrDialoutPortEntry 1}

usrDialoutPortGeneralName OBJECT-TYPE
	SYNTAX      DisplayString (SIZE(8))
	ACCESS      read-only
	STATUS      mandatory
	DESCRIPTION
       "The general service name associated with a virtual port. When a
        network user requires access to a type of service, rather than a
        specific port, the user is able to request a service by its
        general name. This provides network users access to the
        communication server ports without requiring the user to know
        the specific name or location of a port."
::= { usrDialoutPortEntry 2}

usrDialoutPortSpecificName OBJECT-TYPE
	SYNTAX      DisplayString (SIZE(14))
	ACCESS      read-only
	STATUS      mandatory
	DESCRIPTION
       "The specific name associated with a virtual port. This allows a
        network user to locate a particular port for access to a specific
        service associated with that port."
::= { usrDialoutPortEntry 3}

usrDialoutPortState OBJECT-TYPE
	SYNTAX      INTEGER {
                    available(1),
                    unavailable(2),
                    in-use(3),
                    disconnect(4)
                    }
	ACCESS      read-write
	STATUS      mandatory
	DESCRIPTION
       "The state of the virtual port. When a port is in the available(1)
        state, it is available to a network user. When a port is in the
        unavailable(2) state, it is not available to a network user. When
        a port is in the in-use(3) state, it is currently in use by a
        network user. Setting this object to disconnect(4) will cause a
        supervisory disconnect of the current user. Setting this object
        to any other value will have no effect."
::= { usrDialoutPortEntry 4}

usrDialoutPortClientType OBJECT-TYPE
	SYNTAX      INTEGER {
                    none(0),
                    ip(1),
                    ipx(2)
                    }
	ACCESS      read-only
	STATUS      mandatory
	DESCRIPTION
       "The type of client that is attached to this port. This object
        is set to none(0) if no client is attached to the port."
::= { usrDialoutPortEntry 5}

usrDialoutPortIpxClientAddress OBJECT-TYPE
	SYNTAX      OCTET STRING (SIZE(6))
	ACCESS      read-only
	STATUS      mandatory
	DESCRIPTION
       "The Ethernet address of the IPX client workstation attached
        to the port. If no client is attached to the port or an IP
        client is attached to the port, this object is set to all
        zeros."
::= { usrDialoutPortEntry 6}

usrDialoutPortIpClientAddress OBJECT-TYPE
	SYNTAX      IpAddress
	ACCESS      read-only
	STATUS      mandatory
	DESCRIPTION
       "The IP address of the IP client workstation attached to
        the port. If no client is attached to the port or an IPX
        client is attached to the port, this object is set to all
        zeros."
::= { usrDialoutPortEntry 7}

END         -- End usr Dial-out MIB definitions

--
-- For the revision history to work correctly, after a new MIB file has been
-- added to the CVS repository the first time the CVS Admin person needs to
-- set the correct comment string delimter for the file.
--
-- $Log: usr_dialout.mib,v $
-- Revision 1.6.8.2  1998/01/06 14:26:03  psd
-- Added DEFVAL clauses.
--
--Revision 1.6.8.1  1997/09/17  19:06:28  psd
--Merged 2.0 to 3.0
--
--Revision 1.6.14.1  1997/09/05  15:09:30  psd
--Changes to MIBs so that they compile using the SimpleTester.
--
--Revision 1.6  1996/09/25  19:13:21  psd
--Changed usrDialoutSecurity values.
--
-- Revision 1.5  1996/09/25 18:26:21  psd
-- Made 3 port table objects global.
--
-- Revision 1.4  1996/09/23 14:11:42  psd
-- Add client type/address objects.
--
-- Revision 1.3  1996/09/03 16:18:21  psd
-- Enhanced MIB support.
--
-- Revision 1.2  1996/07/12 19:57:49  psd
-- New MIB format.
--
-- Revision 1.1  1996/07/09 18:46:27  psd
-- Initial draft of the Dial-out MIB.
--
--
--
--
-- Local Variables:
-- tab-width:5
-- tab-stop-list:( 5 10 15 20 25 30 35 40 45 50 55 60 65 70 75 80)
-- End:
--
--
--	usr_cli.mib
--
--
-- Author:         Clarise Patton
--
-- $Id: usr_cli.mib,v 1.3.8.2 1998/06/10 22:12:34 eshaji Exp $
--
--  | Copyright (c) 1996 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-CLI-MIB DEFINITIONS ::= BEGIN

	IMPORTS
          OBJECT-TYPE
                  FROM RFC-1212
          DisplayString, UsrConfigStatus, usrCli
                  FROM USR-DEFINITIONS-MIB;


   -- textual conventions

   -- Begin managed object definitions here...

usrCliVersion OBJECT-TYPE
	SYNTAX		DisplayString
	ACCESS		read-only
	STATUS		obsolete
	DESCRIPTION
		"The current software version of the Command Line Interpreter
	       process.."
::= { usrCli 1 }

usrCliConfigFileName OBJECT-TYPE
	SYNTAX		DisplayString
	ACCESS		read-only
	STATUS		mandatory
	DESCRIPTION		
		  "The name of a ConfigFile to read/write permanent database
                   records."
	::= { usrCli 2 }

usrCliCFMStatusFlag OBJECT-TYPE
	SYNTAX		UsrConfigStatus
	ACCESS		read-write
	STATUS		mandatory
	DESCRIPTION
		"This variable controls saving and loading of configuration
           information for the CLI process. The value can 
           be set to either save or load by a management station. The other
           values indicate if any configuration operation and what type
           is in progress."
::= { usrCli 3 }

usrCliHistoryDepth OBJECT-TYPE
     SYNTAX   INTEGER
     ACCESS   read-write
     STATUS   mandatory
     DESCRIPTION
            "The number of commands to be held in the History Array."
	--CONFIGURABLE
::= { usrCli 4 }

usrCliPrompt OBJECT-TYPE
     SYNTAX   DisplayString
     ACCESS   read-write
     STATUS   mandatory
     DESCRIPTION
            "The specific prompt to be used for this CLI."
	--CONFIGURABLE
::= { usrCli 5 }


usrCliConsoleLogin OBJECT-TYPE
     SYNTAX   INTEGER {no(1),yes(2) }
     ACCESS   read-write
     STATUS   mandatory
     DESCRIPTION
            "Whether the Console user will be required to log in.
		This defaults to Enabled and can only be changed by
		a priviledged user."
	--CONFIGURABLE
::= { usrCli 6 }

usrCliConsoleIdleTimeout OBJECT-TYPE
     SYNTAX   INTEGER (0..60)
     ACCESS   read-write
     STATUS   mandatory
     DESCRIPTION
            "If Console user is required to log in, there will be
		an idle timeout specified in minutes.  
		This will default to 5 minutes.
		There is a max of 60 minutes.  
		If this is set to 0, there will be no timeout. 
		This can only be modified by a priviledged user."
	--CONFIGURABLE
::= { usrCli 7 }

usrCliGlobalPageBreak OBJECT-TYPE
     SYNTAX   INTEGER
     ACCESS   read-write
     STATUS   mandatory
     DESCRIPTION
        "This is a flag which says whether global page break is enabled/disabled "
    --CONFIGURABLE
::= { usrCli 8 }
 
usrCliGlobalPageSize OBJECT-TYPE
     SYNTAX   INTEGER
     ACCESS   read-write
     STATUS   mandatory
     DESCRIPTION
        " This is a flag which says whether local page break is enabled/disabled "
    --CONFIGURABLE
::= { usrCli 9 }


END         -- End CLI MIB definitions

--
--
-- $Log: usr_cli.mib,v $
-- Revision 1.3.8.2  1998/06/10 22:12:34  eshaji
-- Sprint page-break support
--
-- Revision 1.3.8.1  1997/09/17 19:06:25  psd
-- Merged 2.0 to 3.0
--
--Revision 1.4  1997/07/15  19:34:48  drema
--Fixed bug #1712 by changing usrCliVersion's status to obsolete
--
-- Revision 1.3  1996/10/18  18:26:20  patton
-- added console login entries
--
-- Revision 1.2  1996/09/18 21:44:40  jhalpin
-- Merge in LANLinker branch changes <sawdust city here I come..>
--
-- Revision 1.1.2.1  1996/09/12 18:32:03  jhalpin
-- Fix Filter protocol bits, build usr_cli.mib into usr_netserver.mib, remove unneeded definitions from usr_definitions.mib
--
-- Revision 1.1  1996/05/20 14:06:20  patton
-- added the CLI MIB
--
-- End:
--
--
--	usr_adsl.mib - ADSL Driver MIB
--
--
-- Author:         Jim Halpin
--
-- $Id: usr_adsl.mib,v 1.3 1997/02/28 20:16:02 jhalpin Exp $
--
--  | Copyright (c) 1995-1997 U.S. Robotics Access Corp., Skokie, IL 60076 |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

Template-MIB DEFINITIONS ::= BEGIN

	IMPORTS
	     Counter
                  FROM RFC1155-SMI
          OBJECT-TYPE
                  FROM RFC-1212
          DisplayString, usrAdsl, UsrConfigStatus
                  FROM USR-DEFINITIONS-MIB;


   -- textual conventions
   -- 
   -- textual conventions are like pre-processor macro in 'C'
   --        (i.e. #define statements)
   -- Use them to define your own 'datatypes'


   -- Begin managed object definitions here...

	usrAdslXmitPower OBJECT-TYPE
         SYNTAX   INTEGER(-15..-3)
         ACCESS   read-only
         STATUS   mandatory
         DESCRIPTION
            "Transmit power of ADSL transceiver represented in dB."
         ::= { usrAdsl 1 }

	usrAdslRmtReqDwnConstStatus OBJECT-TYPE
         SYNTAX   INTEGER (0..128)
         ACCESS   read-write
         STATUS   mandatory
         DESCRIPTION
            	"Value corresponds to the downstream constellation
                 requested."
         ::= { usrAdsl 2 }

	usrAdslActualDwnConstStatus OBJECT-TYPE
         SYNTAX   INTEGER (0..128)
         ACCESS   read-only
         STATUS   mandatory
         DESCRIPTION
            	"Value corresponds to the actual downstream constellation
                 that was used, which may differ from the value requested."
         ::= { usrAdsl 3 }

	usrAdslRmtReqUpConstStatus OBJECT-TYPE
         SYNTAX   INTEGER (0..128)
         ACCESS   read-only
         STATUS   mandatory
         DESCRIPTION
            "Value corresponds to the upstream constellation requested."
         ::= { usrAdsl 4 }

	usrAdslActualUpConstStatus OBJECT-TYPE
         SYNTAX   INTEGER (0..128)
         ACCESS   read-only
         STATUS   mandatory
         DESCRIPTION
            "Value corresponds to the actual upstream constellation that
             was used, which may differ from the value requested."
         ::= { usrAdsl 5 }


	usrAdslFwRel OBJECT-TYPE
         SYNTAX   INTEGER (0..16777215)
         ACCESS   read-only
         STATUS   mandatory
         DESCRIPTION
            "Firmware release number of the GTI supplied transceiver
             software module."
         ::= { usrAdsl 6 }

	usrAdslStartletVerson OBJECT-TYPE
         SYNTAX   INTEGER (0..4)
         ACCESS   read-only
         STATUS   mandatory
         DESCRIPTION
            "Value is a number that corresponds to the version number of
             the STARLET VLSI in the transceiver."
         ::= { usrAdsl 7 }

	usrAdslMeanSqError OBJECT-TYPE
         SYNTAX   INTEGER {
                           minus50db(1),
                           plus50db(2)
                          }
         ACCESS   read-only
         STATUS   mandatory
         DESCRIPTION
            "Received signal to noise ratio."
         ::= { usrAdsl 8 }

	usrAdslEqualization OBJECT-TYPE
         SYNTAX   INTEGER  -- Range values are TBD
         ACCESS   read-only -- TBD
         STATUS   mandatory
         DESCRIPTION
            "TBD"
         ::= { usrAdsl 9 }

	usrAdslReceiverGain OBJECT-TYPE
         SYNTAX   INTEGER -- Range values are TBD
         ACCESS   read-write
         STATUS   mandatory
         DESCRIPTION
            "Total receiver gain measured in dB."
         ::= { usrAdsl 10 }


	usrAdslBytesErrCorrected OBJECT-TYPE
         SYNTAX   INTEGER (0..255)
         ACCESS   read-only
         STATUS   mandatory
         DESCRIPTION
            "Number of bytes corrected by Reed-Solomon error correction
             algorithm in the STARLET."
         ::= { usrAdsl 11 }

	usrAdslBytesNotErrCorrected OBJECT-TYPE
         SYNTAX   INTEGER (0..255)
         ACCESS   read-only
         STATUS   mandatory
         DESCRIPTION
            "Number of bytes not corrected by Reed-Solomon error correction
             algorithm in the STARLET."
         ::= { usrAdsl 12 }

	usrAdslOverflowCounter OBJECT-TYPE
         SYNTAX   Counter
         ACCESS   read-only
         STATUS   mandatory
         DESCRIPTION
            "Running counter for when usrAdslBytesErrorCorrected or 
             usrAdslBytesNotErrorCorrected overflows"
         ::= { usrAdsl 13 }


	usrAdslOpState OBJECT-TYPE
         SYNTAX   INTEGER (0..134)
         ACCESS   read-only
         STATUS   mandatory
         DESCRIPTION
            "Defines the high level operating state of the transceiver.
             Used by the customer to determine whether the transceiver
             is in idle mode, data mode, test mode, or startup."
         ::= { usrAdsl 14 }

	usrAdslStartupProgress OBJECT-TYPE
         SYNTAX   INTEGER (0..191)
         ACCESS   read-only
         STATUS   mandatory
         DESCRIPTION
            "Defines the current detailed startup state of the
             transceiver.  The LSB determines the major mode
             corresponding to startup in var usrAdslOpState."
         ::= { usrAdsl 15 }


	usrAdslLastFailedStatus OBJECT-TYPE
         SYNTAX   INTEGER (0..191)
         ACCESS   read-only
         STATUS   mandatory
         DESCRIPTION
            "Defines the last detailed state reached in
             usrAdslStartupProgress before startup failed."
         ::= { usrAdsl 16 }


	usrAdslActualBaudDataRateDwn OBJECT-TYPE
         SYNTAX   INTEGER (340..952)
         ACCESS   read-only
         STATUS   mandatory
         DESCRIPTION
            "Actual downstream rate of kilobytes per second."
         ::= { usrAdsl 17 }

	usrAdslActualBaudDataRateDwnMar OBJECT-TYPE
         SYNTAX   INTEGER -- Range values are TBD
         ACCESS   read-only
         STATUS   mandatory
         DESCRIPTION
            "TBD"
         ::= { usrAdsl 18 }


	usrAdslActualBaudDataRateUp OBJECT-TYPE
         SYNTAX   INTEGER
         ACCESS   read-only
         STATUS   mandatory
         DESCRIPTION
            "Actual upstream rate of kilobytes per second."
         ::= { usrAdsl 19 }


	usrAdslActualBaudDataRateUpMarg OBJECT-TYPE
         SYNTAX   INTEGER -- Range values are TBD
         ACCESS   read-only
         STATUS   mandatory
         DESCRIPTION
            "TBD"
         ::= { usrAdsl 20 }

        usrAdslCFMStatusFlag OBJECT-TYPE
         SYNTAX  UsrConfigStatus
         ACCESS  read-write
         STATUS  mandatory
         DESCRIPTION
                "This variable controls saving and loading of configuration
                information for the D56k WAN Driver. The value can be set
                to either save or load by a management station. The other
                values indicate if any configuration operation and what type
                is in progress."
         ::= { usrAdsl 21 }

        usrAdslCfgFileName OBJECT-TYPE
         SYNTAX  DisplayString
         ACCESS  read-only
         STATUS  mandatory
         DESCRIPTION
                "The name of a ConfigFile to read/write the D56k parameters.
                 If the value of this object is an empty string, then the
                 D56k Driver uses the default name `@file://D56k.cfg'."
         ::= { usrAdsl 22 }

        usrAdslResetStatus OBJECT-TYPE
         SYNTAX   INTEGER
         ACCESS   read-write
         STATUS   mandatory
         DESCRIPTION
            "The Reset Status of the ADSL Starlet chipset"
         ::= { usrAdsl 23 }


END         -- End usrAdsl MIB definitions

--
-- For the revision history to work correctly, after a new MIB file has been
-- added to the CVS repository the first time the CVS Admin person needs to
-- set the correct comment string delimter for the file.
--
-- $Log: usr_adsl.mib,v $
-- Revision 1.3  1997/02/28 20:16:02  jhalpin
-- Add new object
--
-- Revision 1.2  1997/01/23 17:02:33  jhalpin
-- Remove unused datatype imports
--
-- Revision 1.1  1997/01/23 16:58:07  jhalpin
-- Add new ADSL MIB module
--
--
--
-- Local Variables:
-- tab-width:5
-- tab-stop-list:( 5 10 15 20 25 30 35 40 45 50 55 60 65 70 75 80)
-- End:
--
--
--      usr_ntp.mib - A proprietary Network Time Protocol MIB
--
--
-- Author:         ??? maintained by Reuben Sivan
-- Created:        Feb-24-1997
--
--
--
--  | Copyright (c) 1997 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--


USR-NTP-MIB DEFINITIONS ::= BEGIN

        IMPORTS
          OBJECT-TYPE,
          MODULE-IDENTITY,
          Integer32,
          Counter32,
          IpAddress
                FROM SNMPv2-SMI
          TruthValue,
          DisplayString
                FROM SNMPv2-TC
          MODULE-COMPLIANCE,
          OBJECT-GROUP
                FROM SNMPv2-CONF
          common,
          UsrConfigStatus
                FROM USR-DEFINITIONS-MIB;

usrNTPMib MODULE-IDENTITY
    LAST-UPDATED        "9704282000Z"
    ORGANIZATION        "U.S. Robotics"
    CONTACT-INFO        ""
    DESCRIPTION
     "This MIB Module defines the USRobotics private interface
      to the Simple Network Time Protocol client process.
      The process can be configured with up to two alternate servers,
      a primary server and a secondary server. The primary server is
      always contacted first, the secondary server is contacted after
      all retransmissions to the primary failed have failed.
      The implementation is based on RFC 2030, using unicast mode
      only.
      Note that all the writable objects include a 'DEFVAL'
      clause. The clause is intended to be used as a reference only,
      in case an agent has no previously saved configuration.
      Typically, at start-up, an agent will load data saved from a
      previous session - thus 'DEFVAL' is used mainly for new
      systems."
    ::= { common 34 }

usrNTPObjects OBJECT IDENTIFIER ::= { usrNTPMib 1 }
usrNTPTraps   OBJECT IDENTIFIER ::= { usrNTPMib 3 }


-- Begin managed object definitions here...

usrNTPPrimaryServer OBJECT-TYPE
    SYNTAX      DisplayString (SIZE (0..132))
    MAX-ACCESS  read-write
    STATUS      current
    DESCRIPTION
     "The IP address or host name of the primary NTP server that the
      module will query for time synchronization.
      An empty string means that no primary server is defined."
    DEFVAL { "" }
    --CONFIGURABLE
    ::= { usrNTPObjects 1 }     

usrNTPSecondaryServer OBJECT-TYPE
    SYNTAX      DisplayString (SIZE (0..132))
    MAX-ACCESS  read-write
    STATUS      current
    DESCRIPTION
     "The IP address or host name of the secondary NTP server that the
      module will query for time synchronization whenever the primary
      server is unavailable.
      An empty string means that no secondary server is defined."
    DEFVAL { "" }
    --CONFIGURABLE
    ::= { usrNTPObjects 2 }

usrNTPPollingInterval OBJECT-TYPE
    SYNTAX      Integer32 (64..1024)
    UNITS       "seconds"
    MAX-ACCESS  read-write
    STATUS      current
    DESCRIPTION
     "The polling interval used by the NTP process to gather time
      synchronization information. In sconds.
      The range available is 64 seconds to 1024 seconds. The default is 600
      seconds (10 minutes)."
    REFERENCE "RFC 1305 (NTPv3)."
    DEFVAL { 600 }
    --CONFIGURABLE
    ::= { usrNTPObjects 3 }

usrNTPMaxRetransmits OBJECT-TYPE
    SYNTAX      Integer32 (1..200)
    MAX-ACCESS  read-write
    STATUS      current
    DESCRIPTION 
     "The maximum number of times a request will be retransmitted to a
      given server before the server is considered unavailable. The range
      allowed is 1 to 200 times. The default is 5 times."
    DEFVAL { 5 }
    --CONFIGURABLE
    ::= { usrNTPObjects 4 }

usrNTPTimeOut OBJECT-TYPE
    SYNTAX      Integer32 (1..60)
    UNITS       "seconds"
    MAX-ACCESS  read-write
    STATUS      current
    DESCRIPTION
     "The number of seconds since a request has been sent to a server,
      after which period the request is considered timed-out.
      The range for this is 1 second to 1 minute. The default is 10
      seconds."
    DEFVAL { 10 }
    --CONFIGURABLE
    ::= { usrNTPObjects 5 }

usrNTPEnable OBJECT-TYPE
    SYNTAX      TruthValue
    MAX-ACCESS  read-write
    STATUS      current
    DESCRIPTION
     "This object enables or disables NTP synchronization in a
      system. Default is off (false)."
    DEFVAL { false }
    --CONFIGURABLE
    ::= { usrNTPObjects 6 }

usrNTPProtocolVersion OBJECT-TYPE
    SYNTAX INTEGER {
        ntpV3(3),
        ntpV4(4)
      }
    MAX-ACCESS  read-write
    STATUS      current
    DESCRIPTION
     "The protocol version that the NTP client will use when sending NTP
      client requests to a server."
    DEFVAL { ntpV3 }
    --CONFIGURABLE
    ::= { usrNTPObjects 7 }

usrNTPCfmFileName OBJECT-TYPE
    SYNTAX      DisplayString (SIZE (1..32))
    MAX-ACCESS  read-only
    STATUS      current
    DESCRIPTION
     "The name of the configuration file currently in use."
    DEFVAL { "@file://Ntp.cfg" }
    ::= { usrNTPObjects 8 }

usrNTPCfmSaveFlag OBJECT-TYPE
    SYNTAX      UsrConfigStatus
    MAX-ACCESS  read-write
    STATUS      current
    DESCRIPTION
     "Setting the value of this object to `save' causes the values of the
     NTP Group to be written out to the current config file, which
     is stored in the usrNTPCfmFileName object. While the new
     ConfigFile is being written, the NTP process will set the value
     of this flag set to `saving''. Any attempts to set the value while it
     is  not `normal' (i.e. the file is currently being written to the
     ConfigFile) will result in a badValue error being returned. Setting
     the value to `normal' will result in no action."
    ::= { usrNTPObjects 9 }

usrNTPModuleVersion OBJECT-TYPE
    SYNTAX      DisplayString
    MAX-ACCESS  read-only
    STATUS      current
    DESCRIPTION
     "The current software version of the NTP module."
    ::= { usrNTPObjects 10 }

usrNTPLastGoodServer OBJECT-TYPE
    SYNTAX      DisplayString
    MAX-ACCESS  read-only
    STATUS      current
    DESCRIPTION
     "The symbolic host name of the last server from which
      time synchronization information was received (if there was a numeric
      address defined, this will be a numeric address in dot notation)."
    ::= { usrNTPObjects 11 }

usrNTPRcvdDatagrams OBJECT-TYPE
    SYNTAX      Counter32
    MAX-ACCESS  read-only
    STATUS      current
    DESCRIPTION
     "Number of datagrams received at the port on which NTP is listening to."
    ::= { usrNTPObjects 12 }

usrNTPRcvdTooShorts OBJECT-TYPE
    SYNTAX      Counter32
    MAX-ACCESS  read-only
    STATUS      current
    DESCRIPTION
     "Number of datagrams received which were too short for NTP version
      four."
    ::= { usrNTPObjects 13 }

usrNTPRcvdBadVersions OBJECT-TYPE
    SYNTAX      Counter32
    MAX-ACCESS  read-only
    STATUS      current
    DESCRIPTION
     "Number of datagrams received with a wrong NTP version."
    ::= { usrNTPObjects 14 }

usrNTPRcvdRequests OBJECT-TYPE
    SYNTAX      Counter32
    MAX-ACCESS  read-only
    STATUS      current
    DESCRIPTION
     "Number of NTP requests received."
    ::= { usrNTPObjects 15 }

usrNTPRcvdReplies OBJECT-TYPE
    SYNTAX      Counter32
    MAX-ACCESS  read-only
    STATUS      current
    DESCRIPTION
     "Number of NTP replies received."
    ::= { usrNTPObjects 16 }

usrNTPRcvdUnsuportedModes OBJECT-TYPE
    SYNTAX      Counter32
    MAX-ACCESS  read-only
    STATUS      current
    DESCRIPTION
     "Number of NTP datagrams received which had a mode value not supported
      by this entity."
    ::= { usrNTPObjects 17 }

usrNTPSentRequests OBJECT-TYPE
    SYNTAX      Counter32
    MAX-ACCESS  read-only
    STATUS      current
    DESCRIPTION
     "Number of NTP requests sent."
    ::= { usrNTPObjects 18 }

usrNTPSentReplies OBJECT-TYPE
    SYNTAX      Counter32
    MAX-ACCESS  read-only
    STATUS      current
    DESCRIPTION
     "Number of NTP replies sent since the system was last rebooted."
    ::= { usrNTPObjects 19 }

usrNTPSentRexmits OBJECT-TYPE
    SYNTAX      Counter32
    MAX-ACCESS  read-only
    STATUS      current
    DESCRIPTION
     "Number of NTP requests that were retransmitted due to lack of a timely
      reply."
    ::= { usrNTPObjects 20 }

usrNTPSendErrors OBJECT-TYPE
    SYNTAX      Counter32
    MAX-ACCESS  read-only
    STATUS      current
    DESCRIPTION
     "Number of NTP requests that could not be sent due to internal errors."
    ::= { usrNTPObjects 21 }

usrNTPDnsErrors OBJECT-TYPE
    SYNTAX      Counter32
    MAX-ACCESS  read-only
    STATUS      current
    DESCRIPTION
     "Number of times an error was returned by DNS when processing a name
      resolution request from the NTP module."
    ::= { usrNTPObjects 22 }

usrNTPServerTimeouts OBJECT-TYPE
    SYNTAX      Counter32
    MAX-ACCESS  read-only
    STATUS      current
    DESCRIPTION
     "Number of times a server was considered unavailable after requests
      were sent to it a maximum number of retransmissions without a reply."
    ::= { usrNTPObjects 23 }

usrNTPAllocErrors OBJECT-TYPE
    SYNTAX      Counter32
    MAX-ACCESS  read-only
    STATUS      current
    DESCRIPTION
     "Number of times an operation could not be performed due to a failure
      to allocate memory resources."
    ::= { usrNTPObjects 24 }

usrNTPResolvedIPAddress OBJECT-TYPE
    SYNTAX      IpAddress
    MAX-ACCESS  read-only
    STATUS      current
    DESCRIPTION
     "The IP address resolved from the 'current' server with which
      synchronization is being attempted.
      If there is no resolution, or there is no current server defined, this
      object returns zero."
    ::= { usrNTPObjects 25 }

usrNTPLastRcvdLeapIndicator OBJECT-TYPE
    SYNTAX      Integer32 (0..3)
    MAX-ACCESS  read-only
    STATUS      current
    DESCRIPTION
     "The value of the last received Leap Indicator field."
    REFERENCE "RFC 2030 (NTPv4)."
    ::= { usrNTPObjects 26 }

usrNTPLastRcvdMode OBJECT-TYPE
    SYNTAX      Integer32 (0..7)
    MAX-ACCESS  read-only
    STATUS      current
    DESCRIPTION
     "The value of the last received Mode field."
    REFERENCE "RFC 2030 (NTPv4)."
    ::= { usrNTPObjects 27 }

usrNTPLastRcvdStratum OBJECT-TYPE
    SYNTAX      Integer32 (0..255)
    MAX-ACCESS  read-only
    STATUS      current
    DESCRIPTION
     "The value of the last received Stratum field."
    REFERENCE "RFC 2030 (NTPv4)."
    ::= { usrNTPObjects 28 }

usrNTPLastRcvdPoll OBJECT-TYPE
    SYNTAX      Integer32 (0..255)
    MAX-ACCESS  read-only
    STATUS      current
    DESCRIPTION
     "The value of the last received Poll field."
    REFERENCE "RFC 2030 (NTPv4)."
    ::= { usrNTPObjects 29 }

usrNTPLastRcvdPrecision OBJECT-TYPE
    SYNTAX      Integer32 (-127..127)
    MAX-ACCESS  read-only
    STATUS      current
    DESCRIPTION
     "The value of the last received Precision field."
    REFERENCE "RFC 2030 (NTPv4)."
    ::= { usrNTPObjects 30 }

usrNTPLastRcvdRootDelay OBJECT-TYPE
    SYNTAX      Integer32
    MAX-ACCESS  read-only
    STATUS      current
    DESCRIPTION
     "The value of the last received Root Delay field."
    REFERENCE "RFC 2030 (NTPv4)."
    ::= { usrNTPObjects 31 }

usrNTPLastRcvdRootDispersion OBJECT-TYPE
    SYNTAX      Integer32
    MAX-ACCESS  read-only
    STATUS      current
    DESCRIPTION
     "The value of the last received Root Dispersion field."
    REFERENCE "RFC 2030 (NTPv4)."
    ::= { usrNTPObjects 32 }

usrNTPLastRcvdReferenceIdentifier OBJECT-TYPE
    SYNTAX      Integer32
    MAX-ACCESS  read-only
    STATUS      current
    DESCRIPTION
     "The value of the last received Reference Identifier field."
    REFERENCE "RFC 2030 (NTPv4)."
    ::= { usrNTPObjects 33 }

usrNTPLastRcvdReferenceTimestampHigh OBJECT-TYPE
    SYNTAX      Integer32
    MAX-ACCESS  read-only
    STATUS      current
    DESCRIPTION
     "The value of the last received Reference Timestamp field (high octets)."
    REFERENCE "RFC 2030 (NTPv4)."
    ::= { usrNTPObjects 34 }

usrNTPLastRcvdReferenceTimestampLow OBJECT-TYPE
    SYNTAX      Integer32
    MAX-ACCESS  read-only
    STATUS      current
    DESCRIPTION
     "The value of the last received Reference Timestamp field (low octets)."
    REFERENCE "RFC 2030 (NTPv4)."
    ::= { usrNTPObjects 35 }

usrNTPLastRcvdOriginateTimestampHigh OBJECT-TYPE
    SYNTAX      Integer32
    MAX-ACCESS  read-only
    STATUS      current
    DESCRIPTION
     "The value of the last received Originate Timestamp field (high octets)."
    REFERENCE "RFC 2030 (NTPv4)."
    ::= { usrNTPObjects 36 }

usrNTPLastRcvdOriginateTimestampLow OBJECT-TYPE
    SYNTAX      Integer32
    MAX-ACCESS  read-only
    STATUS      current
    DESCRIPTION
     "The value of the last received Originate Timestamp field (low octets)."
    REFERENCE "RFC 2030 (NTPv4)."
    ::= { usrNTPObjects 37 }

usrNTPLastRcvdReceiveTimestampHigh OBJECT-TYPE
    SYNTAX      Integer32
    MAX-ACCESS  read-only
    STATUS      current
    DESCRIPTION
     "The value of the last received Receive Timestamp field (high octets)."
    REFERENCE "RFC 2030 (NTPv4)."
    ::= { usrNTPObjects 38 }

usrNTPLastRcvdReceiveTimestampLow OBJECT-TYPE
    SYNTAX      Integer32
    MAX-ACCESS  read-only
    STATUS      current
    DESCRIPTION
     "The value of the last received Receive Timestamp field (low octets)."
    REFERENCE "RFC 2030 (NTPv4)."
    ::= { usrNTPObjects 39 }

usrNTPLastRcvdTransmitTimestampHigh OBJECT-TYPE
    SYNTAX      Integer32
    MAX-ACCESS  read-only
    STATUS      current
    DESCRIPTION
     "The value of the last received Transmit Timestamp field (high octets)."
    REFERENCE "RFC 2030 (NTPv4)."
    ::= { usrNTPObjects 40 }

usrNTPLastRcvdTransmitTimestampLow OBJECT-TYPE
    SYNTAX      Integer32
    MAX-ACCESS  read-only
    STATUS      current
    DESCRIPTION
     "The value of the last received Transmit Timestamp field (low octets)."
    REFERENCE "RFC 2030 (NTPv4)."
    ::= { usrNTPObjects 41 }

usrNTPTimeZone OBJECT-TYPE
    SYNTAX     OCTET STRING
    MAX-ACCESS  read-write
    STATUS      current
    DESCRIPTION
      "Timezone variables"
    --CONFIGURABLE
    ::= { usrNTPObjects 42 }


--
-- conformance information
--

usrNTPConformance OBJECT IDENTIFIER ::= { usrNTPMib 2 }
usrNTPCompliances OBJECT IDENTIFIER ::= { usrNTPConformance 1 }
usrNTPGroups      OBJECT IDENTIFIER ::= { usrNTPConformance 2 }

usrNTPCompliance MODULE-COMPLIANCE
    STATUS        current
    DESCRIPTION
     "The compliance statement for entities which implement
      the MIB."
    MODULE    -- this module
    MANDATORY-GROUPS {
      usrNTPGroup
    }
    ::= { usrNTPCompliances 1 }

-- units of conformance

usrNTPGroup OBJECT-GROUP
    OBJECTS {
      usrNTPPrimaryServer,
      usrNTPSecondaryServer,
      usrNTPPollingInterval,
      usrNTPMaxRetransmits,
      usrNTPTimeOut,
      usrNTPEnable,
      usrNTPProtocolVersion,
      usrNTPCfmFileName,
      usrNTPCfmSaveFlag,
      usrNTPModuleVersion,
      usrNTPLastGoodServer,
      usrNTPRcvdDatagrams,
      usrNTPRcvdTooShorts,
      usrNTPRcvdBadVersions,
      usrNTPRcvdRequests,
      usrNTPRcvdReplies,
      usrNTPRcvdUnsuportedModes,
      usrNTPSentRequests,
      usrNTPSentReplies,
      usrNTPSentRexmits,
      usrNTPSendErrors,
      usrNTPDnsErrors,
      usrNTPServerTimeouts,
      usrNTPAllocErrors,
      usrNTPResolvedIPAddress,
      usrNTPLastRcvdLeapIndicator,
      usrNTPLastRcvdMode,
      usrNTPLastRcvdStratum,
      usrNTPLastRcvdPoll,
      usrNTPLastRcvdPrecision,
      usrNTPLastRcvdRootDelay,
      usrNTPLastRcvdRootDispersion,
      usrNTPLastRcvdReferenceIdentifier,
      usrNTPLastRcvdReferenceTimestampHigh,
      usrNTPLastRcvdReferenceTimestampLow,
      usrNTPLastRcvdOriginateTimestampHigh,
      usrNTPLastRcvdOriginateTimestampLow,
      usrNTPLastRcvdReceiveTimestampHigh,
      usrNTPLastRcvdReceiveTimestampLow,
      usrNTPLastRcvdTransmitTimestampHigh,
      usrNTPLastRcvdTransmitTimestampLow
    }
    STATUS        current
    DESCRIPTION
     "All objects in this MIB."
    ::= { usrNTPGroups 1 }

-- Time Zone name  table definition      
 
    usrNTPTimeZoneTable OBJECT-TYPE
    SYNTAX SEQUENCE OF TimeZoneEntry 
    MAX-ACCESS  not-accessible  
    STATUS  current
    DESCRIPTION
        ""
    ::= { usrNTPObjects 43 }
        
    timeZoneEntry    OBJECT-TYPE
    SYNTAX  TimeZoneEntry
    MAX-ACCESS  not-accessible
    STATUS  current
    DESCRIPTION
        ""
    INDEX   { usrNTPIndex  }
    ::= { usrNTPTimeZoneTable 1 }
 
    TimeZoneEntry ::=
    SEQUENCE {
   	usrNTPIndex 
		INTEGER,
    usrNTPNextTimeZone
        DisplayString
	}

    usrNTPIndex OBJECT-TYPE
    SYNTAX  INTEGER
    MAX-ACCESS  not-accessible
    STATUS  current
    DESCRIPTION
        "The key field"
    ::= { timeZoneEntry 1 }

    usrNTPNextTimeZone    OBJECT-TYPE
    SYNTAX  DisplayString
    MAX-ACCESS  read-write
    STATUS  current
    DESCRIPTION 
        "Time zone list name"
    ::= { timeZoneEntry 2 }

     usrNTPServerFailure TRAP-TYPE
        ENTERPRISE  usrNTPTraps
        VARIABLES   {
            usrNTPPrimaryServer,
            usrNTPSecondaryServer
        }
        DESCRIPTION     "This trap is generated for NTP Server
                        connectivity failure."
    --#TYPE "Alarm"
    ::= 1

END

--
-- $Log: usr_ntp.mib,v $
-- Revision 1.9.2.1  1997/09/17 19:06:35  psd
-- Merged 2.0 to 3.0
--
--Revision 1.10.2.1  1997/09/05  15:09:33  psd
--Changes to MIBs so that they compile using the SimpleTester.
--
--Revision 1.10  1997/07/02  21:03:44  rsivan
--Corrected the description of 'PollInterval'.
--
--Revision 1.9  1997/05/06  21:11:24  rsivan
--Added log info on last received PDU.
--
-- Revision 1.8  1997/05/05 19:18:43  rsivan
-- Added usrNTPResolvedIPAddress, improved other descriptions.
--
-- Revision 1.7  1997/05/01 17:12:59  rsivan
-- Significantly modified.
-- Added extensive statistics.
--
--

--
--    usr_slip.mib - The USR SLIP MIB module
--
--
-- Author:         <sanil>
--
-- $Id: usr_slip.mib,v 1.1.4.2 1998/05/28 22:13:31 kelayath Exp $
--
--  | Copyright (c) 1995 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-SLIP-MIB DEFINITIONS ::= BEGIN

          IMPORTS
               OBJECT-TYPE
				FROM RFC-1212
					usrSLIP, DisplayString, UsrConfigStatus
						FROM USR-DEFINITIONS-MIB;


          usrSLIPBase      OBJECT IDENTIFIER ::= { usrSLIP 1 }



          usrSLIPBaseOffloading OBJECT-TYPE
              SYNTAX  INTEGER {
                        yes(2),
                        no(1)
                      }
              ACCESS   read-write
              STATUS   mandatory
              DESCRIPTION
                      "Indicates whether SLIP framing can be offloaded to
					  the modem card, if modem card is capable of doing it."
              DEFVAL { yes }
              --CONFIGURABLE
              ::= { usrSLIPBase 1 }



          usrSLIPBaseCfgFileName OBJECT-TYPE
              SYNTAX   DisplayString
              ACCESS   read-write
              STATUS   mandatory
              DESCRIPTION
                      "The name of a ConfigFile to read/write
                      permanent database records. If the value of this
                      object is an empty string, then the SLIP process
                      uses the default name `@file://SlipFile.cfg'."
              ::= { usrSLIPBase 2 }

          usrSLIPBaseCFMSaveStatus OBJECT-TYPE
              SYNTAX  UsrConfigStatus
              ACCESS  read-write
              STATUS  mandatory
              DESCRIPTION
                      "Setting the value of this object to `save'
                      causes the values of the SLIP Base Group
                      entries to be written out to the current SLIP
                      config file. While the new config file is being
                      written, the SLIP process will set the value
                      of this flag set to `saving''. Any attempts to set
                      the value while it is  not `normal' (i.e. the file
                      is currently being written to the config file)
                      while result in a badValue error being returned.
                      Setting the value to `normal' will result in no
                      action."
              ::= { usrSLIPBase 3 }

          usrSLIPStartMsg OBJECT-TYPE
              SYNTAX  OCTET STRING (SIZE (1..256))
              ACCESS  read-write
              STATUS  mandatory
              DESCRIPTION
                      "Startup Message for SLIP connection"
              --CONFIGURABLE
              ::= { usrSLIPBase 4 }
END
--
--	usr_ping.mib - The U.S. Robotics Ping MIB
--
--
--  | Copyright (c) 1995-97 U.S. Robotics Access Corp., Skokie, IL 60076   |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-PING-MIB DEFINITIONS ::= BEGIN

	IMPORTS
		OBJECT-TYPE, MODULE-IDENTITY, Integer32, Counter32, IpAddress
								FROM	SNMPv2-SMI
		TruthValue, DisplayString	
								FROM SNMPv2-TC
		common, UsrConfigStatus
								FROM USR-DEFINITIONS-MIB;

usrPing MODULE-IDENTITY
        LAST-UPDATED	"9703251600Z"
        ORGANIZATION	"U.S. Robotics"
	   CONTACT-INFO	""
        DESCRIPTION
            "This MIB Module defines the USRobotics private interface
		   to the Ping for Services process."
        ::= { common 36 }


-- Begin managed object definitions here...


	usrPingVersion OBJECT-TYPE
	SYNTAX	     DisplayString
	MAX-ACCESS     read-only
	STATUS      	current
	DESCRIPTION
		"The current software version of the Ping Process."
	::= { usrPing 1}


	usrPingConfigFileName OBJECT-TYPE
	SYNTAX	     DisplayString
	MAX-ACCESS     read-only
	STATUS      	current
	DESCRIPTION		
		"The name of a ConfigFile to read/write  permanent database records.
		 If the value of this object is an empty string, then the
		 Ping process uses the default name `@file://PingProcess.cfg'. "
	::= { usrPing 2 }

	usrPingCFMStatusFlag  OBJECT-TYPE
	SYNTAX		UsrConfigStatus
	MAX-ACCESS     read-write
	STATUS      	current
	DESCRIPTION
		"Setting the value of this object to `save' causes the values
		 of the Ping Group to be written out to the current config
		 file, which is stored in the cfgPingFile object. While
		 the new ConfigFile is being written, the Ping process
		 will set the value of this flag set to `saving''. Any
		 attempts to set the value while it is  not `normal'
		 (i.e. the file is currently being written to the
		 ConfigFile) while result in a badValue error being
		 returned. Setting the value to `normal' will result in no
		 action."
	::= { usrPing 3 }

	usrPingBusyOutEnabled	OBJECT-TYPE
	SYNTAX		TruthValue
	MAX-ACCESS	read-write
	STATUS		current
	DESCRIPTION
		"The variable defines whether the Ping process will continuously
		 ping a list of systems and busy out the modems if those systems
		 do not respond in the specified period of time."
	DEFVAL	{ 1 }
	--CONFIGURABLE
	::= { usrPing 4 }

	usrPingBusyOutTable	OBJECT-TYPE
	SYNTAX		SEQUENCE OF UsrPingBusyOutEntry
	MAX-ACCESS	not-accessible
	STATUS		current
	DESCRIPTION
	      	"A list of systems to ping for connectivity."
	::= { usrPing 5 }

	usrPingBusyOutEntry OBJECT-TYPE
	SYNTAX		UsrPingBusyOutEntry
	MAX-ACCESS	not-accessible
	STATUS		current
	DESCRIPTION
			"An entry containing the server info."
	INDEX { usrPingSystem }
	::= { usrPingBusyOutTable 1 }

	UsrPingBusyOutEntry ::=
	SEQUENCE {
		usrPingSystem DisplayString,
		usrPingServerStatus				INTEGER,
		usrPingFrequency				Integer32,
		usrPingMissesAllowed			Integer32,
		usrPingTimeOut					Integer32,
		usrPingServerReachable			INTEGER,
		usrPingServerTimeSinceContacted	Integer32,
		usrPingServerNumberPingsSent		Counter32,
		usrPingServerPingsReceived		Counter32,
		usrPingServerNumberTimeouts		Counter32,
		usrPingServerNumberUnreachable	Counter32,
		usrPingServerAverageResponseTime	Integer32,
		usrPingServerAddress			IpAddress,
		usrPingServerAverageResponseTimeMS Integer32,
		usrPingTimeInterval			Integer32,
		usrPingReAssign                 INTEGER,
		usrPingMissesAllowedInInterval			Integer32,
		usrPingTriggerClearInterval			Integer32
		}

	usrPingSystem	OBJECT-TYPE
	SYNTAX		DisplayString (SIZE (0..132))
	MAX-ACCESS	not-accessible
	STATUS		current
	DESCRIPTION
		"The name or IP address of the system to ping..."
	--CONFIGURABLE
	::= { usrPingBusyOutEntry 1 }

	usrPingServerStatus	OBJECT-TYPE
	SYNTAX		INTEGER {
				enabled(1),
				disabled(2),
				delete(3)
				}
	MAX-ACCESS	read-write
	STATUS		current
	DESCRIPTION
		"Is this particular server pinged or not?"
	DEFVAL	{ enabled }
	--CONFIGURABLE
	::= { usrPingBusyOutEntry 2 }

	usrPingFrequency	OBJECT-TYPE
	SYNTAX		Integer32(1..200)
	UNITS		"seconds"
	MAX-ACCESS	read-write
	STATUS		current
	DESCRIPTION	
		"How many seconds between each ping request."
	DEFVAL	{ 30 }
	--CONFIGURABLE
	::= { usrPingBusyOutEntry 3 }

	usrPingMissesAllowed	OBJECT-TYPE
	SYNTAX		Integer32(1..1000)
	MAX-ACCESS	read-write
	STATUS		current
	DESCRIPTION	
		"The number of allowable misses before this system is declared
		 unreachble."
	DEFVAL	{ 1 }
	--CONFIGURABLE
	::= { usrPingBusyOutEntry 4 }

	usrPingTimeOut		OBJECT-TYPE
	SYNTAX		Integer32(1..6000)
	UNITS		"seconds"
	MAX-ACCESS	read-write
	STATUS		current
	DESCRIPTION
		"The number of seconds a ping request can be outstanding before
		 it is declared a miss (failure)."
	DEFVAL	{ 10 }
	--CONFIGURABLE
	::= { usrPingBusyOutEntry 5 }

	usrPingServerReachable	OBJECT-TYPE
	SYNTAX		INTEGER {
				reachable (1),
				unreachable (2),
				badNameOrAddress (3),
				unTried (4),
				dnsTimeout (5)
				}
	MAX-ACCESS	read-only
	STATUS		current
	DESCRIPTION
		"Do we consider this server connected?"
	::= { usrPingBusyOutEntry 6 }

	usrPingServerTimeSinceContacted	OBJECT-TYPE
	SYNTAX		Integer32
	UNITS		"seconds"
	MAX-ACCESS	read-only
	STATUS		current
	DESCRIPTION
		"The number of seconds since this server was contacted."
	::= { usrPingBusyOutEntry 7 }

	usrPingServerNumberPingsSent	OBJECT-TYPE
	SYNTAX		Counter32
	MAX-ACCESS	read-only
	STATUS		current
	DESCRIPTION
		"The number of ping requests sent to this server."
	::= { usrPingBusyOutEntry 8 }

	usrPingServerPingsReceived	OBJECT-TYPE
	SYNTAX		Counter32
	MAX-ACCESS	read-only
	STATUS		current
	DESCRIPTION
		"The number of ping responses received from this server."
	::= { usrPingBusyOutEntry 9 }

	usrPingServerNumberTimeouts	OBJECT-TYPE
	SYNTAX		Counter32
	MAX-ACCESS	read-only
	STATUS		current
	DESCRIPTION
		"The number of ping requests sent but not responded to in the specified time."
	::= { usrPingBusyOutEntry 10 }

	usrPingServerNumberUnreachable	OBJECT-TYPE
	SYNTAX		Counter32
	MAX-ACCESS	read-only
	STATUS		current
	DESCRIPTION
		"The number of ICMP responses received that indicate the system was unreachable."
	::= { usrPingBusyOutEntry 11 }

	usrPingServerAverageResponseTime	OBJECT-TYPE
	SYNTAX		Integer32
	UNITS		"seconds"
	MAX-ACCESS	read-only
	STATUS		current
	DESCRIPTION
		"The average response time, in seconds, between ping request and response
		 for this server."
	::= { usrPingBusyOutEntry 12 }

	usrPingServerAddress	OBJECT-TYPE
	SYNTAX		IpAddress
	MAX-ACCESS	read-only
	STATUS		current
	DESCRIPTION
		"The translated IP address of this entry"
	::= { usrPingBusyOutEntry 13 }

	usrPingServerAverageResponseTimeMS	OBJECT-TYPE
	SYNTAX		Integer32
	UNITS		"milliseconds"
	MAX-ACCESS	read-only
	STATUS		current
	DESCRIPTION
		"The average response time, in milliseconds, between ping request
		and response for this server."
	::= { usrPingBusyOutEntry 14 }

	usrPingTimeInterval	OBJECT-TYPE
	SYNTAX		Integer32(1..6000)
	UNITS		"seconds"
	MAX-ACCESS	read-write
	STATUS		current
	DESCRIPTION
		"The number of seconds to wait before sending DSA trap in case of ping 
		failure. "
	DEFVAL { 10 }
	--CONFIGURABLE
	::= { usrPingBusyOutEntry 15 }

	usrPingReAssign	OBJECT-TYPE
    SYNTAX      INTEGER {
                yes(1),
                no(2)
                }
	MAX-ACCESS	read-write
	STATUS		current
	DESCRIPTION
	      	"The varibale defines whetehr the ping process will continuously
			ping a list of systems and initiate DSA reassignment of the modems 
			if those systems do not respond in the specified period of time."
    DEFVAL  { no }
	--CONFIGURABLE
	::= { usrPingBusyOutEntry 16 }
	
	usrPingMissesAllowedInInterval	OBJECT-TYPE
	SYNTAX		Integer32(1..1000)
	MAX-ACCESS	read-write
	STATUS		current
	DESCRIPTION	
		"The number of allowable misses in given time interval before this system
		is declared unreachble."
	DEFVAL	{ 1 }
	--CONFIGURABLE
	::= { usrPingBusyOutEntry 17 }

	usrPingTriggerClearInterval	OBJECT-TYPE
	SYNTAX		Integer32(1..6000)
	UNITS		"seconds"
	MAX-ACCESS	read-write
	STATUS		current
	DESCRIPTION
		"The number of seconds to wait for determining  ping success. "
	DEFVAL { 10 }
	--CONFIGURABLE
	::= { usrPingBusyOutEntry 18 }

END


--
-- For the revision history to work correctly, after a new MIB file has been
-- added to the CVS repository the first time the CVS Admin person needs to
-- set the correct comment string delimter for the file.
--
-- $Log: usr_ping.mib,v $
-- Revision 1.7.2.2  1998/01/15 19:30:18  lching
-- MR2522 - add usrPingServerAverageResponseTimeMS mib variable
--
-- Revision 1.7.2.1  1997/09/17 19:06:36  psd
-- Merged 2.0 to 3.0
--
--Revision 1.7.6.1  1997/09/05  15:09:34  psd
--Changes to MIBs so that they compile using the SimpleTester.
--
--Revision 1.7  1997/03/25  18:22:40  pfc
--SNMPv2 compliant
--
-- Revision 1.6  1997/02/19 21:02:51  pfc
-- Last version of ping mib for busy out
--
-- Revision 1.5  1997/02/19 19:18:08  pfc
-- Checkpoint
--
-- Revision 1.4  1997/02/18 14:41:31  pfc
-- Checkpoint the ping mib
--
-- Revision 1.3  1997/02/10 20:34:20  pfc
-- Whoops, need to make something configurable
--
-- Revision 1.2  1997/02/10 19:51:40  pfc
-- Add usr_ping mib and modify configurator mib to support busy out commands
--
-- Revision 1.1  1997/02/10 19:12:33  pfc
-- First cut
--
--
--
-- Local Variables:
-- tab-width:5
-- tab-stop-list:( 5 10 15 20 25 30 35 40 45 50 55 60 65 70 75 80)
-- End:
--
--
--      usr_remote_ping.mib - A proprietary Remote Ping MIB
--
--
-- Author:         Reuben Sivan
-- Created:        Feb-24-1997
--
--
--
--  | Copyright (c) 1997 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--


USR-REMOTE-PING-MIB DEFINITIONS ::= BEGIN

        IMPORTS
          OBJECT-TYPE,
          Integer32,
          IpAddress,
          TimeTicks
                FROM SNMPv2-SMI
          DisplayString,
          RowStatus
                FROM SNMPv2-TC
          MODULE-COMPLIANCE,
          OBJECT-GROUP
                FROM SNMPv2-CONF
          usrRemotePing, UsrConfigStatus
                FROM USR-DEFINITIONS-MIB;

-- The remote ping MIB is a diagnostic tool intended to test reachability,
-- reliability, and round trip delay between a managed USR NAS and any IP
-- system (PC, UNIX, another NAS, etc.) implementing the common ICMP Echo
-- protocol, also known as 'ping' (from the Unix command 'ping' based
-- on that same protocol).
--
-- As a side effect the tool can also be used to estimate DNS processing
-- delays by monitoring the object usrRemotePingDNSResolutionDelay.
--
--
-- In order to test reachability to a given device, an SNMP client
-- application should:
--
-- 1. Issue an SNMP GET for the object usrRemotePingIndexNext.0.
--    (assume the reply is 'x'). This step is optional, clients might browse
--    the table or just attempt a creation on any index until it succeeds.
--
-- 2. Create a new entry in the Remote Ping table by performing a command
--    such as 'SNMP SET usrRemotePingRowStatus.x = createAndWait.
--
-- 3. If the above succeeds, set values of the various settable objects in
--    the new row.
--    In particular, make sure to set usrRemotePingDestination.x to the name
--    or address to be 'pinged'.
--
--    Alternatively, it is possible to combine several settings on a single
--    SNMP PDU. The PDU could also include a rowStatus value of createAndGo
--    (it should be the last entry in the PDU in relation with a given row)
--    in which case a new row will be created, modified and activated in one
--    transaction.
--
-- 4. After setting the various objects of row x to desired values,
--    modify usrRemotePingRowStatus.x to 'active'.
--
-- 5. If the above succeeds, clients will now typically monitor the value of
--                'usrRemotePingConnectionStatus.x'
--    in order to find out if the process is making progress as expected
--    (it should return 'pinging' or 'completed' very soon now).
--
-- 6. Once 'usrRemotePingConnectionStatus' returns the value 'pinging',
--    clients will typically monitor progress by displaying the ongoing
--    values of:
--         usrRemotePingRequestsSent
--         usrRemotePingRepliesReceived
--         usrRemotePingTimeouts
--         usrRemotePingMinRoundTripTime
--         usrRemotePingMaxRoundTripTime
--         usrRemotePingAverageRoundTripTime
--
--    Other objects could be monitored for various diagnostics purposes,
--    such as:
--         usrRemotePingResolvedIPAddress
--         usrRemotePingCreationTime
--         usrRemotePingActivationTime
--         usrRemotePingLastChanged
--
-- 7. A particular ping sequence is completed when
--    'usrRemotePingConnectionStatus' returns 'completed'. At this point,
--    all the values row x will be steady. Note that, unless
--    'usrRemotePingSelfDestroyDelay' is zero, the row will be
--    self-destroyed a number of minutes after completion (see
--    'usrRemotePingSelfDestroyDelay' which has a default value of 10 minutes).
--
-- 8. In order to start a new sequence using the configuration values
--    already available in an existing row, set 'usrRemotePingRowStatus'
--    first to 'notInService' and then again to 'active'."



--
-- The managed objects
--

usrRemotePingObjects OBJECT IDENTIFIER ::= { usrRemotePing 1 }

usrRemotePingBase OBJECT IDENTIFIER ::= { usrRemotePingObjects 1 }

--
-- base (global) objects
--

usrRemotePingIndexNext OBJECT-TYPE
    SYNTAX      Integer32
    MAX-ACCESS  read-only
    STATUS      current
    DESCRIPTION
     "This object contains an appropriate value that can be used for
      'usrRemotePingIndex' when creating a new row in the Remote Ping
      Table'. If the value 0 is returned, it indicates that the table
      contains the maximum number of rows and thus it is not possible to add
      another one."
    ::= { usrRemotePingBase 1 }

usrRemotePingNRows OBJECT-TYPE
    SYNTAX      Integer32
    MAX-ACCESS  read-only
    STATUS      current
    DESCRIPTION
     "Number of rows currently present in the remote ping table."
    ::= { usrRemotePingBase 2 }

usrRemotePingMaxRows OBJECT-TYPE
    SYNTAX      Integer32 (1..1000)
    MAX-ACCESS  read-write
    STATUS      current
    DESCRIPTION
     "Maximum number of rows allowed in the remote ping table.
      Note that setting this object to a number which is smaller than the
      current number of rows will NOT cause any row deletions - rather, the
      effect of such an action will be noted in future attempts at row creation."
    DEFVAL  { 20 }
    --CONFIGURABLE
    ::= { usrRemotePingBase 3 }

usrRemotePingConfigFileName OBJECT-TYPE
    SYNTAX      DisplayString
    MAX-ACCESS  read-only
    STATUS      current
    DESCRIPTION
     "The name of a ConfigFile to read/write  permanent database records.
     If the value of this object is an empty string, then the Remote Ping
     process uses the default name `@file://RemotePingProcess.cfg'."
    ::= { usrRemotePingBase 4 }

usrRemotePingCFMStatusFlag  OBJECT-TYPE
    SYNTAX      UsrConfigStatus
    MAX-ACCESS  read-write
    STATUS      current
    DESCRIPTION
     "Setting the value of this object to `save' causes the values of the
     Remote Ping Group to be written out to the current config file, which
     is stored in the usrRemotePingConfigFileName object. While the new
     ConfigFile is being written, the Remote Ping process will set the value
     of this flag set to `saving''. Any attempts to set the value while it
     is  not `normal' (i.e. the file is currently being written to the
     ConfigFile) will result in a badValue error being returned. Setting
     the value to `normal' will result in no action."
    ::= { usrRemotePingBase 5 }

usrRemotePingTable OBJECT-TYPE
    SYNTAX      SEQUENCE OF UsrRemotePingEntry
    MAX-ACCESS  not-accessible
    STATUS      current
    DESCRIPTION
     "A table of remote ping entries."
    ::= { usrRemotePingObjects 2 }

usrRemotePingEntry OBJECT-TYPE
    SYNTAX      UsrRemotePingEntry
    MAX-ACCESS  not-accessible
    STATUS      current
    DESCRIPTION
     "A list of control entries used to control and monitor the remote
      ping process."
    INDEX   { usrRemotePingIndex }
    ::= { usrRemotePingTable 1 }

UsrRemotePingEntry ::= SEQUENCE {
    usrRemotePingIndex                      Integer32 (1..65535),
    usrRemotePingDestination                DisplayString (SIZE (1..255)),
    usrRemotePingSize                       Integer32(1..1450),
    usrRemotePingData                       OCTET STRING (SIZE (0..255)),
    usrRemotePingTimeOut                    Integer32(1..60),
    usrRemotePingCount                      Integer32(0..65535),
    usrRemotePingInterval                   Integer32(1..65535),
    usrRemotePingTtl                        Integer32(0..16),
    usrRemotePingSelfDestroyDelay           Integer32(0..65535),
    usrRemotePingState                      INTEGER,
    usrRemotePingRequestsSent               Integer32,
    usrRemotePingRepliesReceived            Integer32,
    usrRemotePingTimeouts                   Integer32,
    usrRemotePingLastRoundTripTime          Integer32,
    usrRemotePingMinRoundTripTime           Integer32,
    usrRemotePingMaxRoundTripTime           Integer32,
    usrRemotePingAverageRoundTripTime       Integer32,
    usrRemotePingResolvedIPAddress          IpAddress,
    usrRemotePingDNSResolutionDelay         Integer32,
    usrRemotePingCreationTime               TimeTicks,
    usrRemotePingActivationTime             TimeTicks,
    usrRemotePingLastChangeTime             TimeTicks,
    usrRemotePingRowStatus                  RowStatus
}

usrRemotePingIndex OBJECT-TYPE
    SYNTAX      Integer32 (1..65535)
    MAX-ACCESS  read-only
    STATUS      current
    DESCRIPTION
     "A unique index identifying this entry in the table."
    ::= { usrRemotePingEntry 1 }

usrRemotePingDestination OBJECT-TYPE
    SYNTAX      DisplayString (SIZE (1..255))
    MAX-ACCESS  read-create
    STATUS      current
    DESCRIPTION
     "The host name or IP address (in dot notation) of the target
      destination being tested by this row. A row cannot be activated
      unless this object has a length greater than zero.
      When a row is activated, a request is sent to the internal DNS process
      to resolve the symbolic name into an IP address. That address can be
      displayed by querying the object 'usrRemotePingResolvedIPAddress'.
      If DNS fails, the object usrRemotePingConnectionStatus will indicate
      'dnsFailed'.
      This object cannot be modified whenever usrRemotePingRowStatus is
      'active'."
    DEFVAL  { "" }
    ::= { usrRemotePingEntry 2 }

usrRemotePingSize OBJECT-TYPE
    SYNTAX      Integer32(1..1450)
    MAX-ACCESS  read-create
    STATUS      current
    DESCRIPTION
     "Size of the data to be sent, in bytes.
      Note that the actual datagram will be larger than this value, as it
      will include:
        - MAC header (14 octets on Ethernet)
        - IP header (20 octets)
        - ICMP header (8 octets)
      Together these add to a typical 42 octets.
      This object cannot be modified whenever usrRemotePingRowStatus is
      'active'."
    DEFVAL  { 64 }
    ::= { usrRemotePingEntry 3 }

usrRemotePingData OBJECT-TYPE
    SYNTAX      OCTET STRING (SIZE (0..255))
    MAX-ACCESS  read-create
    STATUS      current
    DESCRIPTION
     "This object specifies the data to be transmitted. If the length of
      this object is bigger than usrRemotePingSize, only the first
      usrRemotePingSize octets will be used. If the length of this
      object is zero, the agent will use random data. If the length of
      this object is smaller than usrRemotePingSize, the data pattern
      will be repeated as many times as necessary to fill up the
      transmission buffer.
      This object cannot be modified whenever usrRemotePingRowStatus is
      'active'."
    DEFVAL  { "" }
    ::= { usrRemotePingEntry 4 }

usrRemotePingTimeOut OBJECT-TYPE
    SYNTAX      Integer32(1..60)
    MAX-ACCESS  read-create
    STATUS      current
    DESCRIPTION
     "Amount of time in seconds before deciding that a transmission has
      not been replied to.
      This object cannot be modified whenever usrRemotePingRowStatus is
      'active'."
    DEFVAL  { 20 }
    ::= { usrRemotePingEntry 5 }

usrRemotePingCount OBJECT-TYPE
    SYNTAX      Integer32(0..65535)
    MAX-ACCESS  read-create
    STATUS      current
    DESCRIPTION
     "The number of ICMP ECHO requests to be sent in this sequence.
      The conventional value of zero is interpreted as infinite: the process
      will continue forever until the row is deleted or deactivated via an
      SNMP SET command.
      This object cannot be modified whenever usrRemotePingRowStatus is
      'active'."
    DEFVAL  { 1 }
    ::= { usrRemotePingEntry 6 }

usrRemotePingInterval OBJECT-TYPE
    SYNTAX      Integer32(1..65535)
    MAX-ACCESS  read-create
    STATUS      current
    DESCRIPTION
     "Number of seconds between successive ECHO REQUEST request
      transmissions. Note that the actual interval might be different for
      any given transmission, as the agent will not send a new request
      before a previous request is completed (replied or timed-out).
      This object cannot be modified whenever usrRemotePingRowStatus is
      'active'."
    DEFVAL  { 1 }
    ::= { usrRemotePingEntry 7 }

usrRemotePingTtl OBJECT-TYPE
    SYNTAX      Integer32(0..16)
    MAX-ACCESS  read-create
    STATUS      current
    DESCRIPTION
     "The TTL (time to live) to be used for the ECHO REQUEST commands.
      If this object is zero, the TTL value currently in use by the
      IP stack will be in effect.
      This object cannot be modified whenever usrRemotePingRowStatus is
      'active'."
    DEFVAL  { 0 }
    ::= { usrRemotePingEntry 8 }

usrRemotePingSelfDestroyDelay OBJECT-TYPE
    SYNTAX      Integer32(0..65535)
    MAX-ACCESS  read-create
    STATUS      current
    DESCRIPTION
     "Number of minutes this row is allowed to be in a state of inactivity
      before it is destroyed by the agent.
      A row is considered inactive anytime 'usrRemotePingState' is one of:
        - notActive
        - dnsFailed
        - badAddress
        - completed
        - allocFailed
      The wait timer is reset upon any change in a row received through an
      SNMP 'SET' command.
      A value of zero implies no self-destruction will take place on
      this row.
      This object can be modified at any time."
    DEFVAL  { 10 }
    ::= { usrRemotePingEntry 9 }

usrRemotePingState OBJECT-TYPE
    SYNTAX      INTEGER {
      notActive(1),    -- this row is not active.
      waitingDns(2),   -- waiting for DNS resolution.
      dnsFailed(3),    -- destination address could not be resolved.
      badAddress(4),   -- the resolved IP address is illegal.
      pinging(5),      -- sending ping commands after successful DNS.
      completed(6),    -- the requested number of iterations is completed.
      allocFailed(7)   -- failed to allocate resources.
    }
    MAX-ACCESS  read-only
    STATUS      current
    DESCRIPTION
     "The state of the 'remote ping' process associated with this row.
      Before this row is activated, this object will have the value
      'notActive(1)'.
      Upon activation, if DNS resolution is needed, the object will
      receive the value 'waitingDns(2)'. If DNS times out or otherwise
      fails, this object will receive the value 'dnsFailed(3)'.
      If the resolved IP address is not legal, this object value will be
      'badAddress(4)'.
      If none of the above fails, the first ping command will be sent
      and this object will indicate the value 'pinging(5)'.
      After the desired number of ping commands have been sent and
      replied to (or timed-out) this object will receive the value
      completed(6)'.
      If there is a resource allocation error along the way, the process
      will stop and this object will receive the value allocFailed(7)."
    ::= { usrRemotePingEntry 10 }

usrRemotePingRequestsSent OBJECT-TYPE
    SYNTAX      Integer32
    MAX-ACCESS  read-only
    STATUS      current
    DESCRIPTION
     "Number of requests transmitted so far since this row became active."
    ::= { usrRemotePingEntry 11 }

usrRemotePingRepliesReceived OBJECT-TYPE
    SYNTAX      Integer32
    MAX-ACCESS  read-only
    STATUS      current
    DESCRIPTION
     "Number of replies received so far since this row became active."
    ::= { usrRemotePingEntry 12 }

usrRemotePingTimeouts OBJECT-TYPE
    SYNTAX      Integer32
    MAX-ACCESS  read-only
    STATUS      current
    DESCRIPTION
     "Number of requests timed-out (no reply received after
      'usrRemotePingTimeOut' seconds) since this row became active."
    ::= { usrRemotePingEntry 13 }

usrRemotePingLastRoundTripTime OBJECT-TYPE
    SYNTAX      Integer32
    MAX-ACCESS  read-only
    STATUS      current
    DESCRIPTION
     "The round trip time in milliseconds experienced by the last
      request-reply iteration. If the last iteration was a time-out, this
      object will return the value -1.
      This object remains zero until an actual reply or timeout is
      received."
    ::= { usrRemotePingEntry 14 }

usrRemotePingMinRoundTripTime OBJECT-TYPE
    SYNTAX      Integer32
    MAX-ACCESS  read-only
    STATUS      current
    DESCRIPTION
     "The minimum round trip time in milliseconds, not including timed out
      requests. This object remains zero until an actual reply is received."
    ::= { usrRemotePingEntry 15 }

usrRemotePingMaxRoundTripTime OBJECT-TYPE
    SYNTAX      Integer32
    MAX-ACCESS  read-only
    STATUS      current
    DESCRIPTION
     "The maximum round trip time in milliseconds, not including timed out
      requests. This object remains zero until an actual reply is received."
    ::= { usrRemotePingEntry 16 }

usrRemotePingAverageRoundTripTime OBJECT-TYPE
    SYNTAX      Integer32
    MAX-ACCESS  read-only
    STATUS      current
    DESCRIPTION
     "The average round trip time in milliseconds, not counting
      timed-out requests. This object remains zero until an actual reply is
      received."
    ::= { usrRemotePingEntry 17 }

usrRemotePingDNSResolutionDelay OBJECT-TYPE
    SYNTAX      Integer32
    MAX-ACCESS  read-only
    STATUS      current
    DESCRIPTION
     "The time elapsed, in milliseconds, since the agent issued a DNS query
      for this entry until it received a reply."
    ::= { usrRemotePingEntry 18 }

usrRemotePingResolvedIPAddress OBJECT-TYPE
    SYNTAX      IpAddress
    MAX-ACCESS  read-only
    STATUS      current
    DESCRIPTION
     "The IP address resolved from the destination address string.
      If there is no resolution, this object returns zero."
    ::= { usrRemotePingEntry 19 }

usrRemotePingCreationTime OBJECT-TYPE
    SYNTAX      TimeTicks
    MAX-ACCESS  read-only
    STATUS      current
    DESCRIPTION
     "The value of sysUpTime at the time this row was created."
    ::= { usrRemotePingEntry 20 }

usrRemotePingActivationTime OBJECT-TYPE
    SYNTAX      TimeTicks
    MAX-ACCESS  read-only
    STATUS      current
    DESCRIPTION
     "The value of sysUpTime at the time this row was last activated (or
      zero, if never)."
    ::= { usrRemotePingEntry 21 }

usrRemotePingLastChangeTime OBJECT-TYPE
    SYNTAX      TimeTicks
    MAX-ACCESS  read-only
    STATUS      current
    DESCRIPTION
     "The value of sysUpTime at the time any object in this row was last
      modified."
    ::= { usrRemotePingEntry 22 }

usrRemotePingRowStatus OBJECT-TYPE
    SYNTAX      RowStatus
    MAX-ACCESS  read-create
    STATUS      current
    DESCRIPTION
     "This object is used to create, modify or delete a row in this table.
      Setting this object to 'createAndWait' creates the row with default
      values. Right after creation the value of this object will be
      'notReady'.
      When all parameters are given proper values, this object
      will return the value 'notInService', at which point the client can
      set the object to 'active' to activate the row.

      Modifying this object from 'active' to 'notInService' will stop any
      on-going sequence, at which point the row can be re-activated by
      setting the object to 'active' again, after possibly modifying some of
      the associated parameters. Note that this will cause zeroing out of
      any on-going counters such as 'usrRemotePingRequestsSent'.

      Setting this object to 'destroy' will stop any on-going activity and
      delete the row."
    DEFVAL  { createAndWait }
    ::= { usrRemotePingEntry 23 }

--
-- conformance information
--

usrRemotePingConformance OBJECT IDENTIFIER ::= { usrRemotePing 2 }
usrRemotePingCompliances OBJECT IDENTIFIER ::= { usrRemotePingConformance 1 }
usrRemotePingGroups      OBJECT IDENTIFIER ::= { usrRemotePingConformance 2 }

usrRemotePingCompliance MODULE-COMPLIANCE
        STATUS        current
        DESCRIPTION
            "The compliance statement for entities which implement
             the MIB."
        MODULE    -- this module
            MANDATORY-GROUPS {
                usrRemotePingGroup
            }
        ::= { usrRemotePingCompliances 1 }

-- units of conformance

usrRemotePingGroup OBJECT-GROUP
        OBJECTS {
                usrRemotePingIndexNext,
                usrRemotePingNRows,
                usrRemotePingMaxRows,
                usrRemotePingIndex,
                usrRemotePingDestination,
                usrRemotePingSize,
                usrRemotePingData,
                usrRemotePingTimeOut,
                usrRemotePingCount,
                usrRemotePingInterval,
                usrRemotePingTtl,
                usrRemotePingSelfDestroyDelay,
                usrRemotePingState,
                usrRemotePingRequestsSent,
                usrRemotePingRepliesReceived,
                usrRemotePingTimeouts,
                usrRemotePingLastRoundTripTime,
                usrRemotePingMinRoundTripTime,
                usrRemotePingMaxRoundTripTime,
                usrRemotePingAverageRoundTripTime,
                usrRemotePingResolvedIPAddress,
                usrRemotePingDNSResolutionDelay,
                usrRemotePingCreationTime,
                usrRemotePingActivationTime,
                usrRemotePingLastChangeTime,
                usrRemotePingRowStatus
        }
        STATUS        current
        DESCRIPTION
          "All objects in this MIB."
        ::= { usrRemotePingGroups 1 }


END

-- $Log: usr_remote_ping.mib,v $
-- Revision 1.8.2.1  1997/09/17 19:06:38  psd
-- Merged 2.0 to 3.0
--
--Revision 1.8.10.1  1997/09/05  15:09:36  psd
--Changes to MIBs so that they compile using the SimpleTester.
--
--Revision 1.8  1997/05/02  20:35:39  rsivan
--Fixed typo in description of usrRemotePingCFMStatusFlag
--
-- Revision 1.7  1997/03/25 15:10:47  rsivan
-- Removed tbd mark around ttl.
--
-- Revision 1.6  1997/03/24 21:14:45  rsivan
-- Added support for configuration save.
-- Fixed some descriptions and some missnomers.
--
-- Revision 1.5  1997/03/21 16:53:56  rsivan
-- modified to SMIv2, deleted ifIndex, changed min interval, added DNSDelay, added lastTripDelay
--
-- Revision 1.4  1997/03/13 23:55:04  rsivan
-- Self destroy time default changed to 60 minutes.
-- MaxRows made read-write.
--
-- Revision 1.3  1997/03/13 18:01:36  rsivan
-- Removed temp. tree root, this one is linked to USR root.
--
-- Revision 1.2  1997/03/12 19:45:50  rsivan
-- Misc.
--
--
--      usr_traceroute.mib - A proprietary Traceroute MIB
--
--
-- Author:         Jeff Haag
-- Created:        Mar-13-1997
--
--  $Id: usr_traceroute.mib,v 1.4.2.1 1997/09/17 19:06:41 psd Exp $
--
--
--  | Copyright (c) 1997 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--
--
--
-- The traceroute MIB is a diagnostic tool intended to retrieve route 
-- information between a managed USR NAS and any IP system (PC, Unix, 
-- another NAS etc).  It only requires the routers along the way to the
-- the destination to implement IP routing and ICMP Time Exceeded messages.
-- The destination must implement UDP and return ICMP error message 
-- destination unreachable.
-- The functionality is similar to the Unix command 'traceroute' based
-- on those same protocols.
--
-- In order to determine the route to a host, the SNMP client application 
-- should do the following:
--
--
-- *********To start the traceroute*********
--
--  1. Create a new entry in the Traceroute table by performing a command
--     such as 'SNMP SET usrTracerouteRowStatus.x = createAndWait.
--
--  2. If the above succeeds, set values of the various settable objects in
--     the new row.  In particular, make sure to set 
--     usrTracerouteDestination.x to the name or address whose route is to 
--     be traced.
--
--  3. After setting the various objects of row x to desired values,
--     modify usrTracerouteRowStatus.x to 'active'.
--
-- OR
--
--  1. set values of the various settable objects in a new row.  
--     In particular, make sure to set usrTracerouteDestination.x to the 
--     name or address whose route is to be traced. 
--
--  2. Create and activate new entry in the Traceroute table by performing a command
--     such as 'SNMP SET usrTracerouteRowStatus.x = createAndGo.
--
--  3. The row status will automatically get set to active after row creation
--     and the command will begin
--
-- *********After starting the traceroute*********
--
-- 4. If the above succeeds, clients will now typically monitor the values of
--    'usrTracerouteState.x' in order to find out if the process is 
--    'completed' or an error has occurred
--
-- 5. Once 'usrTracerouteState.x' returns the value 'completed',
--    clients can view the route information in the usrTracerouteHopTable
--    by looking at rows that have a matching usrTraceRouteIndex
--
-- 6. A particular traceroute is completed when
--    'usrTracerouteState.x' returns 'completed'. At this point,
--    all the values of row x will be steady and no more entries for this 
--    traceroute will be added to the hop table. 
--
-- 7. In order to start a new sequence using the configuration values
--    already available in an existing row, set 'usrTracerouteRowStatus'
--    first to 'notInService' and then again to 'active'."  This will 
--	  automatically clean up any previous corresponding entries in the 
--    traceroute hop table
--
-- ******************
-- additional notes
-- ******************
-- a)  A row will be removed from the table after 60 minutes if there has been
--     no activity
-- b)  A row may be deleted/destroyed at any time, even if the row status is 
--     'active'
--

USR-TRACEROUTE-MIB DEFINITIONS ::= BEGIN

        IMPORTS
          RowStatus
                FROM SNMPv2-TC
          OBJECT-TYPE
                FROM RFC-1212
          IpAddress
                FROM RFC1155-SMI
          usrTraceroute, DisplayString, UsrConfigStatus 
                FROM USR-DEFINITIONS-MIB;

--
-- Traceroute managed objects
--
usrTracerouteBase OBJECT IDENTIFIER ::= { usrTraceroute 1 }

--
-- Base Objects
--
usrTracerouteIndexNext OBJECT-TYPE
    SYNTAX  INTEGER
    ACCESS  read-only
    STATUS  mandatory
    DESCRIPTION
     "This object contains an appropriate value that can be used for
      'usrTracerouteIndex' when creating a new row in the Traceroute
      Table'. If the value 0 is returned, it indicates that the table
      contains the maximum number of rows and thus it is not possible to add
      another one."
    ::= { usrTracerouteBase 1 }

usrTracerouteIndexNRows OBJECT-TYPE
    SYNTAX  INTEGER
    ACCESS  read-only
    STATUS  mandatory
    DESCRIPTION
     "Number of rows currently present in the Traceroute table."
    ::= { usrTracerouteBase 2 }

usrTracerouteMaxRows OBJECT-TYPE
    SYNTAX  INTEGER (1..255)
    ACCESS  read-write
    STATUS  mandatory
    DESCRIPTION
     "Maximum number of rows allowed in the Traceroute table.
      Note that setting this object to a number which is smaller than the
      current number of rows will NOT cause any row deletions - rather, the
      effect of such an action will be noted in future attempts at row creation."
    DEFVAL  { 20 }
    --CONFIGURABLE
    ::= { usrTracerouteBase 3 }

usrTracerouteConfigFileName OBJECT-TYPE
    SYNTAX  DisplayString
    ACCESS  read-only
    STATUS  mandatory
    DESCRIPTION
     "The name of a ConfigFile to read/write  permanent database records.
     If the value of this object is an empty string, then the Traceroute
     process uses the default name `@file://TracerouteProcess.cfg'."
    ::= { usrTracerouteBase 4 }

usrTracerouteCFMStatusFlag  OBJECT-TYPE
    SYNTAX  UsrConfigStatus
    ACCESS  read-write
    STATUS  mandatory
    DESCRIPTION
     "Setting the value of this object to `save' causes the values of the
     Remote Ping Group to be written out to the current config file, which
     is stored in the usrTracerouteConfigFileName object. While the new
     ConfigFile is being written, the Remote Ping process will set the value
     of this flag set to `saving''. Any attempts to set the value while it
     is  not `normal' (i.e. the file is currently being written to the
     ConfigFile) while result in a badValue error being returned. Setting
     the value to `normal' will result in no action."
    ::= { usrTracerouteBase 5 }

usrTracerouteTable OBJECT-TYPE
    SYNTAX  SEQUENCE OF UsrTracerouteEntry
    ACCESS  not-accessible
    STATUS  mandatory
    DESCRIPTION
     "A table of traceroute entries."
    ::= { usrTraceroute 2 }

usrTracerouteEntry OBJECT-TYPE
    SYNTAX  UsrTracerouteEntry
    ACCESS  not-accessible
    STATUS  mandatory
    DESCRIPTION
     "A list of fields defining this traceroute"
    INDEX   { usrTracerouteIndex }
    ::= { usrTracerouteTable 1 }

UsrTracerouteEntry ::= SEQUENCE {
    usrTracerouteIndex                      INTEGER,
    usrTracerouteDestination                DisplayString (SIZE (1..255)),
    usrTracerouteResolvedIPAddress          IpAddress,
    usrTracerouteHopTimeout                 INTEGER(1..60),
    usrTracerouteHopProbes                  INTEGER(1..10),
    usrTracerouteMaxHops                    INTEGER(1..255),
    usrTracerouteUDPPort                    INTEGER(1..65000),
    usrTracerouteDataSize                   INTEGER(1..8184),
    usrTracerouteHopCount                   INTEGER,
    usrTracerouteState                      INTEGER,
    usrTracerouteRowStatus                  RowStatus
}

usrTracerouteIndex OBJECT-TYPE
    SYNTAX  INTEGER
    ACCESS  not-accessible
    STATUS  mandatory
    DESCRIPTION
     "A unique index identifying this entry in the table."
    ::= { usrTracerouteEntry 1 }

usrTracerouteDestination OBJECT-TYPE
    SYNTAX  DisplayString (SIZE (1..255))
    ACCESS  read-write
    STATUS  mandatory
    DESCRIPTION
     "The host name or IP address (in dot notation) of the target
      destination being traced by this row. A row cannot be activated
      unless this object has a length greater than zero.
      Router DNS services will always be used to resolve (names) and/or
	  verify addresses in dot notation.  If DNS fails, the object 
	  usrTracerouteRowState will indicate 'dnsFailed' or 'badAddress'.
      This object cannot be modified whenever usrTracerouteRowStatus is
      'active'."
    DEFVAL  { "" }
    ::= { usrTracerouteEntry 2 }

usrTracerouteResolvedIPAddress OBJECT-TYPE
    SYNTAX  IpAddress
    ACCESS  read-only
    STATUS  mandatory
    DESCRIPTION
     "The IP address resolved from the destination address string.
      If an IP address was set in the destination field it will
      be reflected here as well.
      If an address cannot be resolved, this object returns zero and the
      state field is set to dnsFail"
    ::= { usrTracerouteEntry 3 }


usrTracerouteHopTimeout OBJECT-TYPE
    SYNTAX  INTEGER(1..60)
    ACCESS  read-write
    STATUS  mandatory
    DESCRIPTION
     "Amount of time in seconds before retrying a hop.  This object cannot 
	  be modified whenever usrTracerouteRowStatus is 'active'."
    DEFVAL  { 3 }
    ::= { usrTracerouteEntry 4 }

usrTracerouteHopProbes OBJECT-TYPE
    SYNTAX  INTEGER(1..10)
    ACCESS  read-write
    STATUS  mandatory
    DESCRIPTION
     "The maixmum number of times to try to discern a hop before moving 
	  on to the next hop"
    DEFVAL  { 3 }
    ::= { usrTracerouteEntry 5 }

usrTracerouteMaxHops OBJECT-TYPE
    SYNTAX  INTEGER(1..255)
    ACCESS  read-write
    STATUS  mandatory
    DESCRIPTION
     "The maixmum number of hops to trace before quitting."
    DEFVAL  { 30 }
    ::= { usrTracerouteEntry 6 }

usrTracerouteUDPPort OBJECT-TYPE
    SYNTAX  INTEGER(1..65000)
    ACCESS  read-write
    STATUS  mandatory
    DESCRIPTION
     "The UDP port value to use when attempting to find the route"
    DEFVAL  { 33434 }
    ::= { usrTracerouteEntry 7 }

usrTracerouteDataSize OBJECT-TYPE
    SYNTAX  INTEGER(1..8184)
    ACCESS  read-write
    STATUS  mandatory
    DESCRIPTION
     "The maixmum number of hops to trace before quitting."
    DEFVAL  { 1 }
    ::= { usrTracerouteEntry 8 }

usrTracerouteHopCount OBJECT-TYPE
    SYNTAX  INTEGER
    ACCESS  read-only
    STATUS  mandatory
    DESCRIPTION
     "The number of hops taken to get to the destination."
    ::= { usrTracerouteEntry 9 }

usrTracerouteState OBJECT-TYPE
    SYNTAX  INTEGER {
      notActive(1),        -- this row is not active.
      waitingDns(2),       -- waiting for DNS resolution.
      dnsFailed(3),        -- destination address could not be resolved.
      badAddress(4),       -- the resolved IP address is illegal.
      hopsExceeded(5),     -- the maximum number of hops was exceeded
      destUnreachable(6),  -- a route to the host could not be found
      tracing(7),          -- performing traceroute
      completed(8),        -- traceroute completed successfully
	  resourceFailure(9)   -- there was not enough resources to complete the command
    }
    ACCESS  read-only
    STATUS  mandatory
    DESCRIPTION
     "The state of the 'traceroute' process associated with this row.
      Before this row is activated, this object will have the value
      'notActive(1)'.
      Upon activation, if DNS resolution is needed, the object will
      receive the value 'waitingDns(2)'. If DNS times out or otherwise
      fails, this object will receive the value 'dnsFailed(3)'.
      If the resolved IP address is not legal, this object value will be
      'badAddress(4)'.
      If the a timeout occurs or the hop count is exceeded, the value will
      be 'hopTimeout(6)' or 'hopsExceeded(7)'.
	  If a route to the host could not be found, a 'destUnreachable(8)'
	  value will be returned.
      If none of the above fails, the first traceroute command will be sent
      and this object will indicate the value 'tracing(9)'.
      After the completes this object will receive the value
      completed(10)'."
    ::= { usrTracerouteEntry 10 }

usrTracerouteRowStatus OBJECT-TYPE
    SYNTAX          RowStatus
    ACCESS          read-write
    STATUS          mandatory
    DESCRIPTION
     "This object is used to create, modify or delete a row in this table.
      Setting this object to 'createAndWait' creates the row with default
      values. Right after creation the value of this object will be
      'notReady'.
      When all parameters are given proper values, this object
      will return the value 'notInService', at which point the client can
      set the object to 'active' to activate the row.
      Modifying this object from 'active' to 'notInService' will cancel any
      on-going traceroute and remove entries for it from the usrTracerouteHopTable.
      Setting the object to 'active' again will start a new traceroute with the
      supplied parameters
      Setting this object to 'destroy' will stop any on-going activity and
      delete the row."
    DEFVAL  { createAndWait }
    ::= { usrTracerouteEntry 11 }


usrTracerouteHopTable OBJECT-TYPE
    SYNTAX  SEQUENCE OF UsrTracerouteHopEntry
    ACCESS  not-accessible
    STATUS  mandatory
    DESCRIPTION
     "A table of traceroute hop entries."
    ::= { usrTraceroute 3 }

usrTracerouteHopEntry OBJECT-TYPE
    SYNTAX  UsrTracerouteHopEntry
    ACCESS  not-accessible
    STATUS  mandatory
    DESCRIPTION
     "A list of fields containing the hop information for all traceroute instances"
    INDEX   { usrTracerouteTableIndex, usrTracerouteHopIndex }
    ::= { usrTracerouteHopTable 1 }

UsrTracerouteHopEntry ::= SEQUENCE {
    usrTracerouteTableIndex                 INTEGER,
    usrTracerouteHopIndex                   INTEGER,
    usrTracerouteHopIPAddress               IpAddress,
    usrTracerouteHopRoundTripTime           INTEGER
}

usrTracerouteTableIndex OBJECT-TYPE
    SYNTAX  INTEGER
    ACCESS  not-accessible
    STATUS  mandatory
    DESCRIPTION
     "The index into the usrTracerouteTable corresponding to this hop."
    ::= { usrTracerouteHopEntry 1 }

usrTracerouteHopIndex OBJECT-TYPE
    SYNTAX  INTEGER
    ACCESS  not-accessible
    STATUS  mandatory
    DESCRIPTION
     "The hop number corresponding to the usrTracerouteHopIPAddress in this row."
    ::= { usrTracerouteHopEntry 2 }

usrTracerouteHopIPAddress OBJECT-TYPE
    SYNTAX  IpAddress
    ACCESS  read-only
    STATUS  mandatory
    DESCRIPTION
     "The IP address for a hop.  An address of zero means that there was no response
	  from that hop."
    ::= { usrTracerouteHopEntry 3 }

usrTracerouteHopRoundTripTime OBJECT-TYPE
    SYNTAX  INTEGER
    ACCESS  read-only
    STATUS  mandatory
    DESCRIPTION
     "Round trip time for this hop in milliseconds."
    ::= { usrTracerouteHopEntry 4 }


END

--
-- File Footer 
--
-- Revisions:
--
-- $Log: usr_traceroute.mib,v $
-- Revision 1.4.2.1  1997/09/17 19:06:41  psd
-- Merged 2.0 to 3.0
--
--Revision 1.5.2.1  1997/09/05  15:09:39  psd
--Changes to MIBs so that they compile using the SimpleTester.
--
--Revision 1.5  1997/08/05  18:35:33  jhaag
--MR2281 changed max UDP port to 65000
--
-- Revision 1.4  1997/05/05 14:21:52  jhaag
-- removed embedded command from comment field in file footer
--
-- Revision 1.3  1997/05/05 14:03:55  jhaag
-- added CONFIGURABLE flag to max rows
--
-- Revision 1.2  1997/05/04 21:40:23  jhaag
-- added CFM and CLI enhancements for traceroute
--
--
--
--
--	usr_tcp.mib
--
--
-- Author:         Jim Halpin
--
-- $Id: usr_tcp.mib,v 1.2.2.2 1998/06/09 21:39:02 jlivermo Exp $
--
--  | Copyright (c) 1995-1997 U.S. Robotics Access Corp., Skokie, IL 60076 |
--  |                                                                      |
--  | The information in this software is subject to change without notice |
--  | and should not be construed as a commitment by U.S. Robotics Access  |
--  | Corp.                                                                |
--  |                                                                      |
--  | U.S. Robotics Access Corp. assumes no responsibility for the use or  |
--  | reliability of its software on equtcpment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownershtcp of the software shall at all   |
--  | times remain in U.S. Robotics Access Corp.                           |
--

USR-TCP-MIB DEFINITIONS ::= BEGIN

	IMPORTS
          OBJECT-TYPE
                  FROM RFC-1212
          usrTcp, UsrConfigStatus, DisplayString
                  FROM USR-DEFINITIONS-MIB;


   -- Begin managed object definitions here...

usrTcpCFMStatusFlag OBJECT-TYPE
	SYNTAX		UsrConfigStatus
	ACCESS		read-write
	STATUS		mandatory
	DESCRIPTION
		"This variable controls saving and loading of configuration
           information for the TCP Module. The value can 
           be set to either save or load by a management station. The other
           values indicate if any configuration operation and what type
           is in progress."
::= { usrTcp 1 }

usrTcpCfgFileName OBJECT-TYPE
	SYNTAX      DisplayString
	ACCESS      read-only
	STATUS      mandatory
	DESCRIPTION		
		"The name of a ConfigFile to read/write  permanent database records.
		 If the value of this object is an empty string, then the
		 TCP module uses the default name `@file://TCPModule.cfg'. "
::= { usrTcp 2 }

usrTcpMaxConn	OBJECT-TYPE
	SYNTAX	INTEGER (0..4096)
	ACCESS	read-write
	STATUS	mandatory
	DESCRIPTION
		"The limit on the total number of TCP connections
           the entity can support.  In entities where the
           maximum number of connections is dynamic, this
           object should contain the value -1.

           This a read-write version of the tcpMaxConn object in rfc1213."
	--CONFIGURABLE
::= { usrTcp 3 }

usrTcpNagleStatus	OBJECT-TYPE
	SYNTAX	INTEGER {
               enable(1),       -- enable tcp nagle algorithm
               disable(0)       -- disable tcp nagle algorithm
               }
	ACCESS	read-write
	STATUS	mandatory
	DESCRIPTION
		"Enable or disable tcp Nagle Algorithm.  When read, it 
           returns the current setting"
	--CONFIGURABLE
::= { usrTcp 4 }

usrTcpKeepaliveStatus	OBJECT-TYPE
	SYNTAX	INTEGER {
               enable(1),       -- enable TCP keep-alives
               disable(0)       -- disable TCP keep-alives
               }
	ACCESS	read-write
	STATUS	mandatory
	DESCRIPTION
		"Enable or disable TCP keep-alives.  When read, it 
           returns the current setting."
	--CONFIGURABLE
::= { usrTcp 5 }

usrTcpKeepaliveInterval	OBJECT-TYPE
	SYNTAX	INTEGER (1..2147483)
	ACCESS	read-write
	STATUS	mandatory
	DESCRIPTION
		"The number of seconds of inactivity on a TCP session
		after which a TCP keep-alive packet is transmitted on
		the session to discover whether it is still active."
	--CONFIGURABLE
::= { usrTcp 6 }

usrTcpAheadofSegDropped	OBJECT-TYPE
	SYNTAX	INTEGER
	ACCESS	read-only
	STATUS	mandatory
	DESCRIPTION
	"Ahead of TCP sequences received and dropped counter can 
  	also be a good indication of network packet dropping"
::= { usrTcp 7 }

END         -- End Template MIB definitions

--
--
-- $Log: usr_tcp.mib,v $
-- Revision 1.2.2.2  1998/06/09 21:39:02  jlivermo
-- MR 4602 Added objects for TCP keep-alive status and interval.
--
-- Revision 1.2.2.1  1998/03/31 21:43:15  jwang
-- add CLI commands to disable or enable TCP Nagle Algorithm
--
-- Revision 1.2  1997/06/12 17:55:04  brant
-- changed tcp max conn upper limit to 4096
--
-- Revision 1.1  1997/06/04 20:55:14  jhalpin
-- Add usrTcp branch
--
--
-- Local Variables:
-- tab-width:5
-- tab-stop-list:( 5 10 15 20 25 30 35 40 45 50 55 60 65 70 75 80)
-- End:
--
USR-IGMP-MIB DEFINITIONS ::= BEGIN

IMPORTS
    OBJECT-TYPE, 
    Counter32, Integer32, IpAddress, Gauge32, TimeTicks  FROM SNMPv2-SMI
    RowStatus, TruthValue                                FROM SNMPv2-TC
    DisplayString, usrIgmp                               FROM USR-DEFINITIONS-MIB
    TRAP-TYPE                                            FROM RFC-1215;


usrIgmpInterfaceTable OBJECT-TYPE
    SYNTAX     SEQUENCE OF UsrIgmpInterfaceEntry
    MAX-ACCESS not-accessible
    STATUS     current
    DESCRIPTION
            "The (conceptual) table listing the interfaces on which IGMP
            is enabled."
    ::= { usrIgmp 1 }

usrIgmpInterfaceEntry OBJECT-TYPE
    SYNTAX     UsrIgmpInterfaceEntry
    MAX-ACCESS not-accessible
    STATUS     current
    DESCRIPTION
            "An entry (conceptual row) representing an interface on
            which IGMP is enabled."
    INDEX      { usrIgmpInterfaceIfName }
    ::= { usrIgmpInterfaceTable 1 }

UsrIgmpInterfaceEntry ::= SEQUENCE {
    usrIgmpInterfaceIfName                DisplayString,
    usrIgmpInterfaceQueryInterval         Integer32,
    usrIgmpInterfaceStatus                RowStatus,
    usrIgmpInterfaceVersion               INTEGER,
    usrIgmpInterfaceQuerier               IpAddress,
    usrIgmpInterfaceQueryMaxResponseTime  Integer32,
    usrIgmpInterfaceVersion1QuerierTimer  Integer32,                        
    usrIgmpInterfaceWrongVersionQueries   Counter32,                        
    usrIgmpInterfaceJoins                 Counter32,                        
    usrIgmpInterfaceGroups	          Gauge32,
    usrIgmpInterfaceRobustness            Integer32,
    usrIgmpInterfaceMcastFwdEnabled       TruthValue,
    usrIgmpInterfacePushEnabled           TruthValue,
    usrIgmpInterfaceProxyEnabled          TruthValue,
    usrIgmpInterfaceShortPackets          Counter32,
    usrIgmpInterfaceBadChecksum           Counter32,
    usrIgmpInterfaceQueriesReceived       Counter32,
    usrIgmpInterfaceReportsReceived       Counter32,
    usrIgmpInterfaceReportsForKnownGroups Counter32,
    usrIgmpInterfaceReportsSent           Counter32,
    usrIgmpInterfaceWrongVersionReports   Counter32
}

usrIgmpInterfaceIfName OBJECT-TYPE
    SYNTAX     DisplayString (SIZE (1..32))
    MAX-ACCESS not-accessible
    STATUS     current
    DESCRIPTION
            "The interface name for which IGMP is enabled."
::= { usrIgmpInterfaceEntry 1 }

usrIgmpInterfaceQueryInterval OBJECT-TYPE
    SYNTAX     Integer32 (5..65535)
    UNITS      "seconds"
    MAX-ACCESS read-create
    STATUS     current
    DESCRIPTION
            "The frequency at which IGMP Host-Query packets are
            transmitted on this interface."
    DEFVAL     { 125 }
    --CONFIGURABLE
::= { usrIgmpInterfaceEntry 2 }

usrIgmpInterfaceStatus OBJECT-TYPE
    SYNTAX     RowStatus
    MAX-ACCESS read-create
    STATUS     current
    DESCRIPTION
            "The activation of a row enables IGMP on the interface.  The
            destruction of a row disables IGMP on the interface."
    --CONFIGURABLE
::= { usrIgmpInterfaceEntry 3 }

usrIgmpInterfaceVersion OBJECT-TYPE
    SYNTAX     INTEGER { version1(1), version2(2) }
    MAX-ACCESS read-create
    STATUS     current
    DESCRIPTION
            "The version of IGMP which is running on this interface.
            This object can be used to configure a router capable of
            running either value.  For IGMP to function correctly, all   
            routers on a LAN must be configured to run the same version  
            of IGMP on that LAN."                                        
    DEFVAL     { version2 }
    --CONFIGURABLE
::= { usrIgmpInterfaceEntry 4 }

usrIgmpInterfaceQuerier OBJECT-TYPE
    SYNTAX     IpAddress
    MAX-ACCESS read-only
    STATUS     current
    DESCRIPTION
            "The address of the IGMP Querier on the IP subnet to which
            this interface is attached."
::= { usrIgmpInterfaceEntry 5 }

usrIgmpInterfaceQueryMaxResponseTime OBJECT-TYPE
    SYNTAX     Integer32 (1..10)
    UNITS      "seconds"
    MAX-ACCESS read-create
    STATUS     current
    DESCRIPTION
            "The maximum query response time advertised in IGMPv2
            queries on this interface.  Smaller values allow a router to
            prune groups faster."
    DEFVAL     { 10 }
    --CONFIGURABLE                                                    
::= { usrIgmpInterfaceEntry 6 }

usrIgmpInterfaceVersion1QuerierTimer OBJECT-TYPE                            
    SYNTAX     Integer32                                                 
    MAX-ACCESS read-only                                                 
    STATUS     current                                                   
    DESCRIPTION                                                          
            "The time remaining until the host assumes that there are no 
            IGMPv1 routers present on the interface.  While this is      
            non-zero, the host will reply to all queries with version 1  
            membership reports."                                         
::= { usrIgmpInterfaceEntry 7 }                                         

usrIgmpInterfaceWrongVersionQueries OBJECT-TYPE                             
    SYNTAX     Counter32                                                 
    MAX-ACCESS read-only                                                 
    STATUS     current                                                   
    DESCRIPTION                                                          
            "The number of queries received whose IGMP version does not  
            match usrIgmpInterfaceVersion.   IGMP requires that all routers 
            on a LAN be configured to run the same version of IGMP.      
            Thus, if any queries are received with the wrong version,    
            this indicates a configuration error."                       
::= { usrIgmpInterfaceEntry 8 }                                        

usrIgmpInterfaceJoins OBJECT-TYPE                                           
    SYNTAX     Counter32                                                 
    MAX-ACCESS read-only                                                 
    STATUS     current                                                   
    DESCRIPTION                                                          
            "The number of times a group membership has been added on    
            this interface; that is, the number of times an entry for    
            this interface has been added to the Cache Table.  This      
            object gives an indication of the amount of IGMP activity    
            over time."                                                  
::= { usrIgmpInterfaceEntry 9 }                                        

usrIgmpInterfaceGroups OBJECT-TYPE
    SYNTAX     Gauge32
    MAX-ACCESS read-only
    STATUS     current
    DESCRIPTION
            "The current number of entries for this interface in the
            Cache Table."
    ::= { usrIgmpInterfaceEntry 10 }

usrIgmpInterfaceRobustness OBJECT-TYPE
    SYNTAX     Integer32 (1..5)
    MAX-ACCESS read-create
    STATUS     current
    DESCRIPTION
            "The Robustness Variable allows tuning for the expected
            packet loss on a subnet.  If a subnet is expected to be
            lossy, the Robustness Variable may be increased.  IGMP is
            robust to (Robustness Variable-1) packet losses."
    DEFVAL     { 2 }
    --CONFIGURABLE                                                    
    ::= { usrIgmpInterfaceEntry 11 }

usrIgmpInterfaceMcastFwdEnabled OBJECT-TYPE                                          
    SYNTAX     TruthValue                                                 
    MAX-ACCESS read-create                                                 
    STATUS     current                                                   
    DESCRIPTION
            "If enabled Multicast packets will be forwarded on this
             interface."   
    DEFVAL    { true }
    --CONFIGURABLE                                                        
::= { usrIgmpInterfaceEntry 12 }                                        
 
usrIgmpInterfacePushEnabled OBJECT-TYPE                                          
    SYNTAX     TruthValue                                                 
    MAX-ACCESS read-create                                                 
    STATUS     current                                                   
    DESCRIPTION 
            "If enabled once a Multicast group is learned on this interface  
             it will not be removed even if a report is not received within
             the membership interval." 
    DEFVAL    { false }
    --CONFIGURABLE                         
::= { usrIgmpInterfaceEntry 13 }                                        

usrIgmpInterfaceProxyEnabled OBJECT-TYPE                                          
    SYNTAX     TruthValue                                                 
    MAX-ACCESS read-create                                                 
    STATUS     current                                                   
    DESCRIPTION 
            "If enabled when a Multicast group is learned on this interface  
             it will also be joined as a proxy on the ethernet interface 
             specified in usrIgmpInterfaceProxyIfName."
    DEFVAL    { false }
    --CONFIGURABLE                         
::= { usrIgmpInterfaceEntry 14 }                                        

usrIgmpInterfaceShortPackets OBJECT-TYPE
    SYNTAX     Counter32
    MAX-ACCESS read-only
    STATUS     current
    DESCRIPTION
            "The number of short IGMP packets received on this interface."
::= { usrIgmpInterfaceEntry 15 }
 
usrIgmpInterfaceBadChecksum OBJECT-TYPE
    SYNTAX     Counter32
    MAX-ACCESS read-only
    STATUS     current
    DESCRIPTION
            "The number of IGMP packets with bad checksum received on 
             this interface."
::= { usrIgmpInterfaceEntry 16 }
 
usrIgmpInterfaceQueriesReceived OBJECT-TYPE
    SYNTAX     Counter32
    MAX-ACCESS read-only
    STATUS     current
    DESCRIPTION
            "The number of queries received on this interface."
::= { usrIgmpInterfaceEntry 17 }
 
usrIgmpInterfaceReportsReceived OBJECT-TYPE
    SYNTAX     Counter32
    MAX-ACCESS read-only
    STATUS     current
    DESCRIPTION
            "The number of reports received on this interface."
::= { usrIgmpInterfaceEntry 18 }
 
usrIgmpInterfaceReportsForKnownGroups OBJECT-TYPE
    SYNTAX     Counter32
    MAX-ACCESS read-only
    STATUS     current
    DESCRIPTION
            "The number of reports for known groups received on this 
             interface."
::= { usrIgmpInterfaceEntry 19 }
 
usrIgmpInterfaceReportsSent OBJECT-TYPE
    SYNTAX     Counter32
    MAX-ACCESS read-only
    STATUS     current
    DESCRIPTION
            "The number of reports sent on this interface."
::= { usrIgmpInterfaceEntry 20 }

usrIgmpInterfaceWrongVersionReports OBJECT-TYPE
    SYNTAX     Counter32
    MAX-ACCESS read-only
    STATUS     current
    DESCRIPTION
            "The number of wrong version reports received on this interface."
::= { usrIgmpInterfaceEntry 21 }

--
--  The IGMP Cache Table
--

usrIgmpCacheTable OBJECT-TYPE
    SYNTAX     SEQUENCE OF UsrIgmpCacheEntry
    MAX-ACCESS not-accessible
    STATUS     current
    DESCRIPTION
            "The (conceptual) table listing the IP multicast groups for
            which there are members on a particular interface."
::= { usrIgmp 2 }

usrIgmpCacheEntry OBJECT-TYPE
    SYNTAX     UsrIgmpCacheEntry
    MAX-ACCESS not-accessible
    STATUS     current
    DESCRIPTION
            "An entry (conceptual row) in the usrIgmpCacheTable."
    INDEX      { usrIgmpCacheAddress, usrIgmpCacheIfName }
::= { usrIgmpCacheTable 1 }

UsrIgmpCacheEntry ::= SEQUENCE {
    usrIgmpCacheAddress            IpAddress,
    usrIgmpCacheIfName             DisplayString,
    usrIgmpCacheSelf               Integer32,
    usrIgmpCacheLastReporter       IpAddress,
    usrIgmpCacheUpTime             TimeTicks,
    usrIgmpCacheExpiryTime         TimeTicks,
    usrIgmpCacheStatus             RowStatus,
    usrIgmpCacheVersion1HostTimer  Integer32                                
}

usrIgmpCacheAddress OBJECT-TYPE
    SYNTAX     IpAddress
    MAX-ACCESS not-accessible
    STATUS     current
    DESCRIPTION
            "The IP multicast group address for which this entry
            contains information."
::= { usrIgmpCacheEntry 1 }

usrIgmpCacheIfName OBJECT-TYPE
    SYNTAX     DisplayString (SIZE (1..32))
    MAX-ACCESS not-accessible
    STATUS     current
    DESCRIPTION
            "The interface name for which this entry contains 
            information for an IP multicast group address."
::= { usrIgmpCacheEntry 2 }

usrIgmpCacheSelf OBJECT-TYPE
    SYNTAX     Integer32
    MAX-ACCESS read-create
    STATUS     current
    DESCRIPTION
            "An indication of whether the local system is a member of
            or proxying this group address on this interface."
::= { usrIgmpCacheEntry 3 }

usrIgmpCacheLastReporter OBJECT-TYPE
    SYNTAX     IpAddress
    MAX-ACCESS read-only
    STATUS     current
    DESCRIPTION
            "The IP address of the source of the last membership report
            received for this IP Multicast group address on this
            interface.  If no membership report has been received, this
            object has the value 0.0.0.0."
::= { usrIgmpCacheEntry 4 }

usrIgmpCacheUpTime OBJECT-TYPE
    SYNTAX     TimeTicks
    MAX-ACCESS read-only
    STATUS     current
    DESCRIPTION
            "The time since the system joined this group address, or
            zero if the system is not currently a member."
::= { usrIgmpCacheEntry 5 }

usrIgmpCacheExpiryTime OBJECT-TYPE
    SYNTAX     TimeTicks
    MAX-ACCESS read-only
    STATUS     current
    DESCRIPTION
            "The minimum amount of time remaining before this entry will
            be aged out."
::= { usrIgmpCacheEntry 6 }

usrIgmpCacheStatus OBJECT-TYPE
    SYNTAX     RowStatus
    MAX-ACCESS read-create
    STATUS     current
    DESCRIPTION
            "The status of this entry."
    --CONFIGURABLE                                                        
::= { usrIgmpCacheEntry 7 }

usrIgmpCacheVersion1HostTimer OBJECT-TYPE                                   
    SYNTAX     Integer32
    UNITS      "seconds"
    MAX-ACCESS read-only
    STATUS     current
    DESCRIPTION
            "The time remaining until the local router will assume that
            there are no longer any IGMP version 1 members on the IP     
            subnet attached to this interface.  Upon hearing any IGMPv1
            Membership Report, this value is reset to the group
            membership timer.  While this time remaining is non-zero,
            the local router ignores any IGMPv2 Leave messages for this  
            group that it receives on this interface."                   
::= { usrIgmpCacheEntry 8 }

usrIgmpProxyInterface OBJECT-TYPE
    SYNTAX     DisplayString (SIZE (1..32))
    MAX-ACCESS read-create                                                 
    STATUS     current                                                   
    DESCRIPTION 
            "The name of the interface on which all groups learned 
             on the wan connections will be proxied onto if 
             usrIgmpInterfaceProxyEnabled is enabled."
    --CONFIGURABLE                         
::= { usrIgmp 3 }

usrIgmpHeartbeatGroup OBJECT IDENTIFIER ::= { usrIgmp 4 }


usrIgmpHeartbeatInterface OBJECT-TYPE
    SYNTAX     DisplayString (SIZE (1..32))
    MAX-ACCESS read-write                                                 
    STATUS     current                                                   
    DESCRIPTION 
            "The name of the interface on which to monitor
             multicast traffic for group specified in
             usrIgmpHeartbeatGroupAddr."
    --CONFIGURABLE                         
::= { usrIgmpHeartbeatGroup 1 }

usrIgmpHeartbeatGroupAddr OBJECT-TYPE
    SYNTAX     IpAddress
    MAX-ACCESS read-write
    STATUS     current
    DESCRIPTION
            "The multicast group being monitored."
    --CONFIGURABLE                         
::= { usrIgmpHeartbeatGroup 2 }

usrIgmpHeartbeatTime OBJECT-TYPE                                   
    SYNTAX     INTEGER (0..65535)
    UNITS      "seconds"
    MAX-ACCESS read-write
    STATUS     current
    DESCRIPTION
            "The time interval to monitor multicast traffic."
    DEFVAL     { 60 }
    --CONFIGURABLE                                                    
::= { usrIgmpHeartbeatGroup 3 }

usrIgmpHeartbeatWindow OBJECT-TYPE
    SYNTAX     INTEGER (0..255)
    MAX-ACCESS read-write
    STATUS     current
    DESCRIPTION
            "The number of usrIgmpHeartbeatTime intervals to monitor 
             multicast traffic on."
    DEFVAL     { 5 }
    --CONFIGURABLE                                                    
::= { usrIgmpHeartbeatGroup 4 }

usrIgmpHeartbeatThreshold OBJECT-TYPE
    SYNTAX     INTEGER (0..65535)
    MAX-ACCESS read-write
    STATUS     current
    DESCRIPTION
            "If multicast traffic in not received for this number or 
             more intervals a SNMP trap is issued."
    DEFVAL     { 3 }
    --CONFIGURABLE                                                    
::= { usrIgmpHeartbeatGroup 5 }

usrIgmpHeartbeatStatus OBJECT-TYPE
   SYNTAX      INTEGER {
                enabled(1),
                disabled(2),
                delete(3)
                }
   MAX-ACCESS  read-write
   STATUS      current
   DESCRIPTION
           "This object is used to allow the system to start or
            or stop the IGMP heartbeat feature.  This heartbeat
            feature is used to monitor multicast traffic for a 
            particular multicast group (usrIgmpHeartbeatGroupAddr)
            on a specified interface (usrIgmpHeartbeatInterface).  
            Traffic is monitored on this interface for 
            usrIgmpHeartbeatWindowSize usrIgmpHeartbeatTime intervals.
            During each time interval it is determined if multicast
            traffic was received.  After usrIgmpHeartbeatWindowSize
            time intervals the number of times we did NOT receive 
            traffic is compared against usrIgmpHeartbeatThreshold. If
            the number of intervals we did NOT receive traffic is 
            equal to or higher than usrIgmpHeartbeatThreshold a SNMP 
            trap is issued." 
    --CONFIGURABLE                                                    
::= { usrIgmpHeartbeatGroup 6 }

usrIgmpTraps OBJECT IDENTIFIER ::= { usrIgmp 5 }

usrIgmpHeartbeatTrap TRAP-TYPE
   ENTERPRISE usrIgmpTraps
   VARIABLES { usrIgmpHeartbeatThreshold }
   DESCRIPTION
	   "A usrIgmpHeartbeatTrap signifies that the configured 
            number of time intervals have occurred without receiving 
            multicast traffic for the configured group."
::= 1

usrIgmpTrafficAffectInactivity OBJECT-TYPE
   SYNTAX      INTEGER {
                enabled(1),
                disabled(2)
                }
   MAX-ACCESS  read-write
   STATUS      current
   DESCRIPTION
           "This object is used to allow the system to treat IGMP traffic 
	    over PPP links as background traffic. If this switch is enabled 
	    then IGMP traffic will be treated as background traffic and idle 
	    timeout functionality will ignore this traffic. If this switch 
	    is disabled the IGMP multicast traffic will be treated as regular
	    traffic and connection will not be dropped." 
    --CONFIGURABLE                                                    
::= { usrIgmp 6 }

END         -- End Template MIB definitions

--
--     usr_mpip.mib -  A template MIB file for Pilgrim MIB modules
--		
--
--	Description:	This module contains MIB definitions for the 
--      		MPIP Process
--
--	Author:	Balaji Tamirisa
--
--	
--
--  ----------------------------------------------------------------------
-- | Copyright (c) 1995 U.S. Robotics Access Corp., Skokie, IL 60076      |
-- |                                                                      |
-- | The information in this software is subject to change without notice |
-- | and should not be construed as a commitment by U.S. Robotics Access  |
-- | Corp.                                                                |
-- |                                                                      |
-- | U.S. Robotics Access Corp. assumes no responsibility for the use or  |
-- | reliability of its software on equipment which is not supplied by    |
-- | U.S. Robotics Access Corp.                                           |
-- |                                                                      |
-- | This software is furnished under a license and may be copied only    |
-- | with the inclusion of the above copyright notice. This software, or  |
-- | any other copies thereof, may not be provided or otherwise made      |
-- | available to any other person except to one who agrees to these      |
-- | license terms. Title to and ownership of the software shall at all   |
-- | times remain in U.S. Robotics Access Corp.                           |
--  ----------------------------------------------------------------------
--


USR-MPIP-MIB DEFINITIONS ::= BEGIN

          IMPORTS
               RowStatus
                FROM SNMPv2-TC
               IpAddress
                    FROM RFC1155-SMI
               OBJECT-TYPE
                    FROM RFC-1212
               DisplayString, usrMPIP, UsrConfigStatus
                    FROM USR-DEFINITIONS-MIB;

          -- All representations of MAC addresses in this MIB Module use,
          -- as a textual convention (i.e. this convention does not affect
          -- their encoding), the data type:

          usrMPIPBase      OBJECT IDENTIFIER ::= { usrMPIP 1 }
          
          --
          -- The MPIP Base Group.
          --

          usrMPIPBaseCfgFileName OBJECT-TYPE
              SYNTAX   DisplayString
              ACCESS   read-write
              STATUS   mandatory
              DESCRIPTION
                      "The name of a ConfigFile to read/write
                      permanent database records. If the value of this
                      object is an empty string, then the PPP process
                      uses the default name `@file://MPIPProcess.cfg'."
              ::= { usrMPIPBase 1 }

          usrMPIPBaseCFMSaveStatus OBJECT-TYPE
              SYNTAX  UsrConfigStatus
              ACCESS  read-write
              STATUS  mandatory
              DESCRIPTION
                      "Setting the value of this object to `save'
                      causes the values of the MPIP Base Group
                      entries to be written out to the current MPIP
                      config file. While the new config file is being
                      written, the MPIP process will set the value
                      of this flag set to `saving''. Any attempts to set
                      the value while it is  not `normal' (i.e. the file
                      is currently being written to the config file)
                      while result in a badValue error being returned.
                      Setting the value to `normal' will result in no
                      action."
              ::= { usrMPIPBase 2 }


          usrMPIPServerStatus OBJECT-TYPE
              SYNTAX  INTEGER {
                        on(1),
                        off(0)
                      }
              ACCESS   read-write
              STATUS   mandatory
              DESCRIPTION
                      "Indicates whether MPIP server is turned off or on."
              DEFVAL { 0 }
              --CONFIGURABLE
              ::= { usrMPIPBase 3 }


          usrMPIPClientStatus OBJECT-TYPE
              SYNTAX  INTEGER {
                        turned-on(1),
                        turned-off(0)
                      }
              ACCESS   read-write
              STATUS   mandatory
              DESCRIPTION
                      "Indicates whether MPIP Client is turned off or on."
              DEFVAL { 0 }
              --CONFIGURABLE
              ::= { usrMPIPBase 4 }

          usrMPIPUDPPort OBJECT-TYPE
			  SYNTAX    INTEGER
			  ACCESS    read-write
			  STATUS    mandatory
              DESCRIPTION
                      "Indicates the UDP Port used by MPIP process\n"
              DEFVAL { 5912 }
              --CONFIGURABLE
              ::= { usrMPIPBase 5 }


           usrMPIPGlobalSharedSecret OBJECT-TYPE
              SYNTAX   OCTET STRING (SIZE(16))
              ACCESS   read-write
              STATUS   mandatory
              DESCRIPTION
                      "Indicates the shared secret for auto-configuration."
              --CONFIGURABLE
              ::= { usrMPIPBase 6 }

          --
          -- The Client Entry Table.
          --
          -- The following object reflect the Entries in the
          -- MPIP Client Entry Table
          --   usrMPIPClientIpaddr
          --   usrMPIPSharedSecret

          usrMPIPClientEntryTable   OBJECT-TYPE
               SYNTAX    SEQUENCE OF UsrMPIPClientEntry
               ACCESS    not-accessible
               STATUS    mandatory
               DESCRIPTION
                         "Table containing the MPIP client IP addresses
                           and shared secrets."
               ::= { usrMPIPBase 7 }


          usrMPIPClientEntry   OBJECT-TYPE
               SYNTAX    UsrMPIPClientEntry
               ACCESS    not-accessible
               STATUS    mandatory
               DESCRIPTION
                         "Each entry in the Client Entry Table."
               INDEX     { usrMPIPClientIpaddr }
               ::= { usrMPIPClientEntryTable 1 }


          UsrMPIPClientEntry ::= SEQUENCE {
               usrMPIPClientIpaddr 		IpAddress,
               usrMPIPClientSharedSecret 	OCTET STRING,
               usrMpipcStatus            	RowStatus,
               usrMPIPClientType			INTEGER,
               usrMPIPClientEntryType 		OCTET STRING
          }


          usrMPIPClientIpaddr OBJECT-TYPE
               SYNTAX    IpAddress
               ACCESS     not-accessible 
               STATUS     mandatory
               DESCRIPTION
                         "The unique identifier of the MPIP Client."
               ::= { usrMPIPClientEntry 1 }


          usrMPIPClientSharedSecret OBJECT-TYPE
               SYNTAX  OCTET STRING (SIZE(16))
               ACCESS    read-write
               STATUS    mandatory
               DESCRIPTION
                         "The Shared secret between MPIP Client 
                          and Server."
               --CONFIGURABLE
               ::= { usrMPIPClientEntry 2 }

  	  usrMpipcStatus OBJECT-TYPE
               SYNTAX          RowStatus
               ACCESS          read-write
               STATUS          mandatory
               DESCRIPTION
                         "The status of this row of the MPIP 
                          Client Table." 
               --CONFIGURABLE
               ::= { usrMPIPClientEntry 3 }

          usrMPIPClientType	OBJECT-TYPE
				SYNTAX		INTEGER {
							hiper(0),
							netserver(1)
							}
				ACCESS		read-write
				STATUS		mandatory
				DESCRIPTION
						"Tells whether the client is a HiperARC or Netserver"
				--CONFIGURABLE
				::= { usrMPIPClientEntry 4 }

          usrMPIPClientEntryType OBJECT-TYPE
               SYNTAX  OCTET STRING
               ACCESS    read-only
               STATUS    mandatory
               DESCRIPTION
                         "Is the client added dynamically or statically?"
               ::= { usrMPIPClientEntry 5 }

          --
          -- The Server Entry Table.
          --
          --  The following object reflect the Entries in the
          --  MPIP Server Entry Table
          --  usrMPIPServerIpaddr
          --  usrMPIPServerPortNum
          --  usrMPIPServerSharedSecret
          --  usrMPIPCurrentState
          --  usrMPIPSendSequenceNum
          --  usrMPIPExpectedSequenceNum 
          --  usrMPIPLastExpectedSequenceNum
          --  usrMPIPSentTime
          --  usrMPIPIdentification
          --  usrMPIPRetransmit

        usrMPIPServerEntryTable   OBJECT-TYPE
               SYNTAX    SEQUENCE OF UsrMPIPServerEntry
               ACCESS    not-accessible
               STATUS    mandatory
               DESCRIPTION
                         "Table containing the MPIP server IP addresse,
 	            UDP port number, shared secret, current state,
                           send sequence number, expected sequence number,
                           last expected sequence number, MPIP sent time,
                           MPIP ID and MPIP retransmit."
               ::= { usrMPIPBase 8 }


          usrMPIPServerEntry   OBJECT-TYPE
               SYNTAX    UsrMPIPServerEntry
               ACCESS    not-accessible
               STATUS    mandatory
               DESCRIPTION
                         "Each entry in the Server Entry Table."
               INDEX     { usrMPIPServerIpaddr }
               ::= { usrMPIPServerEntryTable 1 }

          UsrMPIPServerEntry ::= SEQUENCE {
               	usrMPIPServerIpaddr 		IpAddress,
				usrMPIPServerPortNum 		INTEGER,
                usrMPIPServerSharedSecret 	OCTET STRING,
				usrMPIPServerPreference 	INTEGER,
                usrMpipsStatus            	RowStatus,
                usrMPIPServerEntryType          OCTET STRING
           }

           usrMPIPServerIpaddr OBJECT-TYPE
               SYNTAX    IpAddress
               ACCESS    not-accessible
               STATUS     mandatory
               DESCRIPTION
                         "The unique identifier of the MPIP Server."
               ::= { usrMPIPServerEntry 1 }

           usrMPIPServerPortNum OBJECT-TYPE
               SYNTAX    INTEGER 
               ACCESS    read-write
               STATUS    mandatory
               DESCRIPTION
                         "The Server UDP Port Number."
               --CONFIGURABLE
               ::= { usrMPIPServerEntry 2 }

           usrMPIPServerSharedSecret OBJECT-TYPE
               SYNTAX  OCTET STRING (SIZE(16))
               ACCESS    read-write
               STATUS    mandatory
               DESCRIPTION
                         "The Server's Shared secret with Client."
               --CONFIGURABLE
               ::= { usrMPIPServerEntry 3 }


           usrMPIPServerPreference OBJECT-TYPE
               SYNTAX    INTEGER 
               ACCESS    read-write
               STATUS    mandatory
               DESCRIPTION
                         "The Server Priority."
               --CONFIGURABLE
               ::= { usrMPIPServerEntry 4 }

           usrMpipsStatus OBJECT-TYPE
               SYNTAX    RowStatus
               ACCESS    read-write
               STATUS    mandatory
               DESCRIPTION
                         "Row status."
               --CONFIGURABLE
               ::= { usrMPIPServerEntry 5 }

          usrMPIPServerEntryType OBJECT-TYPE
               SYNTAX  OCTET STRING
               ACCESS    read-only
               STATUS    mandatory
               DESCRIPTION
                         "Is the server added dynamically or statically?"
               ::= { usrMPIPServerEntry 6 }

          --
          -- The Bundle Table 
          --
          --  The following object reflect the Entries in the
		  --  MPIP Bundle Index
          --  MPIP Bundle Table 
          --  usrMPIPBundleEdoType
          --  usrMPIPBundleEdoValue
          --  usrMPIPBundleUsername
          --  usrMPIPBundleCount
 
          usrMPIPBundleTable   OBJECT-TYPE
               SYNTAX    SEQUENCE OF UsrMPIPBundleEntry
               ACCESS    not-accessible
               STATUS    mandatory
               DESCRIPTION
                         "Table containing the MPIP Bundle & links."
               ::= { usrMPIPBase 9 }
 
          usrMPIPBundleEntry   OBJECT-TYPE
               SYNTAX    UsrMPIPBundleEntry
               ACCESS    not-accessible
               STATUS    mandatory
               DESCRIPTION
                         "Each entry in the Bundle Table." 
               INDEX     { usrMPIPBundleIndex }
               ::= { usrMPIPBundleTable 1 }
 
          UsrMPIPBundleEntry ::= SEQUENCE {
                usrMPIPBundleIndex		INTEGER,
                usrMPIPBundleUsername		OCTET STRING,
                usrMPIPBundleEdoType		INTEGER,
                usrMPIPBundleEdoValue		OCTET STRING,
               	usrMPIPBundleOwner 		IpAddress,
                usrMPIPNumOfLinks               INTEGER
           }


           usrMPIPBundleIndex OBJECT-TYPE
               SYNTAX    INTEGER 
               ACCESS    read-write 
               STATUS    mandatory
               DESCRIPTION
                         "The bundle index number "
               ::= { usrMPIPBundleEntry 1 }

           usrMPIPBundleUsername OBJECT-TYPE
               SYNTAX    OCTET STRING (SIZE(64))
               ACCESS    read-write 
               STATUS    mandatory
               DESCRIPTION
                         "User name." 
               ::= { usrMPIPBundleEntry 2 }

           usrMPIPBundleEdoType OBJECT-TYPE
               SYNTAX    INTEGER 
               ACCESS    read-write 
               STATUS    mandatory
               DESCRIPTION
                         "The EDO type." 
               --CONFIGURABLE
               ::= { usrMPIPBundleEntry 3 }

           usrMPIPBundleEdoValue OBJECT-TYPE
               SYNTAX    OCTET STRING (SIZE(20))
               ACCESS    read-write 
               STATUS    mandatory
               DESCRIPTION
                         "The EDO value." 
               --CONFIGURABLE
               ::= { usrMPIPBundleEntry 4 }

           usrMPIPBundleOwner OBJECT-TYPE
               SYNTAX    IpAddress 
               ACCESS    read-write
               STATUS    mandatory
               DESCRIPTION
                         "Bundle Owner."
               ::= { usrMPIPBundleEntry 5 }

           usrMPIPNumOfLinks OBJECT-TYPE
               SYNTAX    INTEGER
               ACCESS    read-write
               STATUS    mandatory
               DESCRIPTION
                         "The number of links per bundle." 
               --CONFIGURABLE
               ::= { usrMPIPBundleEntry 6 }

          --
          -- The Link Table
          --
          --  The following object reflect the Entries in the
          --  MPIP Link Table
          --  usrMPIPLinkOwner
          --  usrMPIPBundleOwner
          --  usrMPIPLinkIdentifier
          --  usrMPIPLinkBundleUsername
          --  usrMPIPLinkStatus

          usrMPIPLinkTable   OBJECT-TYPE
               SYNTAX    SEQUENCE OF UsrMPIPLinkEntry
               ACCESS    not-accessible
               STATUS    mandatory
               DESCRIPTION
                         "Table containing the MPIP Bundle & links."
               ::= { usrMPIPBase 10 }
 
          usrMPIPLinkEntry   OBJECT-TYPE
               SYNTAX    UsrMPIPLinkEntry
               ACCESS    not-accessible
               STATUS    mandatory
               DESCRIPTION 
                         "Each entry in the Bundle Table."
               INDEX     { usrMPIPBundleUsername }
               ::= { usrMPIPLinkTable 1 }
 
          UsrMPIPLinkEntry ::= SEQUENCE {
                usrMPIPLinkNum              INTEGER, 
                usrMPIPLinkBundleOwner      IpAddress, 
                usrMPIPLinkOwner            IpAddress, 
                usrMPIPLinkIdentifier       INTEGER,
                usrMPIPLinkBundleUsername   OCTET STRING,
                usrMpipLinkStatus           RowStatus
           }
 
           usrMPIPLinkNum OBJECT-TYPE
               SYNTAX    INTEGER 
               ACCESS    read-write
               STATUS    mandatory
               DESCRIPTION
                         "Link Identifier."
               ::= { usrMPIPLinkEntry 1 }

           usrMPIPLinkBundleOwner OBJECT-TYPE
               SYNTAX    IpAddress 
               ACCESS    read-write
               STATUS    mandatory
               DESCRIPTION
                         "Bundle Owner."
               ::= { usrMPIPLinkEntry 2 }

           usrMPIPLinkOwner OBJECT-TYPE
               SYNTAX    IpAddress 
               ACCESS    read-write
               STATUS    mandatory
               DESCRIPTION
                         "Link Owner."
               --CONFIGURABLE
               ::= { usrMPIPLinkEntry 3 }

           usrMPIPLinkIdentifier OBJECT-TYPE
               SYNTAX    INTEGER
               ACCESS    read-write
               STATUS    mandatory
               DESCRIPTION
                         "Link Identifier."
               --CONFIGURABLE
               ::= { usrMPIPLinkEntry 4 }  

           usrMPIPLinkBundleUsername OBJECT-TYPE
               SYNTAX    OCTET STRING (SIZE(64))
               ACCESS    read-write
               STATUS    mandatory
               DESCRIPTION
                         "The EDO type."
               --CONFIGURABLE
               ::= { usrMPIPLinkEntry 5 }
 
           usrMpipLinkStatus OBJECT-TYPE
               SYNTAX          RowStatus
               ACCESS          read-write
               STATUS          mandatory
               DESCRIPTION
                         "The status of this row of the Link Table."
               --CONFIGURABLE
               ::= { usrMPIPLinkEntry 6 }
 
		  --
		  --

          usrMPIPLocalLinkTable   OBJECT-TYPE
               SYNTAX    SEQUENCE OF UsrMPIPLocalLinkEntry
               ACCESS    not-accessible
               STATUS    mandatory
               DESCRIPTION
                         "Table containing the MPIP local links."
               ::= { usrMPIPBase 11 }


          usrMPIPLocalLinkEntry   OBJECT-TYPE
               SYNTAX    UsrMPIPLocalLinkEntry
               ACCESS    not-accessible
               STATUS    mandatory
               DESCRIPTION 
                         "Each entry in the Bundle Table."
               INDEX     { usrMPIPLocalLinkUsername }
               ::= { usrMPIPLocalLinkTable 1 }

          UsrMPIPLocalLinkEntry ::= SEQUENCE {
                usrMPIPLocalLinkCount       INTEGER,
                usrMPIPLocalLinkBundleOwner      IpAddress, 
                usrMPIPLocalLinkUsername   OCTET STRING
           }

           usrMPIPLocalLinkCount OBJECT-TYPE
               SYNTAX    INTEGER
               ACCESS    read-only
               STATUS    mandatory
               DESCRIPTION
                         "Link Count."
               --CONFIGURABLE
               ::= { usrMPIPLocalLinkEntry 1 }  

           usrMPIPLocalLinkBundleOwner OBJECT-TYPE
               SYNTAX    IpAddress 
               ACCESS    read-only
               STATUS    mandatory
               DESCRIPTION
                         "Bundle Owner."
               ::= { usrMPIPLocalLinkEntry 2 }

           usrMPIPLocalLinkUsername OBJECT-TYPE
               SYNTAX    OCTET STRING (SIZE(64))
               ACCESS    read-only
               STATUS    mandatory
               DESCRIPTION
                         "The user name."
               --CONFIGURABLE
               ::= { usrMPIPLocalLinkEntry 3 }
          
          usrMPIPACEStatus OBJECT-TYPE
              SYNTAX  INTEGER {
                        on(1),
                        off(0)
                      }
              ACCESS   read-write
              STATUS   mandatory
              DESCRIPTION
                      "Indicates whether MPIP ACE_AUTH is turned off or on."
              DEFVAL { 0 }
              --CONFIGURABLE
              ::= { usrMPIPBase 12 }

END
--
--	usr_dns.mib - A proprietary MIB file for the Domain Name Service
--
--
-- Author:         Clarise E. Patton
--
-- $Id: usr_dns.mib,v 1.5.10.2 1997/12/19 13:20:25 psd Exp $
--
--  | Copyright (c) 1995 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-DNS-MIB DEFINITIONS ::= BEGIN

	IMPORTS
	  RowStatus
                FROM SNMPv2-TC
          Counter, IpAddress
                FROM RFC1155-SMI
          OBJECT-TYPE, Integer32
                FROM SNMPv2-SMI
          DisplayString, UsrConfigStatus, usrDns
                FROM USR-DEFINITIONS-MIB
          DnsName, DnsClass, DnsType, DnsQClass, DnsQType, DnsTime
                FROM DNS-SERVER-MIB;



   -- Begin managed object definitions here...

usrDnsVersion OBJECT-TYPE
	SYNTAX		DisplayString
	MAX-ACCESS		read-only
	STATUS		current
	DESCRIPTION
		"The current software version of the Domain Name Server."
::= { usrDns 1 }

usrDnsCFMStatusFlag OBJECT-TYPE
	SYNTAX		UsrConfigStatus
	MAX-ACCESS		read-write
	STATUS		current
	DESCRIPTION
	"This variable controls saving and loading of all the configuration
           information for the Domain Name Service. The value can 
           be set to either save or load by a management station. The other
           values indicate if any configuration operation and what type
           is in progress."
::= { usrDns 2 }

usrDnsCfgFileName OBJECT-TYPE
	SYNTAX      DisplayString
	MAX-ACCESS      read-write
	STATUS      current
	DESCRIPTION		
		"The name of a ConfigFile to read/write  permanent database records.
		 If the value of this object is an empty string, then the
		 DNS module uses the default name `@file://DNS.cfg'. "
	--CONFIGURABLE
::= { usrDns 3 }

usrDnsDomainName OBJECT-TYPE
	SYNTAX      DisplayString
	MAX-ACCESS      read-write
	STATUS      current
	DESCRIPTION		
		"The default Domain Name to be appended to a Host Name if
           it cannot be resolved without a Domain Name."
	--CONFIGURABLE
::= { usrDns 4 }

usrDnsNumberRetries OBJECT-TYPE
     SYNTAX   INTEGER (1..5)
     MAX-ACCESS   read-write
     STATUS   current
     DESCRIPTION
            "The number of times DNS will attempt to resolve a name before
             determining it cannot be resolved."
	--CONFIGURABLE
::= { usrDns 5 }

usrDnsTimeout OBJECT-TYPE
     SYNTAX   INTEGER
     MAX-ACCESS   read-write
     STATUS   current
     DESCRIPTION
            "The number of seconds DNS will wait for a response from
             a name server before determining it is not coming."
	--CONFIGURABLE
::= { usrDns 6 }

usrDnsQueries OBJECT-TYPE
     SYNTAX   Counter
     MAX-ACCESS   read-only
     STATUS   current
     DESCRIPTION
            "The total number of queries received by DNS"
::= { usrDns 7 }

usrDnsTotalResponses OBJECT-TYPE
     SYNTAX   Counter
     MAX-ACCESS   read-only
     STATUS   current
     DESCRIPTION
            "The total number of responses sent by DNS"
::= { usrDns 8 }

usrDnsResponseOK OBJECT-TYPE
     SYNTAX   Counter
     MAX-ACCESS   read-only
     STATUS   current
     DESCRIPTION
            "The number of success responses received by DNS"
::= { usrDns 9 }

usrDnsResponseFormat OBJECT-TYPE
     SYNTAX   Counter
     MAX-ACCESS   read-only
     STATUS   current
     DESCRIPTION
            "The number of Format Error responses received by DNS"
::= { usrDns 10 }

usrDnsResponseServer OBJECT-TYPE
     SYNTAX   Counter
     MAX-ACCESS   read-only
     STATUS   current
     DESCRIPTION
            "The number of Server Error responses received by DNS"
::= { usrDns 11 }

usrDnsResponseName OBJECT-TYPE
     SYNTAX   Counter
     MAX-ACCESS   read-only
     STATUS   current
     DESCRIPTION
            "The number of No Such Name responses received by DNS"
::= { usrDns 12 }

usrDnsResponseNIY OBJECT-TYPE
     SYNTAX   Counter
     MAX-ACCESS   read-only
     STATUS   current
     DESCRIPTION
            "The number of NIY responses sent by DNS.
	This indicates that the Server does not implement this operation"
::= { usrDns 13 }

usrDnsResponseRefused OBJECT-TYPE
     SYNTAX   Counter
     MAX-ACCESS   read-only
     STATUS   current
     DESCRIPTION
            "The number of Refused responses sent by DNS.
	This indicates the Server refuses to perform the operation."
::= { usrDns 14 }

usrDnsResponsesLocal OBJECT-TYPE
     SYNTAX   Counter
     MAX-ACCESS   read-only
     STATUS   current
     DESCRIPTION
            "The number of responses answered Locally by DNS"
::= { usrDns 15 }

usrDnsResponsesRemote OBJECT-TYPE
     SYNTAX   Counter
     MAX-ACCESS   read-only
     STATUS   current
     DESCRIPTION
            "The number of responses received by DNS"
::= { usrDns 16 }

usrDnsResponseBadProt OBJECT-TYPE
     SYNTAX   Counter
     MAX-ACCESS   read-only
     STATUS   current
     DESCRIPTION
            "The number of corrupted responses received by DNS"
::= { usrDns 17 }

usrDnsTimeOuts OBJECT-TYPE
     SYNTAX   Counter
     MAX-ACCESS   read-only
     STATUS   current
     DESCRIPTION
            "The total number of timeouts on requests sent by DNS"
::= { usrDns 18 }

usrDnsResponseNotSent OBJECT-TYPE
     SYNTAX   Counter
     MAX-ACCESS   read-only
     STATUS   current
     DESCRIPTION
            "The number of send failures on replies sent by DNS"
::= { usrDns 19 }

usrDnsErrorResponse OBJECT-TYPE
     SYNTAX   Counter
     MAX-ACCESS   read-only
     STATUS   current
     DESCRIPTION
            "The number of failure  replies sent by DNS"
::= { usrDns 20 }

usrDnsHostTable OBJECT-TYPE
	SYNTAX SEQUENCE OF UsrDnsHostEntry
	MAX-ACCESS not-accessible
	STATUS current
	DESCRIPTION
		"The table of DNS Hosts. "
::= { usrDns 21 }

usrDnsHostEntry OBJECT-TYPE
	SYNTAX UsrDnsHostEntry
	MAX-ACCESS not-accessible
	STATUS current
	DESCRIPTION
		"A (conceptual) entry for one Dns Host."
	INDEX { usrDnsHostName }
::= { usrDnsHostTable 1 }

UsrDnsHostEntry ::= SEQUENCE {
	usrDnsHostName			DisplayString,
	usrDnsHostAddress		IpAddress,
	usrDnsHostStatus     	        RowStatus
	}

usrDnsHostName OBJECT-TYPE
	SYNTAX		DisplayString
	MAX-ACCESS		not-accessible
	STATUS		current
	DESCRIPTION
		"The logical identifier of the Host Table. "
::= { usrDnsHostEntry 1 }

usrDnsHostAddress OBJECT-TYPE
	SYNTAX		IpAddress
	MAX-ACCESS		read-write
	STATUS		current
	DESCRIPTION
		"The specified or resolved ip address of the named Host. "
	--CONFIGURABLE
::= { usrDnsHostEntry 2 }

usrDnsHostStatus OBJECT-TYPE
	SYNTAX		RowStatus
	MAX-ACCESS		read-write
	STATUS		current
	DESCRIPTION
		"The status of this row of the Host Table. "
	--CONFIGURABLE
::= { usrDnsHostEntry 3 }

usrDnsServerTable OBJECT-TYPE
	SYNTAX SEQUENCE OF UsrDnsServerEntry
	MAX-ACCESS not-accessible
	STATUS current
	DESCRIPTION
		"The table of DNS Servers. "
::= { usrDns 22 }
usrDnsServerEntry OBJECT-TYPE
	SYNTAX UsrDnsServerEntry
	MAX-ACCESS not-accessible
	STATUS current
	DESCRIPTION
		"A (conceptual) entry for one Dns Server."
	INDEX { usrDnsServerPreference }
::= { usrDnsServerTable 1 }

UsrDnsServerEntry ::= SEQUENCE {
	usrDnsServerPreference		INTEGER,
	usrDnsServerName		DisplayString,
	usrDnsServerAddress		IpAddress,
	usrDnsServerStatus     	        RowStatus
	}

usrDnsServerPreference OBJECT-TYPE
	SYNTAX		INTEGER
	MAX-ACCESS		not-accessible
	STATUS		current
	DESCRIPTION
		"The logical identifier of the Server Table. "
::= { usrDnsServerEntry 1 }

usrDnsServerName OBJECT-TYPE
	SYNTAX		DisplayString
	MAX-ACCESS		read-write
	STATUS		current
	DESCRIPTION
		"The specified name of the Server. "
	--CONFIGURABLE
::= { usrDnsServerEntry 2 }

usrDnsServerAddress OBJECT-TYPE
	SYNTAX		IpAddress
	MAX-ACCESS		read-write
	STATUS		current
	DESCRIPTION
		"The specified or resolved ip address of the named Server. "
	--CONFIGURABLE
::= { usrDnsServerEntry 3 }

usrDnsServerStatus OBJECT-TYPE
	SYNTAX		RowStatus
	MAX-ACCESS		read-write
	STATUS		current
	DESCRIPTION
		"The status of this row of the Server Table. "
	--CONFIGURABLE
::= { usrDnsServerEntry 4 }

usrDnsHostRotation OBJECT-TYPE
     SYNTAX   INTEGER { enabled(1), disabled(2) }
     MAX-ACCESS   read-write
     STATUS   current
     DESCRIPTION
            "Setting this object to a value of enabled(1) will enable
             the DNS host rotation feature. Setting this object to
             disabled(2) will disable the DNS Host Rotation feature."
     --CONFIGURABLE
::= { usrDns 23 }

-- Resolver Cache Table

usrDnsCacheTable OBJECT-TYPE
    SYNTAX      SEQUENCE OF UsrDnsCacheEntry
    MAX-ACCESS  not-accessible
    STATUS      current
    DESCRIPTION
           "This table contains information about all the resource
           records currently in the resolver's cache."
::= { usrDns 24 }

usrDnsRoundRobin OBJECT-TYPE
     SYNTAX   INTEGER { enabled(1), disabled(2) }
     MAX-ACCESS   read-write
     STATUS   current
     DESCRIPTION
            "Setting this object to a value of enabled(1) will enable
             the DNS round robin feature. Setting this object to
             disabled(2) will set the DNS into random."
     --CONFIGURABLE
::= { usrDns 26 }

usrDnsCacheEntry OBJECT-TYPE
    SYNTAX      UsrDnsCacheEntry
    MAX-ACCESS  not-accessible
    STATUS      current
    DESCRIPTION
           "An entry in the resolvers's cache.  Rows may be created
           only by the resolver.  SNMP SET requests may be used to
           delete rows."
    INDEX     { usrDnsCacheRRIndex }
::= { usrDnsCacheTable 1 }

UsrDnsCacheEntry ::=
    SEQUENCE {
        usrDnsCacheRRIndex
            Integer32,
        usrDnsCacheRRClass
            DnsClass,
        usrDnsCacheRRType
            DnsType,
        usrDnsCacheRRTTL
            DnsTime,
        usrDnsCacheRRElapsedTTL
            DnsTime,
        usrDnsCacheRRSource
            IpAddress,
        usrDnsCacheRRData
            OCTET STRING,
        usrDnsCacheRRStatus
            RowStatus,
        usrDnsCacheRRPrettyName
            DnsName
    }

usrDnsCacheRRIndex OBJECT-TYPE
    SYNTAX      Integer32
    MAX-ACCESS  not-accessible
    STATUS      current
    DESCRIPTION
           "A value which makes entries in the table unique."
::= { usrDnsCacheEntry 1 }

usrDnsCacheRRClass OBJECT-TYPE
    SYNTAX      DnsClass
    MAX-ACCESS  read-only
    STATUS      current
    DESCRIPTION
           "DNS class of the Resource Record in the cache which is
           identified in this row of the table."
::= { usrDnsCacheEntry 2 }

usrDnsCacheRRType OBJECT-TYPE
    SYNTAX      DnsType
    MAX-ACCESS  read-only
    STATUS      current
    DESCRIPTION
           "DNS type of the Resource Record in the cache which is
           identified in this row of the table."
::= { usrDnsCacheEntry 3 }

usrDnsCacheRRTTL OBJECT-TYPE
    SYNTAX      DnsTime
    MAX-ACCESS  read-only
    STATUS      current
    DESCRIPTION
           "Time-To-Live of RR in DNS cache.  This is the initial
           TTL value which was received with the RR when it was
           originally received."
::= { usrDnsCacheEntry 4 }

usrDnsCacheRRElapsedTTL OBJECT-TYPE
    SYNTAX      DnsTime
    MAX-ACCESS  read-only
    STATUS      current
    DESCRIPTION
           "Elapsed seconds since RR was received."
::= { usrDnsCacheEntry 5 }

usrDnsCacheRRSource OBJECT-TYPE
    SYNTAX      IpAddress
    MAX-ACCESS  read-only
    STATUS      current
    DESCRIPTION
           "Host from which RR was received, 0.0.0.0 if unknown."
::= { usrDnsCacheEntry 6 }

usrDnsCacheRRData OBJECT-TYPE
    SYNTAX      OCTET STRING
    MAX-ACCESS  read-only
    STATUS      current
    DESCRIPTION
           "RDATA portion of a cached RR.  The value is in the
           format defined for the particular DNS class and type of
           the resource record."
    REFERENCE
           "RFC-1035 section 3.2.1."
::= { usrDnsCacheEntry 7 }

usrDnsCacheRRStatus OBJECT-TYPE
    SYNTAX      RowStatus
    MAX-ACCESS  read-write
    STATUS      current
    DESCRIPTION
           "Status column for the resolver cache table.  Since only
           the agent (DNS resolver) creates rows in this table, the
           only values that a manager may write to this variable
           are active(1) and destroy(6)."
::= { usrDnsCacheEntry 8 }

usrDnsCacheRRPrettyName OBJECT-TYPE
    SYNTAX      DnsName
    MAX-ACCESS  read-only
    STATUS      current
    DESCRIPTION
           "Name of the RR at this row in the table.  This is
           identical to the dnsResCacheRRName variable, except that
           character case is preserved in this variable, per DNS
           conventions."
    REFERENCE
           "RFC-1035 section 2.3.3."
::= { usrDnsCacheEntry 9 }

-- Resolver Negative Cache Table

usrDnsNCacheTable OBJECT-TYPE
    SYNTAX      SEQUENCE OF UsrDnsNCacheEntry
    MAX-ACCESS  not-accessible
    STATUS      current
    DESCRIPTION
           "The resolver's negative response cache.  This table
           contains information about authoritative errors that
           have been cached by the resolver."
::= { usrDns 25 }

usrDnsNCacheEntry OBJECT-TYPE
    SYNTAX      UsrDnsNCacheEntry
    MAX-ACCESS  not-accessible
    STATUS      current
    DESCRIPTION
           "An entry in the resolver's negative response cache
           table.  Only the resolver can create rows.  SNMP SET
           requests may be used to delete rows."
       INDEX     { usrDnsNCacheErrIndex }
::= { usrDnsNCacheTable 1 }

UsrDnsNCacheEntry ::=
    SEQUENCE {
        usrDnsNCacheErrIndex
            Integer32,
        usrDnsNCacheErrQClass
            DnsQClass,
        usrDnsNCacheErrQType
            DnsQType,
        usrDnsNCacheErrTTL
            DnsTime,
        usrDnsNCacheErrElapsedTTL
            DnsTime,
        usrDnsNCacheErrSource
            IpAddress,
        usrDnsNCacheErrCode
            INTEGER,
        usrDnsNCacheErrStatus
            RowStatus,
        usrDnsNCacheErrPrettyName
            DnsName
    }

usrDnsNCacheErrIndex OBJECT-TYPE
    SYNTAX      Integer32
    MAX-ACCESS  read-only
    STATUS      current
    DESCRIPTION
           "A value which makes entries in the table unique."
::= { usrDnsNCacheEntry 9 }

usrDnsNCacheErrQClass OBJECT-TYPE
    SYNTAX      DnsQClass
    MAX-ACCESS  read-only
    STATUS      current
    DESCRIPTION
           "DNS QCLASS associated with a cached authoritative
           error."
::= { usrDnsNCacheEntry 2 }

usrDnsNCacheErrQType OBJECT-TYPE
    SYNTAX      DnsQType
    MAX-ACCESS  read-only
    STATUS      current
    DESCRIPTION
           "DNS QTYPE associated with a cached authoritative error."
::= { usrDnsNCacheEntry 3 }

usrDnsNCacheErrTTL OBJECT-TYPE
    SYNTAX      DnsTime
    MAX-ACCESS  read-only
    STATUS      current
    DESCRIPTION
           "Time-To-Live of a cached authoritative error at the time
           of the error, it should not be decremented by the number
           of seconds since it was received.  This should be the
           TTL as copied from the MINIMUM field of the SOA that
           accompanied the authoritative error, or a smaller value
           if the resolver implements a ceiling on negative
           response cache TTLs."
    REFERENCE
           "RFC-1034 section 4.3.4."
::= { usrDnsNCacheEntry 4 }

usrDnsNCacheErrElapsedTTL OBJECT-TYPE
    SYNTAX      DnsTime
    MAX-ACCESS  read-only
    STATUS      current
    DESCRIPTION
           "Elapsed seconds since authoritative error was received."
::= { usrDnsNCacheEntry 5 }

usrDnsNCacheErrSource OBJECT-TYPE
    SYNTAX      IpAddress
    MAX-ACCESS  read-only
    STATUS      current
    DESCRIPTION
           "Host which sent the authoritative error, 0.0.0.0 if
           unknown."
::= { usrDnsNCacheEntry 6 }

usrDnsNCacheErrCode OBJECT-TYPE
    SYNTAX      INTEGER { nonexistantName(1), noData(2), other(3) }
    MAX-ACCESS  read-only
    STATUS      current
    DESCRIPTION
           "The authoritative error that has been cached:

           nonexistantName(1) indicates an authoritative name error
           (RCODE = 3).

           noData(2) indicates an authoritative response with no
           error (RCODE = 0) and no relevant data.

           other(3) indicates some other cached authoritative
           error.  At present, no such errors are known to exist."
::= { usrDnsNCacheEntry 7 }

usrDnsNCacheErrStatus OBJECT-TYPE
    SYNTAX      RowStatus
    MAX-ACCESS  read-write
    STATUS      current
    DESCRIPTION
           "Status column for the resolver negative response cache
           table.  Since only the agent (DNS resolver) creates rows
           in this table, the only values that a manager may write
           to this variable are active(1) and destroy(6)."
::= { usrDnsNCacheEntry 8 }

usrDnsNCacheErrPrettyName OBJECT-TYPE
    SYNTAX      DnsName
    MAX-ACCESS  read-only
    STATUS      current
    DESCRIPTION
           "QNAME associated with this row in the table.  This is
           identical to the dnsResNCacheErrQName variable, except
           that character case is preserved in this variable, per
           DNS conventions."
    REFERENCE
           "RFC-1035 section 2.3.3."
::= { usrDnsNCacheEntry 10 }

END         -- End USR-DNS-MIB definitions

--
--
-- $Log: usr_dns.mib,v $
-- Revision 1.5.10.2  1997/12/19 13:20:25  psd
-- Another merge from 2.0
--
-- Revision 1.5.10.1  1997/08/22 16:00:58  hdas
-- Merge change from Pilgrim20 branch into pilgrim_3_0_0
--
-- Revision 1.6  1997/08/06 19:57:40  psd
-- Added the DNS Host Rotation feature.
--
--Revision 1.5  1996/05/14  20:28:54  patton
--put configurable into min
--
-- Revision 1.4  1996/04/25 21:32:25  patton
-- added counters
--
-- Revision 1.3  1996/04/09 20:44:48  patton
-- Added Timeout
--
-- Revision 1.2  1996/04/08 21:49:56  patton
-- NameServer Table
--
-- Revision 1.1  1996/03/21 22:59:26  patton
-- DNS proprietary mib
--
--
-- End:
--
--
--	usr_tap.mib - A proprietary MIB file for the Port Tapping Service
--
--
-- Author:         J Senthilnathan
--
--  | Copyright (c) 1995 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-TAP-MIB DEFINITIONS ::= BEGIN

       IMPORTS
          OBJECT-TYPE
                FROM SNMPv2-SMI
          IpAddress
                FROM RFC1155-SMI
          DisplayString, usrTap
                FROM USR-DEFINITIONS-MIB;

   -- Begin managed object definitions here...

usrTapTable OBJECT-TYPE
	SYNTAX SEQUENCE OF UsrTapEntry
	MAX-ACCESS not-accessible
	STATUS current
	DESCRIPTION
		"The table of Tap entries. "
::= { usrTap 1 }

usrTapEntry OBJECT-TYPE
	SYNTAX UsrTapEntry
	MAX-ACCESS not-accessible
	STATUS current
	DESCRIPTION
		"A entry for one tap."
	INDEX { usrTapOutput }
::= { usrTapTable 1 }

UsrTapEntry ::= SEQUENCE {
	usrTapIfaceName		DisplayString,
	usrTapIface		INTEGER,
	usrTapUserName		DisplayString,
	usrTapUser		INTEGER,
	usrTapNext		INTEGER,
	usrTapPermanent 	INTEGER,
	usrTapOutput		INTEGER,
	usrTapFormat		INTEGER,
	usrTapFacility		INTEGER,
	usrTapPriority     	INTEGER,
	usrTapAddress     	IpAddress,
	usrTapOutputIcb		INTEGER,
	usrTapStatus		INTEGER,
	usrTapPermanent		INTEGER
	}

usrTapIfaceName OBJECT-TYPE
	SYNTAX		DisplayString 
	MAX-ACCESS	read-write
	STATUS		current
	DESCRIPTION
		"The name of the interface being tapped."
::= { usrTapEntry 1 }

usrTapUserName OBJECT-TYPE
	SYNTAX		DisplayString 
	MAX-ACCESS	read-write
	STATUS		current
	DESCRIPTION
		"The name of the user being tapped."
::= { usrTapEntry 2 }

usrTapOutput OBJECT-TYPE
	SYNTAX		INTEGER { syslog(0), screen(1) }
	MAX-ACCESS	read-write
	STATUS		current
	DESCRIPTION
		"The tapped output can be sent to syslog or to screen."
::= { usrTapEntry 3 }

usrTapFormat OBJECT-TYPE
	SYNTAX		INTEGER { ascii(0), hex(1), clear(2) }
	MAX-ACCESS	read-write
	STATUS		current
	DESCRIPTION
		"The output can be in hex, ascii or clear formats."
::= { usrTapEntry 4 }

usrTapFacility OBJECT-TYPE
	SYNTAX		INTEGER { auth(1), local0(2), local1(3), local2(4), local3(5), local4(6), local5(7), local6(8), local7(9) }
	MAX-ACCESS	read-write
	STATUS		current
	DESCRIPTION
		"The syslog facility used for logging."
::= { usrTapEntry 5 }

usrTapPriority OBJECT-TYPE
	SYNTAX		INTEGER { critical(0), unusual(1), common(2), verbose(3) }
	MAX-ACCESS	read-write
	STATUS		current
	DESCRIPTION
		"The syslog level used for logging."
::= { usrTapEntry 6 }

usrTapAddress OBJECT-TYPE
	SYNTAX		IpAddress 
	MAX-ACCESS	read-write
	STATUS		current
	DESCRIPTION
		"The IP address for logging the output to."
::= { usrTapEntry 7 }

usrTapOutputIcb OBJECT-TYPE
	SYNTAX		INTEGER 
	MAX-ACCESS	read-write
	STATUS		current
	DESCRIPTION
		"The icb ptr for tap commands issued via cli."
::= { usrTapEntry 8 }

usrTapStatus OBJECT-TYPE
	SYNTAX		INTEGER 
	MAX-ACCESS	read-write
	STATUS		current
	DESCRIPTION
		"The status of the tap"
::= { usrTapEntry 9 }

usrTapIface OBJECT-TYPE
	SYNTAX		INTEGER 
	MAX-ACCESS	read-write
	STATUS		current
	DESCRIPTION
		"Whether this is a interface based tap."
::= { usrTapEntry 10 }

usrTapUser OBJECT-TYPE
	SYNTAX		INTEGER 
	MAX-ACCESS	read-write
	STATUS		current
	DESCRIPTION
		"Whether this is a user based tap."
::= { usrTapEntry 11 }

usrTapNext OBJECT-TYPE
	SYNTAX		INTEGER 
	MAX-ACCESS	read-write
	STATUS		current
	DESCRIPTION
		"Whether the next call is to be tapped."
::= { usrTapEntry 12 }

usrTapPermanent OBJECT-TYPE
	SYNTAX		INTEGER { temporary(0), permanent(1) }
	MAX-ACCESS	read-write
	STATUS		current
	DESCRIPTION
		"Whether the tap is permanent (user profile has it) or temp (CLI issued)"
::= { usrTapEntry 13 }

END         -- End USR-TAP-MIB definitions

   USR-L2TP-MIB DEFINITIONS ::= BEGIN

   IMPORTS
           OBJECT-IDENTITY, OBJECT-TYPE FROM SNMPv2-SMI


           	TruthValue 
           		FROM SNMPv2-TC
		   	IpAddress
                FROM RFC1155-SMI
		   	RowStatus
                FROM SNMPv2-TC
	   		usrL2TP, DisplayString, UsrConfigStatus
	   			FROM USR-DEFINITIONS-MIB;


   usrL2TPGlobal  OBJECT-IDENTITY
           STATUS          current
           DESCRIPTION
              "The root of the L2TP global Object-Identifiers."
           ::= { usrL2TP 1 }

   usrL2TPConfigTable OBJECT-TYPE
           SYNTAX          SEQUENCE OF UsrL2TPConfigEntry
           MAX-ACCESS      not-accessible
           STATUS          current
           DESCRIPTION
              ""
           ::= { usrL2TPGlobal 1 }

   usrL2tpConfigEntry OBJECT-TYPE
           SYNTAX          UsrL2TPConfigEntry
           MAX-ACCESS      not-accessible
           STATUS          current
           DESCRIPTION
              "."
           INDEX           { usrL2tpConfigIndex }
           ::= { usrL2TPConfigTable 1 }

   UsrL2TPConfigEntry ::= SEQUENCE {
           usrL2tpConfigIndex
                   INTEGER,
           usrL2tpLoadBalancing
                   TruthValue,
	   		usrL2tpDialOut
					OCTET STRING,
			usrL2tpLnsFlag INTEGER ,
		usrL2tpPasswordEncryptStyle INTEGER,
    		usrL2tpAuthenticationRequiredOnOutgoingTunnels
					TruthValue,
           usrL2tpNumberOfEchoRetransmissions
                   INTEGER(0..65535),
           usrL2tpEchoRetransmissionInterval
                   INTEGER(0..65535)
		}


   usrL2tpConfigIndex         OBJECT-TYPE
           SYNTAX          INTEGER
           MAX-ACCESS      read-only
           STATUS          current
           DESCRIPTION
              " A unique value for each l2tp protocol stack. "
           ::= { usrL2tpConfigEntry 1 }

   usrL2tpLoadBalancing  OBJECT-TYPE
           SYNTAX          TruthValue
           MAX-ACCESS      read-write
           STATUS          current
           DESCRIPTION
              "Defines If Load Balancing is enabled or not."
           DEFVAL          { true }
		 --CONFIGURABLE
           ::= { usrL2tpConfigEntry 2 }
	

   usrL2tpDialOut OBJECT-TYPE       
        SYNTAX  OCTET STRING (SIZE(0..32))
        MAX-ACCESS  read-write
        STATUS  current
        DESCRIPTION
                "This variable is set through the CLI when the user
                 manually issues a L2TP dial-out."      
        ::= { usrL2tpConfigEntry 3 }

   usrL2tpLnsFlag OBJECT-TYPE
      SYNTAX   INTEGER { enabled(1), disabled(2) }
      MAX-ACCESS   read-write
      STATUS   current     
      DESCRIPTION
             "Setting this object to a value of enabled(1) will enable
              the L2TP lns enable feature. Setting this object to
              disabled(2) will disable the L2TP LNS feature."
     --CONFIGURABLE
   ::= { usrL2tpConfigEntry 4 } 

    usrL2tpPasswordEncryptStyle OBJECT-TYPE
      SYNTAX   INTEGER { draft-3(1), draft-6(2) }
      MAX-ACCESS   read-write
      STATUS   current     
      DESCRIPTION
             "Setting this object to a value of Draft-3(1) will set
              the encryption style for tunnel password as retrieved 
                from RADIUS to be as specified in Draft-3. Otherwise, it will
                be set to the style defined in Draft-6."
	DEFVAL {1}
     --CONFIGURABLE
   ::= { usrL2tpConfigEntry  5 }

	usrL2TPLcpRenegotiateAtLNS OBJECT-TYPE
	SYNTAX  INTEGER {
		enabled(1),                                        
		disabled(2)
		} 
	MAX-ACCESS   read-write
	STATUS   current
	DESCRIPTION
		"This flag is used to enable/disable LCP renegotiation
		for calls when doing proxy LCP on LNS"
	--CONFIGURABLE    
	::= { usrL2tpConfigEntry 6 }

    usrL2tpAuthenticationRequiredOnOutgoingTunnels   OBJECT-TYPE
           SYNTAX          TruthValue
           MAX-ACCESS      read-write
           STATUS          current
           DESCRIPTION
              "When set to a value of true(1) requires that all
              outgoing tunnels request tunnel authentication."
           DEFVAL          { true }
		 --CONFIGURABLE
           ::= { usrL2tpConfigEntry 7 }

   usrL2tpTunnel OBJECT IDENTIFIER ::= {usrL2TP 2}

   usrL2tpTunnelQueryTable OBJECT-TYPE
           SYNTAX          SEQUENCE OF UsrL2tpTunnelQueryEntry
           MAX-ACCESS      not-accessible
           STATUS          current
           DESCRIPTION
              "A table containing the READ ONLY propietary extension
			   parameters for L2TP Tunnel MIB."
           ::= { usrL2tpTunnel 1 }

   usrL2tpTunnelQueryEntry OBJECT-TYPE
           SYNTAX          UsrL2tpTunnelQueryEntry
           MAX-ACCESS      not-accessible
           STATUS          current
           DESCRIPTION
              "  "
           INDEX           { usrL2tpTunnelLogicalStackIndex,
                             usrL2tpTunnelLocalControlTunnelId }
           ::= { usrL2tpTunnelQueryTable 1 }

   UsrL2tpTunnelQueryEntry ::= SEQUENCE {
           usrL2tpTunnelLogicalStackIndex
                   INTEGER,
           usrL2tpTunnelLocalControlTunnelId
                   INTEGER,
           usrL2tpTunnelSecurityLevel
                   INTEGER,
		usrL2tpTunnelDisconnect
                   INTEGER}


    usrL2tpTunnelLogicalStackIndex OBJECT-TYPE
           SYNTAX          INTEGER
           MAX-ACCESS      read-only     
           STATUS          current
           DESCRIPTION
              "This object contains a reference to the logical
              l2tp protocol stack and must be the same as the
              l2tpConfigIndex."
           ::= { usrL2tpTunnelQueryEntry 1 }  
                   
   usrL2tpTunnelLocalControlTunnelId OBJECT-TYPE   
           SYNTAX          INTEGER
           MAX-ACCESS      read-only      
           STATUS          current
           DESCRIPTION
              "This object contains the local tunnel Identifier."
           ::= { usrL2tpTunnelQueryEntry 2 }      
  
   usrL2tpTunnelSecurityLevel OBJECT-TYPE
           SYNTAX          INTEGER{
                                    none(0),
                                    control-Only(1),
                                    data-Only(2),
                                    both-Data-And-Control(3)
                                  }
           MAX-ACCESS      read-only
           STATUS          current
           DESCRIPTION
              "This field contains the security level 
              of the tunnel."
		   ::= {usrL2tpTunnelQueryEntry 3}

	usrL2tpTunnelDisconnect	OBJECT-TYPE
           SYNTAX          INTEGER
           MAX-ACCESS      read-write  
           STATUS          current
           DESCRIPTION
              "This object is used to disconnect a specific tunnel."
           ::= { usrL2tpTunnelQueryEntry 4 }

	 usrL2tpSession OBJECT-IDENTITY      
          STATUS         current    
          DESCRIPTION               
             "The root of L2TP Session Module Object-identifiers."
          ::= { usrL2TP 3 }
                                    
   usrL2tpSessionTable OBJECT-TYPE    
           SYNTAX    SEQUENCE OF UsrL2tpSessionEntry
           MAX-ACCESS not-accessible
           STATUS current
           DESCRIPTION
              ""
           ::= { usrL2tpSession 1 }
 
   usrL2tpSessionEntry OBJECT-TYPE
           SYNTAX          UsrL2tpSessionEntry
           MAX-ACCESS      not-accessible
           STATUS          current 
           DESCRIPTION
              "."
           INDEX           { usrL2tpSessionLogicalStackIndex,
                           usrL2tpSessionTunnelID , usrL2tpSessionLocalCallID }
           ::= { usrL2tpSessionTable 1 }
 
   UsrL2tpSessionEntry ::= SEQUENCE {
	   usrL2tpSessionLogicalStackIndex
                   INTEGER,
       usrL2tpSessionTunnelID
                   INTEGER,
       usrL2tpSessionLocalCallID
                   INTEGER,
		usrL2tpSessionDisconnect	
                   INTEGER
				}

   usrL2tpSessionLogicalStackIndex OBJECT-TYPE
           SYNTAX          INTEGER
           MAX-ACCESS      read-only
           STATUS          current
           DESCRIPTION
              "This object contains a reference to the logical
              l2tp protocol stack and must be the same as the
              l2tpConfigIndex and l2tpTunelLogicalStackIndex."
           ::= { usrL2tpSessionEntry 1 }
 
   usrL2tpSessionTunnelID OBJECT-TYPE
           SYNTAX          INTEGER
           MAX-ACCESS      read-only
           STATUS          current
           DESCRIPTION
              "This object contains the control Channel Tunnel
              identifier for this session"
           ::= { usrL2tpSessionEntry 2 }
 
   usrL2tpSessionLocalCallID  OBJECT-TYPE
           SYNTAX          INTEGER
           MAX-ACCESS      read-only
           STATUS          current
           DESCRIPTION
              "This object contains the local call identifier
              for the session.  "
           ::= { usrL2tpSessionEntry 3 }

	    usrL2tpSessionDisconnect OBJECT-TYPE
           SYNTAX          INTEGER
           MAX-ACCESS      read-write
           STATUS          current
           DESCRIPTION
              "This object is used to disconnect a specific tunnel."
           ::= { usrL2tpSessionEntry 4 }


	usrL2tpHostTable OBJECT-TYPE
        	SYNTAX SEQUENCE OF UsrL2tpHostEntry
        	MAX-ACCESS not-accessible
        	STATUS current
        	DESCRIPTION
                "The table of L2TP LNSs. "
			::= { usrL2TP 4 }
 
	usrL2tpHostEntry OBJECT-TYPE
		        SYNTAX UsrL2tpHostEntry
	        	MAX-ACCESS not-accessible
	        	STATUS current
	        	DESCRIPTION
	              "A (conceptual) entry for one pptp Host."
	        	INDEX { usrL2tpHostIndex }
				::= { usrL2tpHostTable 1 }
	 
	UsrL2tpHostEntry ::= SEQUENCE {
	        usrL2tpHostIndex       INTEGER,
	        usrL2tpHostAddress     IpAddress,
	        usrL2tpHostStatus      RowStatus,
	        usrL2tpSharedSecret    OCTET STRING,
	        usrL2tpSharedSecretStatus    TruthValue,
			usrL2tpSecurityLevel	INTEGER	
	        }
	 
	usrL2tpHostIndex OBJECT-TYPE
	        SYNTAX          INTEGER
	        MAX-ACCESS      not-accessible
	        STATUS          current
	        DESCRIPTION
	              "The logical identifier of the Host Table. "
			::= { usrL2tpHostEntry 1 }
	 
	usrL2tpHostAddress OBJECT-TYPE
	        SYNTAX          IpAddress
	        MAX-ACCESS      read-write
	        STATUS          current
	        DESCRIPTION
	                "The specified or resolved ip address of the named Host. "
	        --CONFIGURABLE
			::= { usrL2tpHostEntry 2 }
	 
	usrL2tpHostStatus OBJECT-TYPE
	        SYNTAX          RowStatus
	        MAX-ACCESS      read-write
	        STATUS          current
	        DESCRIPTION
	            "The status of this row of the Host Table. "
	        --CONFIGURABLE
			::= { usrL2tpHostEntry 3 }

	 usrL2tpSharedSecret OBJECT-TYPE
                SYNTAX          OCTET STRING  
                MAX-ACCESS      read-write
                STATUS          current
                DESCRIPTION
                      "The Shared Secret For This Host. "
		 --CONFIGURABLE
                        ::= { usrL2tpHostEntry 4 }

	 usrL2tpSharedSecretStatus OBJECT-TYPE
                SYNTAX          TruthValue 
                MAX-ACCESS      read-write
                STATUS          current
                DESCRIPTION
                      "The Shared Secret Status For This Host. "
		 --CONFIGURABLE
                        ::= { usrL2tpHostEntry 5 }

     usrL2tpSecurityLevel OBJECT-TYPE    
                SYNTAX          INTEGER{
                                    none(0),
                                    control-Only(1),
                                    data-Only(2),
                                    both-Data-And-Control(3)
                                  }

                MAX-ACCESS      read-write
                STATUS          current
                DESCRIPTION   
                      "The Security Level For This Host. "
		 --CONFIGURABLE
                        ::= { usrL2tpHostEntry 6 }

	usrL2TPConfigFileName OBJECT-TYPE
          SYNTAX      DisplayString
          MAX-ACCESS  read-write
          STATUS      current
          DESCRIPTION
          "The name of a ConfigFile to read/write permanent database records.
           If the value of this object is an empty string, then the
           L2TP process uses the default name `@file://L2tpProcess.cfg'. "
          ::= { usrL2TP 5 }

    usrL2TPCFMStatusFlag  OBJECT-TYPE
          SYNTAX         UsrConfigStatus
          MAX-ACCESS     read-write
          STATUS         current
          DESCRIPTION
                 "CFM Config Flag"
          ::= { usrL2TP 6 }                   

   usrL2tpNumberOfEchoRetransmissions  OBJECT-TYPE
           SYNTAX          INTEGER (0..65535)
           MAX-ACCESS      read-write
           STATUS          current
           DESCRIPTION
              "This object defines the number of Hello retransmission's
              which the L2TP stack will attempt before assuming that
              the peer is no longer reachable. The default value for
              this object is five (5)."
           DEFVAL          { 5 }
		 --CONFIGURABLE
           ::= { usrL2tpConfigEntry 8 }

   usrL2tpEchoRetransmissionInterval   OBJECT-TYPE
           SYNTAX          INTEGER(0..65535)
           MAX-ACCESS      read-write
           STATUS          current
           DESCRIPTION
              "This object defines the number of seconds between each
              retransmission."
           DEFVAL          { 10 }
		 --CONFIGURABLE
           ::= { usrL2tpConfigEntry 9 }

    usrL2TPSendDNIStoLNS OBJECT-TYPE
	SYNTAX  INTEGER {
		enabled(1),                                        
		disabled(2)
		} 
	MAX-ACCESS   read-write
	STATUS   current
	DESCRIPTION
		"This flag is used to at the LAC to enable/disable sending
		DNIS digits to the LNS in ICRQ message. Default is Enabled"
    DEFVAL          { enabled }
	--CONFIGURABLE    
	::= { usrL2tpConfigEntry 10 }

    usrL2TPForceMultipleTunnels OBJECT-TYPE
    SYNTAX  INTEGER {
        enabled(1),
        disabled(2)
        }
    MAX-ACCESS   read-write
    STATUS   current
    DESCRIPTION
        "This flag is used to enable/disable each user to go on a new
        tunnel to the same LNS."
    --CONFIGURABLE      
    ::= { usrL2tpConfigEntry 11 }

	 usrL2TPClientAuthIdOverload OBJECT-TYPE
    SYNTAX  INTEGER {
        enabled(1),        
        disabled(2)
        }  
    MAX-ACCESS   read-write
    STATUS   current
    DESCRIPTION
        "If enabled, the user's Client Auth Id attribute is used as if it
		were Tunnel Assignment Id.  This flag is disabled by default."
    --CONFIGURABLE
    ::= { usrL2tpConfigEntry 12 }

   usrL2TPCounterTable OBJECT-TYPE
           SYNTAX          SEQUENCE OF UsrL2TPCounterEntry
           MAX-ACCESS      not-accessible
           STATUS          current
           DESCRIPTION     "L2TP Session Counter Table"
           ::= { usrL2TPGlobal 2 }

   usrL2TPCounterEntry OBJECT-TYPE
           SYNTAX          UsrL2TPCounterEntry
           MAX-ACCESS      not-accessible
           STATUS          current
           DESCRIPTION     "L2TP Session Counter Entry"
           INDEX           { usrL2tpTunnelEndpoint }
           ::= { usrL2TPCounterTable 1 }

   UsrL2TPCounterEntry ::= SEQUENCE {
           usrL2tpTunnelEndpoint
                   IpAddress,
           usrL2tpSessionSuccessfullAttempts
                   INTEGER,
           usrL2tpSessionFailedAttempts
                   INTEGER,
           usrL2tpSessionTotalAttempts
                   INTEGER
		}

   usrL2tpTunnelEndpoint OBJECT-TYPE
           SYNTAX          IpAddress
           MAX-ACCESS      not-accessible
           STATUS          current
           DESCRIPTION     "L2TP Tunnel Endpoint"
          ::= {usrL2TPCounterEntry 1}

   usrL2tpSessionSuccessfullAttempts OBJECT-TYPE
           SYNTAX          INTEGER
           MAX-ACCESS      read-only
           STATUS          current
           DESCRIPTION     "No of Successfull Attempts to Tunnel Endpoint"
          ::= {usrL2TPCounterEntry 2}

   usrL2tpSessionFailedAttempts OBJECT-TYPE
           SYNTAX          INTEGER
           MAX-ACCESS      read-only
           STATUS          current
           DESCRIPTION     "No of Failed Attempts to Tunnel Endpoint"
          ::= {usrL2TPCounterEntry 3}

   usrL2tpSessionTotalAttempts OBJECT-TYPE
           SYNTAX          INTEGER
           MAX-ACCESS      read-only
           STATUS          current
           DESCRIPTION     "Total No of Attempts to Tunnel Endpoint"
          ::= {usrL2TPCounterEntry 4}

   usrL2tpSessionCountersResetFlag OBJECT-TYPE
           SYNTAX          INTEGER {
                             no(0),
                             yes(1)
                           }
           MAX-ACCESS      read-write
           STATUS          current
           DESCRIPTION     "Flag to reset L2TP session counters"
           ::= { usrL2TPGlobal 3 }


END
   L2tp-MIB DEFINITIONS ::= BEGIN

   IMPORTS
           Counter32, experimental, MODULE-IDENTITY,
           OBJECT-IDENTITY, OBJECT-TYPE FROM SNMPv2-SMI
           IpAddress FROM RFC1155-SMI

           TEXTUAL-CONVENTION, DisplayString, TruthValue FROM SNMPv2-TC;

   MilliSeconds ::=  TEXTUAL-CONVENTION
           DISPLAY-HINT    "d-3"
           STATUS          current
           DESCRIPTION
              " A period of time measured in units of .001 of seconds
              when used in conjunction with the DISPLAY-HINT will
              show seconds and fractions of second with a resolution
              of .001 of a second."
           SYNTAX          INTEGER (0..2147483646)

   l2tpSystem MODULE-IDENTITY
           LAST-UPDATED    "9708081800Z"
           ORGANIZATION    "IETF L2TP Working Group"
           CONTACT-INFO
              "Pat Calhoun, Bill Vroman Gayam Reddy
              Postal: 3Com
                      1800 W. Central Rd
                      Mt. Prospect, IL 60056-2293
              Tel:    +1 847222 2008
              Email:  pcalhoun, greddy, bvroman@usr.com

              Ross Wheeler
              Postal: RouterWare
                      3961 MacArthur Blvd, Suite 212
                      Newport Beach, CA 92660
              Tel:    +1 714442 0770
              Email:  ross@routerware.com"
           DESCRIPTION
              "The MIB module that describes managed objects of
              general use by L2TP Layer two Transport Protocol.
              This module has three tables of information about L2TP
              streams.
                1. Global  configuration and statistics tables.
                2. A table of tunnel read-only objects
                3. A table of session related parameters ."
           ::= { experimental 9999 }

	l2tpMIBObjects  OBJECT IDENTIFIER ::= {l2tpSystem 1}

   l2tp OBJECT-IDENTITY
           STATUS          current
           DESCRIPTION
              "The root of L2TP Object-identifiers."
           ::= { experimental 9998 }


   l2tpGlobal  OBJECT-IDENTITY
           STATUS          current
           DESCRIPTION
              "The root of the L2TP global Object-Identifiers."
           ::= { l2tp 1 }

   l2tpConfigTable OBJECT-TYPE
           SYNTAX          SEQUENCE OF L2tpConfigEntry
           MAX-ACCESS      not-accessible
           STATUS          current
           DESCRIPTION
              ""
           ::= { l2tpGlobal 1 }

   l2tpConfigEntry OBJECT-TYPE
           SYNTAX          L2tpConfigEntry
           MAX-ACCESS      not-accessible
           STATUS          current
           DESCRIPTION
              "."
           INDEX           { l2tpConfigIndex }
           ::= { l2tpConfigTable 1 }

   L2tpConfigEntry ::= SEQUENCE {
           l2tpConfigIndex
                   INTEGER,
           l2tpMaxNumberOfSessions
                   INTEGER,
           l2tpMaxNumberOfTunnels
                   INTEGER,
           l2tpControlTunnelSeekDescriptors
                   INTEGER,
           l2tpAuthenticateIncomingTunnelRequests
                   TruthValue,
           l2tpUseDataTunnelFlowControl
                   TruthValue,
           l2tpDataTunnelDelayedAckTimeout
                   MilliSeconds,
           l2tpDataTunnelReassemblyTimeout
                   MilliSeconds,
           l2tpControlChannelRecvPacketWindow
                   INTEGER,
           l2tpDataChannelRecvPacketWindow
                   INTEGER,
           l2tpHelloInactivityHoldTime
                   INTEGER,
           l2tpEchoReplyTimeoutSeconds
                   INTEGER,
           l2tpLoggingLevel
                   INTEGER,
           l2tpNumberOfRetransmissions
                   INTEGER(0..65535),
           l2tpRetransmissionInterval
                   INTEGER(0..65535),
           l2tpAuthenticationRequiredOnIncomingTunnels
                   TruthValue }

   l2tpConfigIndex         OBJECT-TYPE
           SYNTAX          INTEGER
           MAX-ACCESS      read-only
           STATUS          current
           DESCRIPTION
              " A unique value for each l2tp protocol stack. "
           ::= { l2tpConfigEntry 1 }


   l2tpMaxNumberOfSessions OBJECT-TYPE
           SYNTAX          INTEGER
           MAX-ACCESS      read-write
           STATUS          current
           DESCRIPTION
               "Defines the number of simultaneous active sessions
               that the L2TP stack will support."
           DEFVAL          { 0 }
		 --CONFIGURABLE
           ::= { l2tpConfigEntry 2 }

   l2tpMaxNumberOfTunnels OBJECT-TYPE
           SYNTAX          INTEGER
           MAX-ACCESS      read-write
           STATUS          current
           DESCRIPTION
               "Defines the number of simultaneous active tunnels
               that the L2TP stack will support. Remember that sessions
               are multiplexed within a single tunnel, therefore this
               object contains the number of active L2TP tunnel
               sessions which are to be supported per tunnel."
           DEFVAL          { 0 }
		 --CONFIGURABLE
           ::= { l2tpConfigEntry 3 }

   l2tpControlTunnelSeekDescriptors  OBJECT-TYPE
           SYNTAX          INTEGER
           MAX-ACCESS      read-write
           STATUS          current
           DESCRIPTION
              "Defines the number of tunnel terminators which the L2TP
              stack is to be able to simultaneous connect to. Once a
              tunnel is in the established state, the seek descriptor
              is no longer used."
           DEFVAL          { 8 }
		 --CONFIGURABLE
           ::= { l2tpConfigEntry 4 }

   l2tpAuthenticateIncomingTunnelRequests  OBJECT-TYPE
           SYNTAX          TruthValue
           MAX-ACCESS      read-write
           STATUS          current
           DESCRIPTION
              "Defines whether the L2TP MUST require authentication from
              it's peers. When set, the L2TP stack will reject any tunnel
              requests which are not secure."
           DEFVAL          { false }
		 --CONFIGURABLE
           ::= { l2tpConfigEntry 5 }

   l2tpUseDataTunnelFlowControl  OBJECT-TYPE
           SYNTAX          TruthValue
           MAX-ACCESS      read-write
           STATUS          current
           DESCRIPTION
              "This object determines whether or not the L2TP stack is
              to use flow control on the data tunnel."
           DEFVAL          { false }
		 --CONFIGURABLE
           ::= { l2tpConfigEntry 6 }

   l2tpDataTunnelDelayedAckTimeout  OBJECT-TYPE
           SYNTAX          MilliSeconds
           MAX-ACCESS      read-write
           STATUS          current
           DESCRIPTION
              "This object defines the number of milliseconds which the
              L2TP stack will wait  to send and ACK to it's peer in the
              case where there are no data or control packets to piggy-
              back the ACK to.  The default value for this object is 0
              which results in immediate acknowledgment when there are
              no data or control packets pending."
           DEFVAL          { 0 }
		 --CONFIGURABLE
           ::= { l2tpConfigEntry 7 }

   l2tpDataTunnelReassemblyTimeout  OBJECT-TYPE
           SYNTAX          MilliSeconds
           MAX-ACCESS      read-write
           STATUS          current
           DESCRIPTION
              "This object defines the number of milliseconds that the
              L2TP stack will use to determine the window to use before
              reassembling out of order packets. A low value increases
              the chance of out-of-sequence packets to be lost (which
              MAY causes the PPP decompression engine to reset), a high
              value increases the time period where the L2TP stack
              processes packets which were received out of order
              (especially in the case of a packet which was lost within
              the network).  The default value for this object is zero
              (0) which may result in all out of sequence packets being
              lost."
           DEFVAL          { 0 }
		 --CONFIGURABLE
           ::= { l2tpConfigEntry 8 }

   l2tpControlChannelRecvPacketWindow  OBJECT-TYPE
           SYNTAX          INTEGER
           MAX-ACCESS      read-write
           STATUS          current
           DESCRIPTION
              "This object defines the Control Channel receive window
              size which is transmitted to the L2TP peers."
           DEFVAL          { 4 }
		 --CONFIGURABLE
           ::= { l2tpConfigEntry 9 }

   l2tpDataChannelRecvPacketWindow  OBJECT-TYPE
           SYNTAX          INTEGER
           MAX-ACCESS      read-write
           STATUS          current
           DESCRIPTION
              "This object defines the Data Channel receive window
              size which is transmitted to the L2TP peers."
           DEFVAL          { 7 }
		 --CONFIGURABLE
           ::= { l2tpConfigEntry 10 }

   l2tpHelloInactivityHoldTime    OBJECT-TYPE
           SYNTAX          INTEGER
           MAX-ACCESS      read-write
           STATUS          current
           DESCRIPTION
              "This object defines the length of the inactivity timer
              in seconds which causes the L2TP stack to transmit a
              keep-alive packet (known as Hello)."
           DEFVAL          { 0 }
		 --CONFIGURABLE
           ::= { l2tpConfigEntry 11 }

   l2tpEchoReplyTimeoutSeconds  OBJECT-TYPE
           SYNTAX          INTEGER
           MAX-ACCESS      read-write
           STATUS          current
           DESCRIPTION
              "This object defines the number of seconds which the L2TP
              stack must wait until a time-out occurs in receiving a
              response to the Hello  message."
           DEFVAL          { 0 }
		 --CONFIGURABLE
           ::= { l2tpConfigEntry 12 }

   l2tpLoggingLevel  OBJECT-TYPE
           SYNTAX          INTEGER {
               logDisabled(1),
               logControlPackets(2),
               logControlAndDataPacketHeaders(3),
               logControlAndDataPackets(4)
           }
           MAX-ACCESS      read-write
           STATUS          current
           DESCRIPTION
              "This object defines the logging level which the L2TP
              protocol stack will use."
           DEFVAL          { logDisabled }
		 --CONFIGURABLE
           ::= { l2tpConfigEntry 13 }

   l2tpNumberOfRetransmissions  OBJECT-TYPE
           SYNTAX          INTEGER (0..65535)
           MAX-ACCESS      read-write
           STATUS          current
           DESCRIPTION
              "This object defines the number of retransmission's
              which the L2TP stack will attempt before assuming that
              the peer is no longer reachable. The default value for
              this object is zero (0) which results in the L2TP stack
              not doing retransmission's ."
           DEFVAL          { 0 }
		 --CONFIGURABLE
           ::= { l2tpConfigEntry 14 }

   l2tpRetransmissionInterval   OBJECT-TYPE
           SYNTAX          INTEGER(0..65535)
           MAX-ACCESS      read-write
           STATUS          current
           DESCRIPTION
              "This object defines the number of seconds between each
              retransmission."
           DEFVAL          { 0 }
		 --CONFIGURABLE
           ::= { l2tpConfigEntry 15 }

   l2tpAuthenticationRequiredOnIncomingTunnels   OBJECT-TYPE
           SYNTAX          TruthValue
           MAX-ACCESS      read-write
           STATUS          current
           DESCRIPTION
              "When set to a value of true(1) requires that all
              incoming tunnels perform tunnel authentication."
           DEFVAL          { false }
		 --CONFIGURABLE
           ::= { l2tpConfigEntry 16 }

   l2tpStatsTable OBJECT-TYPE
           SYNTAX          SEQUENCE OF L2tpStatsEntry
           MAX-ACCESS      not-accessible
           STATUS          current
           DESCRIPTION
              ""
           ::= { l2tpGlobal 2 }

   l2tpStatsEntry OBJECT-TYPE
           SYNTAX          L2tpStatsEntry
           MAX-ACCESS      not-accessible
           STATUS          current
           DESCRIPTION
              "."
           INDEX           { l2tpStatsIndex }
           ::= { l2tpStatsTable 1 }

   L2tpStatsEntry ::= SEQUENCE {
           l2tpStatsIndex
                   INTEGER,
           l2tpNumActiveTunnels
                   INTEGER,
           l2tpStatsNumActiveSessions
                   INTEGER,
           l2tpStatsFailedAuthentications
                   Counter32,
           l2tpStatsMalformedPackets
                   Counter32,
           l2tpStatsControlTunnelRecvPackets
                   Counter32,
           l2tpStatsControlTunnelWithDataRecvPackets
                   Counter32,
           l2tpStatsControlTunnelWithoutDataRecvPackets
                   Counter32,
           l2tpStatsProcessedControlTunnelRecvPackets
                   Counter32,
           l2tpStatsInSequenceControlTunnelRecvPackets
                   Counter32,
           l2tpStatsOutSequenceControlTunnelRecvPackets
                   Counter32,
           l2tpStatsInOrderControlTunnelRecvPackets
                   Counter32,
           l2tpStatsOutOfOrderControlTunnelRecvPackets
                   Counter32,
           l2tpStatsFlowDiscardedControlTunnelRecvPackets
                   Counter32,
           l2tpStatsOutOfOrderDiscardedControlTunnelRecvPackets
                   Counter32,
           l2tpStatsControlTunnelSendPackets
                   Counter32,
           l2tpStatsControlTunnelWithdataSendPackets
                   Counter32,
           l2tpStatsControlTunnelWithoutdataSendPackets
                   Counter32,
           l2tpStatsControlTunnelFlowControlTimeouts
                   Counter32,
           l2tpStatsLocalControlTunnelFlowControlEnables
                   Counter32,
           l2tpStatsRemoteControlTunnelFlowControlEnables
                   Counter32,
           l2tpStatsControlTunnelReassemblyTimeouts
                   Counter32,
           l2tpStatsDataTunnelRecvPackets
                   Counter32,
           l2tpStatsDataTunnelWithdataRecvPackets
                   Counter32,
           l2tpStatsDataTunnelWithoutdataRecvPackets
                   Counter32,
           l2tpStatsProcessedDataTunnelRecvPackets
                   Counter32,
           l2tpStatsInSequenceDataTunnelRecvPackets
                   Counter32,
           l2tpStatsOutSequenceDataTunnelRecvPackets
                   Counter32,
           l2tpStatsInOrderDataTunnelRecvPackets
                   Counter32,
           l2tpStatsOutOfOrderDataTunnelRecvPackets
                   Counter32,
           l2tpStatsFlowDiscardedDataTunnelRecvPackets
                   Counter32,
           l2tpStatsOutOfOrderDiscardedDataTunnelRecvPackets
                   Counter32,
           l2tpStatsDataTunnelSendPackets
                   Counter32,
           l2tpStatsDataTunnelWithdataSendPackets
                   Counter32,
           l2tpStatsDataTunnelWithoutdataSendPackets
                   Counter32,
           l2tpStatsDataTunnelFlowControlTimeouts
                   Counter32,
           l2tpStatsLocalDataTunnelFlowControlEnables
                   Counter32,
           l2tpStatsRemoteDataTunnelFlowControlEnables
                   Counter32,
           l2tpStatsDataTunnelReassemblyTimeouts
                   Counter32 }

   l2tpStatsIndex          OBJECT-TYPE
           SYNTAX          INTEGER
           MAX-ACCESS      read-only
           STATUS          current
           DESCRIPTION
              " Should be the same value as l2tpConfigIndex to
              reference the same logical l2tp protocol stack. "
           ::= { l2tpStatsEntry 1 }


   l2tpNumActiveTunnels  OBJECT-TYPE
           SYNTAX          INTEGER
           MAX-ACCESS      read-only
           STATUS          current
           DESCRIPTION
              "This object returns the number of L2TP tunnels
              that are currently active. "
           ::= { l2tpStatsEntry 2 }

   l2tpStatsNumActiveSessions  OBJECT-TYPE
           SYNTAX          INTEGER
           MAX-ACCESS      read-only
           STATUS          current
           DESCRIPTION
              "This object returns the number of L2TP sessions
              that are currently active. "
           ::= { l2tpStatsEntry 3 }

   l2tpStatsFailedAuthentications OBJECT-TYPE
           SYNTAX          Counter32
           MAX-ACCESS      read-only
           STATUS          current
           DESCRIPTION
              "This object returns a count of the number of L2TP
              authentication's that have failed since this stack
              was last initialized.  "
           ::= { l2tpStatsEntry 4 }

   l2tpStatsMalformedPackets    OBJECT-TYPE
           SYNTAX          Counter32
           MAX-ACCESS      read-only
           STATUS          current
           DESCRIPTION
              "This object returns a count of the number of malformed
              packets received by this L2TP stack since it was last
              initialized.   "
           ::= { l2tpStatsEntry 5 }

   l2tpStatsControlTunnelRecvPackets   OBJECT-TYPE
           SYNTAX          Counter32
           MAX-ACCESS      read-only
           STATUS          current
           DESCRIPTION
              " This object returns a count of the number of control
              packets received by this L2TP stack since it was last
              initialized."
           ::= { l2tpStatsEntry 6 }

   l2tpStatsControlTunnelWithDataRecvPackets  OBJECT-TYPE
           SYNTAX          Counter32
           MAX-ACCESS      read-only
           STATUS          current
           DESCRIPTION
              " This object returns a count of the number of control
              packets with data included that were received by this
              L2TP stack since it was last initialized."
           ::= { l2tpStatsEntry 7 }

   l2tpStatsControlTunnelWithoutDataRecvPackets OBJECT-TYPE
           SYNTAX          Counter32
           MAX-ACCESS      read-only
           STATUS          current
           DESCRIPTION
              " This object returns a count of the number of Zero
              length control packets that were received by this L2TP
              stack since it was last initialized."
           ::= { l2tpStatsEntry 8 }

   l2tpStatsProcessedControlTunnelRecvPackets   OBJECT-TYPE
           SYNTAX          Counter32
           MAX-ACCESS      read-only
           STATUS          current
           DESCRIPTION
              " This object returns a count of the number of received
              control packets that were processed by this L2TP stack
              since it was last initialized."
           ::= { l2tpStatsEntry 9 }

   l2tpStatsInSequenceControlTunnelRecvPackets   OBJECT-TYPE
           SYNTAX          Counter32
           MAX-ACCESS      read-only
           STATUS          current
           DESCRIPTION
              " This object returns a count of the number of control
              packets that were received in sequence by this L2TP
              stack since it was last initialized."
           ::= { l2tpStatsEntry 10 }

   l2tpStatsOutSequenceControlTunnelRecvPackets   OBJECT-TYPE
           SYNTAX          Counter32
           MAX-ACCESS      read-only
           STATUS          current
           DESCRIPTION
              " This object returns a count of the number of control
              packets that were received out of sequence by this L2TP
              stack since it was last initialized."
           ::= { l2tpStatsEntry 11 }

   l2tpStatsInOrderControlTunnelRecvPackets  OBJECT-TYPE
           SYNTAX          Counter32
           MAX-ACCESS      read-only
           STATUS          current
           DESCRIPTION
              " This object returns a count of the number of control
              packets that were received in order by this L2TP stack
              since it was last initialized."
           ::= { l2tpStatsEntry 12 }

   l2tpStatsOutOfOrderControlTunnelRecvPackets  OBJECT-TYPE
           SYNTAX          Counter32
           MAX-ACCESS      read-only
           STATUS          current
           DESCRIPTION
              " This object returns a count of the number of control
              packets that were received out of order by this L2TP
              stack since it was last initialized."
           ::= { l2tpStatsEntry 13 }

   l2tpStatsFlowDiscardedControlTunnelRecvPackets    OBJECT-TYPE
           SYNTAX          Counter32
           MAX-ACCESS      read-only
           STATUS          current
           DESCRIPTION
              " This object returns a count of the number of control
              packets that were discarded due to flow control by this
              L2TP stack since it was last initialized."
           ::= { l2tpStatsEntry 14 }

   l2tpStatsOutOfOrderDiscardedControlTunnelRecvPackets   OBJECT-TYPE
           SYNTAX          Counter32
           MAX-ACCESS      read-only
           STATUS          current
           DESCRIPTION
              " This object returns a count of the number of control
              packets that were received and discarded due to ordering
              by this L2TP stack since it was  last initialized."
           ::= { l2tpStatsEntry 15 }

   l2tpStatsControlTunnelSendPackets   OBJECT-TYPE
           SYNTAX          Counter32
           MAX-ACCESS      read-only
           STATUS          current
           DESCRIPTION
              " This object returns a count of the number of control
              packets that were transmitted by this L2TP stack since
              it was last initialized. "
           ::= { l2tpStatsEntry 16 }

   l2tpStatsControlTunnelWithdataSendPackets  OBJECT-TYPE
           SYNTAX          Counter32
           MAX-ACCESS      read-only
           STATUS          current
           DESCRIPTION
              " This object returns a count of the number of control
              packets that were transmitted with data by this L2TP
              stack since it was last initialized."
           ::= { l2tpStatsEntry 17 }

   l2tpStatsControlTunnelWithoutdataSendPackets  OBJECT-TYPE
           SYNTAX          Counter32
           MAX-ACCESS      read-only
           STATUS          current
           DESCRIPTION
              " This object returns a count of the number of Zero
              Length control packets that were transmitted by this
              L2TP stack since it was last initialized."
           ::= { l2tpStatsEntry 18 }

   l2tpStatsControlTunnelFlowControlTimeouts  OBJECT-TYPE
           SYNTAX          Counter32
           MAX-ACCESS      read-only
           STATUS          current
           DESCRIPTION
              " This object returns a count of the number of control
              tunnel timeouts due to flow control that were seen by
              this L2TP stack since it was last initialized."
           ::= { l2tpStatsEntry 19 }

   l2tpStatsLocalControlTunnelFlowControlEnables    OBJECT-TYPE
           SYNTAX          Counter32
           MAX-ACCESS      read-only
           STATUS          current
           DESCRIPTION
              " This object returns a count of the number of local
              control Tunnel flow control enables that were seen by
              this L2TP stack since it was last initialized."
           ::= { l2tpStatsEntry 20 }

   l2tpStatsRemoteControlTunnelFlowControlEnables     OBJECT-TYPE
           SYNTAX          Counter32
           MAX-ACCESS      read-only
           STATUS          current
           DESCRIPTION
              " This object returns a count of the number of remote
              control tunnel flow control enables that were seen by
              this L2TP stack since it was last initialized."
           ::= { l2tpStatsEntry 21 }

   l2tpStatsControlTunnelReassemblyTimeouts    OBJECT-TYPE
           SYNTAX          Counter32
           MAX-ACCESS      read-only
           STATUS          current
           DESCRIPTION
              " This object returns a count of the number of control
              tunnel re-assembly time-outs  that were seen by this
              L2TP stack since it was last initialized."
           ::= { l2tpStatsEntry 22 }

   l2tpStatsDataTunnelRecvPackets     OBJECT-TYPE
           SYNTAX          Counter32
           MAX-ACCESS      read-only
           STATUS          current
           DESCRIPTION
              " This object returns a count of the number of data
              packets that were received by this L2TP stack since
              it was last initialized. "
           ::= { l2tpStatsEntry 23 }

   l2tpStatsDataTunnelWithdataRecvPackets     OBJECT-TYPE
           SYNTAX          Counter32
           MAX-ACCESS      read-only
           STATUS          current
           DESCRIPTION
              " This object returns a count of the number of data
              packets that were received with data by this L2TP stack
              since it was last initialized. "
           ::= { l2tpStatsEntry 24 }

   l2tpStatsDataTunnelWithoutdataRecvPackets    OBJECT-TYPE
           SYNTAX          Counter32
           MAX-ACCESS      read-only
           STATUS          current
           DESCRIPTION
              " This object returns a count of the number of Zero
              Length data packets that were received by this L2TP
              stack since it was last initialized. "
           ::= { l2tpStatsEntry 25 }

   l2tpStatsProcessedDataTunnelRecvPackets  OBJECT-TYPE
           SYNTAX          Counter32
           MAX-ACCESS      read-only
           STATUS          current
           DESCRIPTION
              " This object returns a count of the number of data
              packets that were received and processed by this L2TP
              stack since it was last initialized."
           ::= { l2tpStatsEntry 26 }

   l2tpStatsInSequenceDataTunnelRecvPackets    OBJECT-TYPE
           SYNTAX          Counter32
           MAX-ACCESS      read-only
           STATUS          current
           DESCRIPTION
              " This object returns a count of the number of data
              packets that were received in sequence by this L2TP
              stack since it was last initialized. "
           ::= { l2tpStatsEntry 27 }

   l2tpStatsOutSequenceDataTunnelRecvPackets    OBJECT-TYPE
           SYNTAX          Counter32
           MAX-ACCESS      read-only
           STATUS          current
           DESCRIPTION
              " This object returns a count of the number of data
              packets that were received out of sequence by this
              L2TP stack since it was last initialized."
           ::= { l2tpStatsEntry 28 }

   l2tpStatsInOrderDataTunnelRecvPackets   OBJECT-TYPE
           SYNTAX          Counter32
           MAX-ACCESS      read-only
           STATUS          current
           DESCRIPTION
              " This object returns a count of the number of data
              packets that were received in order by this L2TP
              stack since it was last initialized. "
           ::= { l2tpStatsEntry 29 }

   l2tpStatsOutOfOrderDataTunnelRecvPackets     OBJECT-TYPE
           SYNTAX          Counter32
           MAX-ACCESS      read-only
           STATUS          current
           DESCRIPTION
              " This object returns a count of the number of data
              packets that were received out of order by this L2TP
              stack since it was last initialized. "
           ::= { l2tpStatsEntry 30 }

   l2tpStatsFlowDiscardedDataTunnelRecvPackets    OBJECT-TYPE
           SYNTAX          Counter32
           MAX-ACCESS      read-only
           STATUS          current
           DESCRIPTION
              " This object returns a count of the number of data
              packets that were received and discarded due to flow
              control by this L2TP stack since it was last initialized."
           ::= { l2tpStatsEntry 31 }

   l2tpStatsOutOfOrderDiscardedDataTunnelRecvPackets   OBJECT-TYPE
           SYNTAX          Counter32
           MAX-ACCESS      read-only
           STATUS          current
           DESCRIPTION
              " This object returns a count of the number of data
              packets that were received and discarded due to
              ordering by this L2TP stack since it was last initialized."
           ::= { l2tpStatsEntry 32 }

   l2tpStatsDataTunnelSendPackets    OBJECT-TYPE
           SYNTAX          Counter32
           MAX-ACCESS      read-only
           STATUS          current
           DESCRIPTION
              " This object returns a count of the number of data
              packets that were transmitted on the data Tunnel by
              this L2TP stack since it was last initialized."
           ::= { l2tpStatsEntry 33 }

   l2tpStatsDataTunnelWithdataSendPackets    OBJECT-TYPE
           SYNTAX          Counter32
           MAX-ACCESS      read-only
           STATUS          current
           DESCRIPTION
              " This object returns a count of the number of data
              packets that were transmitted with data by this L2TP
              stack since it was last initialized. "
           ::= { l2tpStatsEntry 34 }

   l2tpStatsDataTunnelWithoutdataSendPackets    OBJECT-TYPE
           SYNTAX          Counter32
           MAX-ACCESS      read-only
           STATUS          current
           DESCRIPTION
              " This object returns a count of the number of Zero
              length data packets that were transmitted by this L2TP
              stack since it was last initialized."
           ::= { l2tpStatsEntry 35 }

   l2tpStatsDataTunnelFlowControlTimeouts      OBJECT-TYPE
           SYNTAX          Counter32
           MAX-ACCESS      read-only
           STATUS          current
           DESCRIPTION
              " This object returns a count of the number of data
              Tunnel flow control time-outs seen by this L2TP stack
              since it was last initialized.  "
           ::= { l2tpStatsEntry 36}

   l2tpStatsLocalDataTunnelFlowControlEnables    OBJECT-TYPE
           SYNTAX          Counter32
           MAX-ACCESS      read-only
           STATUS          current
           DESCRIPTION
              " This object returns a count of the number of local
              data Tunnel flow control enables seen by this L2TP
              stack since it was last initialized."
           ::= { l2tpStatsEntry 37 }

   l2tpStatsRemoteDataTunnelFlowControlEnables    OBJECT-TYPE
           SYNTAX          Counter32
           MAX-ACCESS      read-only
           STATUS          current
           DESCRIPTION
              " This object returns a count of the number of remote
              data Tunnel flow control enables seen by this L2TP
              stack since it was last initialized. "
           ::= { l2tpStatsEntry 38 }

   l2tpStatsDataTunnelReassemblyTimeouts    OBJECT-TYPE
           SYNTAX          Counter32
           MAX-ACCESS      read-only
           STATUS          current
           DESCRIPTION
              " This object returns a count of the number of data
              Tunnel re-assembly time-outs seen by this L2TP stack
              since it was last initialized.  "
           ::= { l2tpStatsEntry 39 }


   l2tpTunnel  OBJECT-IDENTITY
           STATUS      current
           DESCRIPTION
              "The root of the L2TP tunnel Object-Identifiers."
           ::= { l2tp 2 }


   l2tpTunnelQueryTable OBJECT-TYPE
           SYNTAX          SEQUENCE OF L2tpTunnelQueryEntry
           MAX-ACCESS      not-accessible
           STATUS          current
           DESCRIPTION
              "A table containing the READ ONLY parameters for L2TP
               Tunnel MIB."
           ::= { l2tpTunnel 1 }

   l2tpTunnelQueryEntry OBJECT-TYPE
           SYNTAX          L2tpTunnelQueryEntry
           MAX-ACCESS      not-accessible
           STATUS          current
           DESCRIPTION
              "  "
           INDEX           { l2tpTunnelLogicalStackIndex,
                             l2tpTunnelLocalControlTunnelId }
           ::= { l2tpTunnelQueryTable 1 }

   L2tpTunnelQueryEntry ::= SEQUENCE {
           l2tpTunnelLogicalStackIndex
                   INTEGER,
           l2tpTunnelLocalControlTunnelId
                   INTEGER,
           l2tpTunnelPeerControlTunnelId
                   INTEGER,
           l2tpTunnelControlTunnelState
                   INTEGER,
           l2tpTunnelLocalInitConnection
                   TruthValue,
           l2tpTunnelIpAddress
                   IpAddress,
           l2tpTunnelLocalRecvPktWindow
                   INTEGER,
           l2tpTunnelRemoteRecvPktWindow
                   INTEGER,
           l2tpTunnelControlTunnelRecvPkts
                   Counter32,
           l2tpTunnelControlTunnelDataRecvPkts
                   Counter32,
           l2tpTunnelControlTunnelNoDataRecvPkt
                   Counter32,
           l2tpTunnelProcessedControlTunnelRecvPkts
                   Counter32,
           l2tpTunnelInSeqControlTunnelRecvPkts
                   Counter32,
           l2tpTunnelOutOfSequenceControlTunnelRecvPkts
                   Counter32,
           l2tpTunnelInOrderControlTunnelRecvPkts
                   Counter32,
           l2tpTunnelOutOfOrderControlTunnelRecvPkts
                   Counter32,
           l2tpTunnelFlwDiscControlTunnelRecvPk
                   Counter32,
           l2tpTunnelOutOfOrderDisCtlChnRecvPkt
                   Counter32,
           l2tpTunnelCtlTunnelSndPkts
                   Counter32,
           l2tpTunnelCtlTunnelDataSndPkts
                   Counter32,
           l2tpTunnelCtlTunnelNoDataSndPkts
                   Counter32,
           l2tpTunnelCtlTunnelFlwCtlTimeouts
                   Counter32,
           l2tpTunnelLocalCtlTunnelFlwCtlOn
                   TruthValue,
           l2tpTunnelLocalCtlTunnelFlwCtlEnables
                   Counter32,
           l2tpTunnelRemoCtlTunnelFlwCtlOn
                   TruthValue,
           l2tpTunnelRemoCtlTunnelFlwCtlEna
                   Counter32,
           l2tpTunnelCtlTunnelReassmblyTimeouts
                   Counter32,
           l2tpTunnelRemoteHostName
                   OCTET STRING,
		   l2tpTunnelNumActiveSessions
                   INTEGER,
		   l2tpTunnelStartTime
                   INTEGER,
           l2tpTunnelDomainName
                   OCTET STRING }

   l2tpTunnelLogicalStackIndex OBJECT-TYPE
           SYNTAX          INTEGER
           MAX-ACCESS      read-only
           STATUS          current
           DESCRIPTION
              "This object contains a reference to the logical
              l2tp protocol stack and must be the same as the
              l2tpConfigIndex."
           ::= { l2tpTunnelQueryEntry 1 }

   l2tpTunnelLocalControlTunnelId OBJECT-TYPE
           SYNTAX          INTEGER
           MAX-ACCESS      read-only
           STATUS          current
           DESCRIPTION
              "This object contains the local tunnel Identifier."
           ::= { l2tpTunnelQueryEntry 2 }

   l2tpTunnelPeerControlTunnelId OBJECT-TYPE
           SYNTAX          INTEGER
           MAX-ACCESS      read-only
           STATUS          current
           DESCRIPTION
              "This object contains the remote tunnel Identifier."
           ::= { l2tpTunnelQueryEntry 3 }

   l2tpTunnelControlTunnelState OBJECT-TYPE
           SYNTAX          INTEGER{
                                    noState(1),
                                    tunnelAllocated(2),
                                    tunnelConnecting(3),
                                    tunnelStartingSession(4),
                                    tunnelEstablished(5),
                                    tunnelStoppingSession(6),
                                    tunnelDisconnecting(7),
                                    tunnelLost(8),
                                    idleTimeOut(9)
                                  }
           MAX-ACCESS      read-only
           STATUS          current
           DESCRIPTION
              "This field contains the current state of
              the control tunnel. "
           ::= { l2tpTunnelQueryEntry 4 }

   l2tpTunnelLocalInitConnection OBJECT-TYPE
           SYNTAX          TruthValue
           MAX-ACCESS      read-only
           STATUS          current
           DESCRIPTION
              "This object indicates whether the tunnel was
              generated locally or not.  When this object
              returns a value of true(1) the tunnel was
              locally generated."
           ::= { l2tpTunnelQueryEntry 5 }

   l2tpTunnelIpAddress OBJECT-TYPE
           SYNTAX          IpAddress
           MAX-ACCESS      read-only
           STATUS          current
           DESCRIPTION
              "IP address of the remote peer."
           ::= { l2tpTunnelQueryEntry 6 }

   l2tpTunnelLocalRecvPktWindow OBJECT-TYPE
           SYNTAX          INTEGER
           MAX-ACCESS      read-only
           STATUS          current
           DESCRIPTION
              "This object contains the local Send Window Size."
           ::= { l2tpTunnelQueryEntry 7 }

   l2tpTunnelRemoteRecvPktWindow OBJECT-TYPE
           SYNTAX          INTEGER
           MAX-ACCESS      read-only
           STATUS          current
           DESCRIPTION
              "This object contains the remote receive window size."
           ::= { l2tpTunnelQueryEntry 8 }

   l2tpTunnelControlTunnelRecvPkts OBJECT-TYPE
           SYNTAX          Counter32
           MAX-ACCESS      read-only
           STATUS          current
           DESCRIPTION
              "This object contains the number of control packets
              received on the control tunnel."
           ::= { l2tpTunnelQueryEntry 9 }

   l2tpTunnelControlTunnelDataRecvPkts OBJECT-TYPE
           SYNTAX          Counter32
           MAX-ACCESS      read-only
           STATUS          current
           DESCRIPTION
              "This object contains the number of control packets
              received with data."
           ::= { l2tpTunnelQueryEntry 10 }

   l2tpTunnelControlTunnelNoDataRecvPkt OBJECT-TYPE
           SYNTAX          Counter32
           MAX-ACCESS      read-only
           STATUS          current
           DESCRIPTION
              "This object contains the number of Zero Length packets
              received."
           ::= { l2tpTunnelQueryEntry 11 }

   l2tpTunnelProcessedControlTunnelRecvPkts OBJECT-TYPE
           SYNTAX          Counter32
           MAX-ACCESS      read-only
           STATUS          current
           DESCRIPTION
              "This object contains the number of received packets
              which were processed."
           ::= { l2tpTunnelQueryEntry 12 }

   l2tpTunnelInSeqControlTunnelRecvPkts OBJECT-TYPE
           SYNTAX          Counter32
           MAX-ACCESS      read-only
           STATUS          current
           DESCRIPTION
              "This object contains the number of packet received
              in sequence."
           ::= { l2tpTunnelQueryEntry 13 }

   l2tpTunnelOutOfSequenceControlTunnelRecvPkts OBJECT-TYPE
           SYNTAX          Counter32
           MAX-ACCESS      read-only
           STATUS          current
           DESCRIPTION
              "This object contains the number of packets received
              out of sequence."
           ::= { l2tpTunnelQueryEntry 14 }

   l2tpTunnelInOrderControlTunnelRecvPkts OBJECT-TYPE
           SYNTAX          Counter32
           MAX-ACCESS      read-only
           STATUS          current
           DESCRIPTION
              "This object contains the number of packets received
              in order."
           ::= { l2tpTunnelQueryEntry 15 }

   l2tpTunnelOutOfOrderControlTunnelRecvPkts OBJECT-TYPE
           SYNTAX          Counter32
           MAX-ACCESS      read-only
           STATUS          current
           DESCRIPTION
              "This object contains the number of packets received
              out of order."
           ::= { l2tpTunnelQueryEntry 16 }

   l2tpTunnelFlwDiscControlTunnelRecvPk OBJECT-TYPE
           SYNTAX          Counter32
           MAX-ACCESS      read-only
           STATUS          current
           DESCRIPTION
              "This object contains the number of received packets
              discarded due to flow control."
           ::= { l2tpTunnelQueryEntry 17 }

   l2tpTunnelOutOfOrderDisCtlChnRecvPkt OBJECT-TYPE
           SYNTAX          Counter32
           MAX-ACCESS      read-only
           STATUS          current
           DESCRIPTION
              "This object contains the number of received packets
              discarded due to ordering."
           ::= { l2tpTunnelQueryEntry 18 }

   l2tpTunnelCtlTunnelSndPkts OBJECT-TYPE
           SYNTAX          Counter32
           MAX-ACCESS      read-only
           STATUS          current
           DESCRIPTION
              "This object contains the number of packets transmitted."
           ::= { l2tpTunnelQueryEntry 19 }

   l2tpTunnelCtlTunnelDataSndPkts OBJECT-TYPE
           SYNTAX          Counter32
           MAX-ACCESS      read-only
           STATUS          current
           DESCRIPTION
              "This object contains the number of packets transmitted
              with data."
           ::= { l2tpTunnelQueryEntry 20 }

   l2tpTunnelCtlTunnelNoDataSndPkts OBJECT-TYPE
           SYNTAX          Counter32
           MAX-ACCESS      read-only
           STATUS          current
           DESCRIPTION
              "This object contains the number of Zero Length packets
              transmitted."
           ::= { l2tpTunnelQueryEntry 21 }

   l2tpTunnelCtlTunnelFlwCtlTimeouts OBJECT-TYPE
           SYNTAX          Counter32
           MAX-ACCESS      read-only
           STATUS          current
           DESCRIPTION
              "This object contains the number of timeouts due to
              flow control."
           ::= { l2tpTunnelQueryEntry 22 }

   l2tpTunnelLocalCtlTunnelFlwCtlOn OBJECT-TYPE
           SYNTAX          TruthValue
           MAX-ACCESS      read-only
           STATUS          current
           DESCRIPTION
              "This object indicates the local flow control status."
           ::= { l2tpTunnelQueryEntry 23 }

   l2tpTunnelLocalCtlTunnelFlwCtlEnables OBJECT-TYPE
           SYNTAX          Counter32
           MAX-ACCESS      read-only
           STATUS          current
           DESCRIPTION
              "This object contains the number of local flow control
              enables for the control session."
           ::= { l2tpTunnelQueryEntry 24 }

   l2tpTunnelRemoCtlTunnelFlwCtlOn OBJECT-TYPE
           SYNTAX          TruthValue
           MAX-ACCESS      read-only
           STATUS          current
           DESCRIPTION
              "This object contains the remote flow control status."
           ::= { l2tpTunnelQueryEntry 25 }

   l2tpTunnelRemoCtlTunnelFlwCtlEna OBJECT-TYPE
           SYNTAX          Counter32
           MAX-ACCESS      read-only
           STATUS          current
           DESCRIPTION
              "This object contains the number of remote flow control
              enables for the control session."
           ::= { l2tpTunnelQueryEntry 26 }

   l2tpTunnelCtlTunnelReassmblyTimeouts OBJECT-TYPE
           SYNTAX          Counter32
           MAX-ACCESS      read-only
           STATUS          current
           DESCRIPTION
              "This object contains the number of reassembly
              timeouts which occurred."
           ::= { l2tpTunnelQueryEntry 27 }

   l2tpTunnelRemoteHostName OBJECT-TYPE
           SYNTAX          OCTET STRING
           MAX-ACCESS      read-only
           STATUS          current
           DESCRIPTION
              "This object contains the host name of the L2TP peer."
           ::= { l2tpTunnelQueryEntry 28 }

   l2tpTunnelNumActiveSessions OBJECT-TYPE
           SYNTAX          INTEGER
           MAX-ACCESS      read-only
           STATUS          current
           DESCRIPTION
              "This object contains the number of sessions beloning to the tunnel."
           ::= { l2tpTunnelQueryEntry 29 }

   l2tpTunnelStartTime OBJECT-TYPE
           SYNTAX          INTEGER
           MAX-ACCESS      read-only
           STATUS          current
           DESCRIPTION
              "This object contains the time elapsed since the tunnel was set up."
           ::= { l2tpTunnelQueryEntry 30 }

   l2tpTunnelDomainName OBJECT-TYPE
           SYNTAX          OCTET STRING
           MAX-ACCESS      read-only
           STATUS          current
           DESCRIPTION
              "This object contains the Domain Name of the L2TP peer."
           ::= { l2tpTunnelQueryEntry 31 }

   l2tpSession OBJECT-IDENTITY
          STATUS         current
          DESCRIPTION
             "The root of L2TP Session Module Object-identifiers."
          ::= { l2tp 3 }

   l2tpSessionTable OBJECT-TYPE
           SYNTAX    SEQUENCE OF L2tpSessionEntry
           MAX-ACCESS not-accessible
           STATUS current
           DESCRIPTION
              ""
           ::= { l2tpSession 1 }

   l2tpSessionEntry OBJECT-TYPE
           SYNTAX          L2tpSessionEntry
           MAX-ACCESS      not-accessible
           STATUS          current
           DESCRIPTION
              "."
           INDEX           { l2tpSessionLogicalStackIndex,
                           l2tpSessionTunnelID , l2tpSessionLocalCallID }
           ::= { l2tpSessionTable 1 }

   L2tpSessionEntry ::= SEQUENCE {
           l2tpSessionLogicalStackIndex
                   INTEGER,
           l2tpSessionTunnelID
                   INTEGER,
           l2tpSessionLocalCallID
                   INTEGER,
           l2tpSessionRemoteCallID
                   INTEGER,
           l2tpSessionPeerName
                   DisplayString,
           l2tpSessionDuration
                   MilliSeconds,
           l2tpSessionLineState
                   INTEGER,
           l2tpSessionCallDeviceNumber
                   INTEGER,
           l2tpSessionCallSerialNumber
                   DisplayString,
           l2tpSessionConnectBps
                   INTEGER,
           l2tpSessionCallBearerType
                   INTEGER,
           l2tpSessionFramingType
                   INTEGER,
           l2tpSessionLocalRecvPacketWindow
                   INTEGER,
           l2tpSessionRemoteRecvPacketWindow
                   INTEGER,
           l2tpSessionRemoteWindowType
                   INTEGER,
           l2tpSessionLocalWindowType
                   INTEGER,
           l2tpSessionDataTunnelRecvPackets
                   Counter32,
           l2tpSessionDataTunnelWithDataRecvPackets
                   Counter32,
           l2tpSessionDataTunnelWithoutDataRecvPackets
                   Counter32,
           l2tpSessionProcessedDataTunnelRecvPackets
                   Counter32,
           l2tpSessionInSequenceDataTunnelRecvPackets
                   Counter32,
           l2tpSessionOutSequenceDataTunnelRecvPackets
                   Counter32,
           l2tpSessionInOrderDatTunnelRecvPackets
                   Counter32,
           l2tpSessionOutOfOrderDataTunnelRecvPackets
                   Counter32,
           l2tpSessionFlowDiscardedDataTunnelRecvPackets
                   Counter32,
           l2tpSessionOutOfOrderDiscardedDataTunnelRecvPackets
                   Counter32,
           l2tpSessionDataTunnelSendPackets
                   Counter32,
           l2tpSessionDataTunnelWithDataSendPackets
                   Counter32,
           l2tpSessionDataTunnelWithoutDataSendPackets
                   Counter32,
           l2tpSessionDataTunnelFlowControlTimeouts
                   Counter32,
           l2tpSessionLocalDataTunnelFlowControlOn
                   TruthValue,
           l2tpSessionLocalDataTunnelFlowControlEnables
                   Counter32,
           l2tpSessionRemoteDataTunnelFlowwControlOn
                   TruthValue,
           l2tpSessionRemoteDataTunnelFlowControlEnables
                   Counter32,
           l2tpSessionDataTunnelReassemblyTimeouts
                   Counter32,
           l2tpSessionRoundTripTime
                   MilliSeconds, 
           l2tpSessionDomainName
                   OCTET STRING,
	   l2tpSessionRemoteIpAddress
		   IpAddress}

   l2tpSessionLogicalStackIndex OBJECT-TYPE
           SYNTAX          INTEGER
           MAX-ACCESS      read-only
           STATUS          current
           DESCRIPTION
              "This object contains a reference to the logical
              l2tp protocol stack and must be the same as the
              l2tpConfigIndex and l2tpTunelLogicalStackIndex."
           ::= { l2tpSessionEntry 1 }

   l2tpSessionTunnelID OBJECT-TYPE
           SYNTAX          INTEGER
           MAX-ACCESS      read-only
           STATUS          current
           DESCRIPTION
              "This object contains the control Channel Tunnel
              identifier for this session"
           ::= { l2tpSessionEntry 2 }

   l2tpSessionLocalCallID  OBJECT-TYPE
           SYNTAX          INTEGER
           MAX-ACCESS      read-only
           STATUS          current
           DESCRIPTION
              "This object contains the local call identifier
              for the session.  "
           ::= { l2tpSessionEntry 3 }

   l2tpSessionRemoteCallID OBJECT-TYPE
           SYNTAX          INTEGER
           MAX-ACCESS      read-only
           STATUS          current
           DESCRIPTION
              "This object contains the remote call identifier
              for the session.  "
           ::= { l2tpSessionEntry 4 }

   l2tpSessionPeerName     OBJECT-TYPE
           SYNTAX          DisplayString
           MAX-ACCESS      read-only
           STATUS          current
           DESCRIPTION
              " identifies the peer session name on this interface.
              This is typically the login name of the remote user "
           ::= { l2tpSessionEntry 5 }

   l2tpSessionDuration     OBJECT-TYPE
           SYNTAX          MilliSeconds
           MAX-ACCESS      read-only
           STATUS          current
           DESCRIPTION
           " Number of milliseconds the session has been up on this
           interface "
           ::= { l2tpSessionEntry 6 }


   l2tpSessionLineState  OBJECT-TYPE
           SYNTAX          INTEGER {
                                    noState(1),
                                    allocated(2),
                                    waitingControlTunnel(3),
                                    calling(4),
                                    offering(5),
                                    answering(6),
                                    connected(7),
                                    disconnectingLocal(8),
                                    disconnectingRemote(9),
                                    lostControlTunnel(10)
                                   }
           MAX-ACCESS      read-only
           STATUS          current
           DESCRIPTION
              "This object contains the current state of the
              control Tunnel. "
           ::= { l2tpSessionEntry 7 }

   l2tpSessionCallDeviceNumber    OBJECT-TYPE
           SYNTAX          INTEGER
           MAX-ACCESS      read-only
           STATUS          current
           DESCRIPTION
              "NO DESCRIPTION PROVIDED"
           ::= { l2tpSessionEntry 8 }

   l2tpSessionCallSerialNumber    OBJECT-TYPE
           SYNTAX          DisplayString
           MAX-ACCESS      read-only
           STATUS          current
           DESCRIPTION
              "This object contains the serial number that applies
              to the session.  "
           ::= { l2tpSessionEntry 9 }

   l2tpSessionConnectBps   OBJECT-TYPE
           SYNTAX          INTEGER
           MAX-ACCESS      read-only
           STATUS          current
           DESCRIPTION
              "This object returns the baud rate which this session
              was established at."
           ::= { l2tpSessionEntry 10 }

   l2tpSessionCallBearerType    OBJECT-TYPE
           SYNTAX          INTEGER {
                                    digital(1),
                                    analog(2)
                                           }
           MAX-ACCESS      read-only
           STATUS          current
           DESCRIPTION
              "This object returns the bearer type that applies to
              this session."
           ::= { l2tpSessionEntry 11 }

   l2tpSessionFramingType  OBJECT-TYPE
           SYNTAX          INTEGER {
                                    asynchronous(1),
                                    synchronous(2)
                                           }
           MAX-ACCESS      read-only
           STATUS          current
           DESCRIPTION
              "This object returns the framing type used for this
              session.  "
           ::= { l2tpSessionEntry 12 }

   l2tpSessionLocalRecvPacketWindow    OBJECT-TYPE
           SYNTAX          INTEGER
           MAX-ACCESS      read-only
           STATUS          current
           DESCRIPTION
              "This object returns the local send window size for
              this session."
           ::= { l2tpSessionEntry 13 }

   l2tpSessionRemoteRecvPacketWindow    OBJECT-TYPE
           SYNTAX          INTEGER
           MAX-ACCESS      read-only
           STATUS          current
           DESCRIPTION
              "This object returns the remote send window size for
              this session."
           ::= { l2tpSessionEntry 14 }

   l2tpSessionRemoteWindowType    OBJECT-TYPE
           SYNTAX          INTEGER {
                                    enabled(1),
                                    disabled(2)
                                           }
           MAX-ACCESS      read-only
           STATUS          current
           DESCRIPTION
              "This object returns the remote window type."
           ::= { l2tpSessionEntry 15 }

   l2tpSessionLocalWindowType    OBJECT-TYPE
           SYNTAX          INTEGER {
                                    enabled(1),
                                    disabled(2)
                                           }
           MAX-ACCESS      read-only
           STATUS          current
           DESCRIPTION
              "This object returns the local window type."
           ::= { l2tpSessionEntry 16 }

   l2tpSessionDataTunnelRecvPackets    OBJECT-TYPE
           SYNTAX          Counter32
           MAX-ACCESS      read-only
           STATUS          current
           DESCRIPTION
              "This object returns the total number of packets received
              on the data Tunnel for this session. "
           ::= { l2tpSessionEntry 17 }

   l2tpSessionDataTunnelWithDataRecvPackets    OBJECT-TYPE
           SYNTAX          Counter32
           MAX-ACCESS      read-only
           STATUS          current
           DESCRIPTION
              "This object returns the total number of packets received
              on the data Tunnel for this session which contained data. "
           ::= { l2tpSessionEntry 18 }

   l2tpSessionDataTunnelWithoutDataRecvPackets    OBJECT-TYPE
           SYNTAX          Counter32
           MAX-ACCESS      read-only
           STATUS          current
           DESCRIPTION
              "This object returns the total number of Zero Length
              packets received on the data Tunnel for this session. "
           ::= { l2tpSessionEntry 19 }

   l2tpSessionProcessedDataTunnelRecvPackets    OBJECT-TYPE
           SYNTAX          Counter32
           MAX-ACCESS      read-only
           STATUS          current
           DESCRIPTION
              "This object returns the total number of packets
              received on the data Tunnel for this session which
              were processed. "
           ::= { l2tpSessionEntry 20 }

   l2tpSessionInSequenceDataTunnelRecvPackets    OBJECT-TYPE
           SYNTAX          Counter32
           MAX-ACCESS      read-only
           STATUS          current
           DESCRIPTION
              "This object returns the total number of packets
              received on the data Tunnel for this session which
              were received in sequence.  "
           ::= { l2tpSessionEntry 21 }

   l2tpSessionOutSequenceDataTunnelRecvPackets    OBJECT-TYPE
           SYNTAX          Counter32
           MAX-ACCESS      read-only
           STATUS          current
           DESCRIPTION
              "This object returns the total number of packets
              received on the data Tunnel for this session which
              were received out of sequence. "
           ::= { l2tpSessionEntry 22 }

   l2tpSessionInOrderDatTunnelRecvPackets    OBJECT-TYPE
           SYNTAX          Counter32
           MAX-ACCESS      read-only
           STATUS          current
           DESCRIPTION
              "This object returns the total number of packets
              received on the data Tunnel for this session which
              were received in order. "
           ::= { l2tpSessionEntry 23 }

   l2tpSessionOutOfOrderDataTunnelRecvPackets    OBJECT-TYPE
           SYNTAX          Counter32
           MAX-ACCESS      read-only
           STATUS          current
           DESCRIPTION
              "This object returns the total number of packets
              received on the data Tunnel for this session which
              were received out of order. "
           ::= { l2tpSessionEntry 24 }

   l2tpSessionFlowDiscardedDataTunnelRecvPackets    OBJECT-TYPE
           SYNTAX          Counter32
           MAX-ACCESS      read-only
           STATUS          current
           DESCRIPTION
              "This object returns the total number of packets
              received on the data Tunnel for this session which
              were discarded due to flow control. "
           ::= { l2tpSessionEntry 25 }

   l2tpSessionOutOfOrderDiscardedDataTunnelRecvPackets        OBJECT-TYPE
           SYNTAX          Counter32
           MAX-ACCESS      read-only
           STATUS          current
           DESCRIPTION
              "This object returns the total number of packets
              received on the data Tunnel for this session which
              were discarded due to ordering. "
           ::= { l2tpSessionEntry 26 }

   l2tpSessionDataTunnelSendPackets    OBJECT-TYPE
           SYNTAX          Counter32
           MAX-ACCESS      read-only
           STATUS          current
           DESCRIPTION
              "This object returns the total number of packets
              transmitted on the data Tunnel for this session.  "
           ::= { l2tpSessionEntry 27 }

   l2tpSessionDataTunnelWithDataSendPackets    OBJECT-TYPE
           SYNTAX          Counter32
           MAX-ACCESS      read-only
           STATUS          current
           DESCRIPTION
              "This object returns the total number of packets
              transmitted on the data Tunnel for this session
              which contained data.  "
           ::= { l2tpSessionEntry 28 }

   l2tpSessionDataTunnelWithoutDataSendPackets    OBJECT-TYPE
           SYNTAX          Counter32
           MAX-ACCESS      read-only
           STATUS          current
           DESCRIPTION
              "This object returns the total number of Zero
              Length packets transmitted on the data Tunnel
              for this session.  "
           ::= { l2tpSessionEntry 29 }

   l2tpSessionDataTunnelFlowControlTimeouts    OBJECT-TYPE
           SYNTAX          Counter32
           MAX-ACCESS      read-only
           STATUS          current
           DESCRIPTION
              "This object returns the total number of flow
              control time-outs seen on the data Tunnel for
              this session.  "
           ::= { l2tpSessionEntry 30 }

   l2tpSessionLocalDataTunnelFlowControlOn    OBJECT-TYPE
           SYNTAX          TruthValue
           MAX-ACCESS      read-only
           STATUS          current
           DESCRIPTION
              "This object returns the current local flow control
              state for the data Tunnel of this session."
           ::= { l2tpSessionEntry 31 }

   l2tpSessionLocalDataTunnelFlowControlEnables    OBJECT-TYPE
           SYNTAX          Counter32
           MAX-ACCESS      read-only
           STATUS          current
           DESCRIPTION
              "This object returns the total number of  local flow
              control enables seen on the data Tunnel for this session. "
           ::= { l2tpSessionEntry 32 }

   l2tpSessionRemoteDataTunnelFlowwControlOn    OBJECT-TYPE
           SYNTAX          TruthValue
           MAX-ACCESS      read-only
           STATUS          current
           DESCRIPTION
              "This object returns the current remote flow control
              state for the data Tunnel of this session."
           ::= { l2tpSessionEntry 33 }

   l2tpSessionRemoteDataTunnelFlowControlEnables    OBJECT-TYPE
           SYNTAX          Counter32
           MAX-ACCESS      read-only
           STATUS          current
           DESCRIPTION
              "This object returns the number of  remote flow control
              enables seen on the data Tunnel for this session."
           ::= { l2tpSessionEntry 34 }

   l2tpSessionDataTunnelReassemblyTimeouts    OBJECT-TYPE
           SYNTAX          Counter32
           MAX-ACCESS      read-only
           STATUS          current
           DESCRIPTION
              "This object returns the nubmer of re-assembly time-outs
              seen on the data Tunnel for this session."
           ::= { l2tpSessionEntry 35 }

   l2tpSessionRoundTripTime     OBJECT-TYPE
           SYNTAX          MilliSeconds
           MAX-ACCESS      read-only
           STATUS          current
           DESCRIPTION
           "Round Trip Time of a packe in Milliseconds 
           "
           ::= { l2tpSessionEntry 36 }


   l2tpSessionDomainName OBJECT-TYPE
           SYNTAX          OCTET STRING
           MAX-ACCESS      read-only
           STATUS          current
           DESCRIPTION
              "This object contains the Domain Name of the L2TP peer."
           ::= { l2tpSessionEntry 37 }

   l2tpSessionRemoteIpAddress OBJECT-TYPE
           SYNTAX          IpAddress
           MAX-ACCESS      read-only
           STATUS          current
           DESCRIPTION
              "IP address of the remote peer."
           ::= { l2tpSessionEntry 38 }
   END
--
--	usr_TD.mib - A proprietary MIB file for the tunnel dispatcher 
--
--
-- Author:         Ajoy K Singh 
--
-- $Id: usrTD.mib,v 1.1.2.2 1998/06/23 23:10:02 asingh Exp $
--
--  | Copyright (c) 1995 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-TD-MIB DEFINITIONS ::= BEGIN
	 IMPORTS
         Counter32,OBJECT-IDENTITY, OBJECT-TYPE FROM SNMPv2-SMI
         TruthValue FROM SNMPv2-TC
         TEXTUAL-CONVENTION FROM SNMPv2-TC
         usrTundisp FROM USR-DEFINITIONS-MIB ;

         
usrTDGlobal  OBJECT-IDENTITY

           STATUS          current
           DESCRIPTION
              "The root of the TD global Object-Identifiers."
           ::= { usrTundisp 1 }


usrTDStatsTable OBJECT-TYPE
           SYNTAX          SEQUENCE OF UsrTDStatsEntry 
           MAX-ACCESS      not-accessible
           STATUS          current
           DESCRIPTION
              ""
           ::= { usrTDGlobal 1  }

usrTDStatsEntry OBJECT-TYPE
           SYNTAX          UsrTDStatsEntry 
           MAX-ACCESS      not-accessible
           STATUS          current
           DESCRIPTION
              "."
           INDEX { usrTDConfigIndex }
           ::= {usrTDStatsTable 1 }


UsrTDStatsEntry ::= SEQUENCE {
           usrTDStatsIndex INTEGER,
           usrTDNumPPTPTunnelsSwitchedtoL2TP
                   Counter32,
           usrTDNumPPTPTunnelsSwitchedtoPPTP
                   Counter32,
           usrTDNumL2TPTunnelSwitchedtoPPTP
                   Counter32,
           usrTDNumL2TPTunnelSwitchedtoL2TP 
                   Counter32 ,
           usrTDNumActivePPTPTunnelsSwitchedtoL2TP
                   Counter32 ,
           usrTDNumActivePPTPTunnelsSwitchedtoPPTP
                   Counter32,
           usrTDNumActiveL2TPTunnelsSwitchedtoPPTP
                   Counter32,
           usrTDNumActiveL2TPTunnelsSwitchedtoL2TP
                   Counter32
 }

usrTDStatsIndex  OBJECT-TYPE
    SYNTAX INTEGER
    MAX-ACCESS      read-only
    STATUS          current
    DESCRIPTION
            " A unique value for each tundispatcher protocol stack. "
         ::= { usrTDStatsEntry 1 }

usrTDNumPPTPTunnelsSwitchedtoL2TP OBJECT-TYPE
           SYNTAX          Counter32
           MAX-ACCESS      read-only
           STATUS          current
           DESCRIPTION
               "Defines the number of PPTPTunnelsSwitchedtoL2TP." 
           ::= { usrTDStatsEntry 2 }

usrTDNumPPTPTunnelsSwitchedtoPPTP OBJECT-TYPE
           SYNTAX          Counter32
           MAX-ACCESS      read-only
           STATUS          current
           DESCRIPTION
               "Defines the number of usrTDNumPPTPTunnelsSwitchedtoPPTP."   
           ::= { usrTDStatsEntry 3 }

usrTDNumL2TPTunnelSwitchedtoPPTP OBJECT-TYPE   
           SYNTAX          Counter32
           MAX-ACCESS      read-only
           STATUS          current
           DESCRIPTION
               "Defines the number of usrTDNumL2TPTunnelSwitchedtoPPTP."
           ::= { usrTDStatsEntry 4 }

usrTDNumL2TPTunnelSwitchedtoL2TP OBJECT-TYPE   
           SYNTAX          Counter32
           MAX-ACCESS      read-only
           STATUS          current
           DESCRIPTION
               "Defines the number of usrTDNumL2TPTunnelSwitchedtoL2TP."
           ::= { usrTDStatsEntry 5 }

usrTDNumActivePPTPTunnelsSwitchedtoL2TP OBJECT-TYPE
	  SYNTAX 	Counter32
          MAX-ACCESS    read-only
	  STATUS          current
          DESCRIPTION
                 "Defines the number of usrTDNumActivePPTPTunnelsSwitchedtoL2TP."
           ::= { usrTDStatsEntry 6 }

usrTDNumActivePPTPTunnelsSwitchedtoPPTP OBJECT-TYPE
          SYNTAX        Counter32
          MAX-ACCESS    read-only
          STATUS          current 
          DESCRIPTION 
                 "Defines the number of usrTDNumActivePPTPTunnelsSwitchedtoPPTP."
           ::= { usrTDStatsEntry 7 }

usrTDNumActiveL2TPTunnelsSwitchedtoPPTP OBJECT-TYPE 
          SYNTAX        Counter32
          MAX-ACCESS    read-only
          STATUS        current
          DESCRIPTION
                 "Defines the number of usrTDNumActiveL2TPTunnelsSwitchedtoL2TP."
          ::= { usrTDStatsEntry 8 }

usrTDNumActiveL2TPTunnelsSwitchedtoL2TP OBJECT-TYPE 
          SYNTAX        Counter32
          MAX-ACCESS    read-only
          STATUS        current  
          DESCRIPTION
                 "Defines the number of usrTDNumActiveL2TPTunnelsSwitchedtoL2TP."
          ::= { usrTDStatsEntry 9 } 

usrTDConfigTable OBJECT-TYPE
           SYNTAX          SEQUENCE OF UsrTDConfigEntry
           MAX-ACCESS      not-accessible
           STATUS          current
           DESCRIPTION
              ""
           ::= { usrTDGlobal 2 }

usrTDConfigEntry OBJECT-TYPE
           SYNTAX          UsrTDConfigEntry
           MAX-ACCESS      not-accessible
           STATUS          current
           DESCRIPTION
              "."
           INDEX { usrTDConfigIndex }
           ::= {usrTDConfigTable 1 }

UsrTDConfigEntry ::= SEQUENCE {
           usrTDConfigIndex INTEGER,
           usrTunnelSwitchEnabled TruthValue
 }


usrTDConfigIndex  OBJECT-TYPE
    SYNTAX INTEGER
    MAX-ACCESS      read-only
    STATUS          current
    DESCRIPTION
            " A unique value for each tundispatcher protocol stack. "
         ::= { usrTDConfigEntry 1 }

usrTunnelSwitchEnabled  OBJECT-TYPE
       SYNTAX          TruthValue
       MAX-ACCESS      read-write
       STATUS          current
       DESCRIPTION
            "Defines.If Load Balancing is enabled or not."
       DEFVAL          { true }
       ::= { usrTDConfigEntry 2 }

END    -- End USR-DNS-MIB definitions 

--
--	usr_NPPTP.mib - A proprietary MIB file for the Point to Point tunneling protocol 
--
--
-- Author:         Ajoy K Singh 
--
-- $Id: usrNPPTP.mib,v 1.1.2.8 1998/06/22 21:17:33 rverma Exp $
--
--  | Copyright (c) 1995 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-PPTP-MIB DEFINITIONS ::= BEGIN
	 IMPORTS
         Counter32,OBJECT-IDENTITY, OBJECT-TYPE FROM SNMPv2-SMI
	 RowStatus,
	 TruthValue
         FROM SNMPv2-TC
         IpAddress
                FROM RFC1155-SMI
         TEXTUAL-CONVENTION FROM SNMPv2-TC
         DisplayString,usrPptp,UsrConfigStatus 
         	FROM USR-DEFINITIONS-MIB;

         
   MilliSeconds ::=  TEXTUAL-CONVENTION
          DISPLAY-HINT    "d-3"
          STATUS          current
          DESCRIPTION     
              " A period of time measured in units of .001 of seconds
              when used in conjunction with the DISPLAY-HINT will
              show seconds and fractions of second with a resolution
              of .001 of a second."
       SYNTAX          INTEGER (0..2147483646)      
         

   usrPPTPGlobal  OBJECT-IDENTITY
           STATUS          current
           DESCRIPTION
              "The root of the PPTP global Object-Identifiers."
           ::= { usrPptp 1 }

   usrPPTPConfigTable OBJECT-TYPE
           SYNTAX          SEQUENCE OF UsrPPTPConfigEntry
           MAX-ACCESS      not-accessible
           STATUS          current
           DESCRIPTION
              ""
           ::= { usrPPTPGlobal 1 }

   usrPptpConfigEntry OBJECT-TYPE
           SYNTAX          UsrPPTPConfigEntry
           MAX-ACCESS      not-accessible
           STATUS          current
           DESCRIPTION
              "."
           INDEX           { usrPptpConfigIndex }
           ::= { usrPPTPConfigTable 1 }

   UsrPPTPConfigEntry ::= SEQUENCE {
           usrPptpConfigIndex
                   INTEGER,
           usrPptpMaxNumberOfSessions
                   INTEGER,
           usrPptpMaxNumberOfTunnels
                   INTEGER,
           usrPptpControlTunnelSeekDescriptors
                   INTEGER,
           usrPptpUseDataTunnelFlowControl
                   TruthValue,
           usrPptpDataTunnelDelayedAckTimeout
                   MilliSeconds,
           usrPptpDataTunnelReassemblyTimeout
                   MilliSeconds,
           usrPptpDataChannelRecvPacketWindow
                   INTEGER,
           usrPptpHelloInactivityHoldTime
                   INTEGER,
           usrPptpEchoReplyTimeoutSeconds
                   INTEGER,
           usrPptpLoggingLevel
                   INTEGER,
           usrPptpLoadBalancing
                   TruthValue,
           usrPptpDialOut
                OCTET STRING,
	   usrPptpPnsFlag 
                    INTEGER 
       }

   usrPptpConfigIndex     OBJECT-TYPE
           SYNTAX          INTEGER
           MAX-ACCESS      read-only
           STATUS          current
           DESCRIPTION
              " A unique value for each pptp protocol stack. "
           ::= { usrPptpConfigEntry 1 }

   usrPptpMaxNumberOfSessions OBJECT-TYPE
           SYNTAX          INTEGER
           MAX-ACCESS      read-write
           STATUS          current
           DESCRIPTION
               "Defines the number of simultaneous active sessions
               that the PPTP stack will support."
           DEFVAL          { 0 }
              --CONFIGURABLE
           ::= { usrPptpConfigEntry 2 }

   usrPptpMaxNumberOfTunnels OBJECT-TYPE
           SYNTAX          INTEGER
           MAX-ACCESS      read-write
           STATUS          current
           DESCRIPTION
               "Defines the number of simultaneous active tunnels
               that the PPTP stack will support. Remember that sessions
               are multiplexed within a single tunnel, therefore this
               object contains the number of active PPTP tunnel
               sessions which are to be supported per tunnel."
           DEFVAL          { 0 }
               --CONFIGURABLE
           ::= { usrPptpConfigEntry 3 }

   usrPptpControlTunnelSeekDescriptors  OBJECT-TYPE
           SYNTAX          INTEGER
           MAX-ACCESS      read-write
           STATUS          current
           DESCRIPTION
              "Defines the number of tunnel terminators which the PPTP
              stack is to be able to simultaneous connect to. Once a
              tunnel is in the established state, the seek descriptor
              is no longer used."
           DEFVAL          { 8 }
              --CONFIGURABLE
           ::= { usrPptpConfigEntry 4 }

    usrPptpUseDataTunnelFlowControl  OBJECT-TYPE
           SYNTAX          TruthValue
           MAX-ACCESS      read-write
           STATUS          current
           DESCRIPTION
              "This object determines whether or not the PPTP stack is
              to use flow control on the data tunnel."
           DEFVAL          { false }
              --CONFIGURABLE
           ::= { usrPptpConfigEntry 5 }


    usrPptpDataTunnelDelayedAckTimeout  OBJECT-TYPE
           SYNTAX          MilliSeconds
           MAX-ACCESS      read-write
           STATUS          current
           DESCRIPTION
              "This object defines the number of milliseconds which the
              PPTP stack will wait  to send and ACK to it's peer in the
              case where there are no data or control packets to piggy-
              back the ACK to.  The default value for this object is 0
              which results in immediate acknowledgment when there are
              no data or control packets pending."
             DEFVAL          { 0 }
            --CONFIGURABLE
           ::= { usrPptpConfigEntry 6 }

     
     usrPptpDataTunnelReassemblyTimeout  OBJECT-TYPE
           SYNTAX          MilliSeconds
           MAX-ACCESS      read-write
           STATUS          current
           DESCRIPTION
              "This object defines the number of milliseconds that the
              PPTP stack will use to determine the window to use before
              reassembling out of order packets. A low value increases
              the chance of out-of-sequence packets to be lost (which
              MAY causes the PPP decompression engine to reset), a high
              value increases the time period where the PPTP stack
              processes packets which were received out of order
              (especially in the case of a packet which was lost within
              the network).  The default value for this object is zero
              (0) which may result in all out of sequence packets being
              lost."
           DEFVAL          { 0 }
           --CONFIGURABLE
           ::= { usrPptpConfigEntry 7 }

   
   usrPptpDataChannelRecvPacketWindow  OBJECT-TYPE
           SYNTAX          INTEGER
           MAX-ACCESS      read-write
           STATUS          current
           DESCRIPTION
              "This object defines the Data Channel receive window
              size which is transmitted to the PPTP peers."
           DEFVAL          { 7 }
           --CONFIGURABLE
           ::= { usrPptpConfigEntry 8 }

    usrPptpHelloInactivityHoldTime    OBJECT-TYPE
           SYNTAX          INTEGER
           MAX-ACCESS      read-write
           STATUS          current
           DESCRIPTION
              "This object defines the length of the inactivity timer
              in seconds which causes the PPTP stack to transmit a
              keep-alive packet (known as Hello)."
           DEFVAL          { 0 }
            --CONFIGURABLE
           ::= { usrPptpConfigEntry 9 }

    usrPptpEchoReplyTimeoutSeconds  OBJECT-TYPE
           SYNTAX          INTEGER
           MAX-ACCESS      read-write
           STATUS          current
           DESCRIPTION
              "This object defines the number of seconds which the PPTP
              stack must wait until a time-out occurs in receiving a
              response to the Hello  message."
           DEFVAL          { 0 }
              --CONFIGURABLE
           ::= { usrPptpConfigEntry 10 }

     usrPptpLoggingLevel  OBJECT-TYPE
           SYNTAX          INTEGER {
               logDisabled(1),
               logControlPackets(2),
               logControlAndDataPacketHeaders(3),
               logControlAndDataPackets(4)
           }
           MAX-ACCESS      read-write
           STATUS          current
           DESCRIPTION
              "This object defines the logging level which the PPTP
              protocol stack will use."
           DEFVAL          { logDisabled }
                --CONFIGURABLE
           ::= { usrPptpConfigEntry 11 }

     
   usrPptpLoadBalancing  OBJECT-TYPE
           SYNTAX          TruthValue
           MAX-ACCESS      read-write
           STATUS          current
           DESCRIPTION
              "Defines If Load Balancing is enabled or not."
           DEFVAL          { true }
             --CONFIGURABLE 
           ::= { usrPptpConfigEntry 12 }

usrPptpDialOut OBJECT-TYPE
        SYNTAX  OCTET STRING (SIZE(0..32))
        MAX-ACCESS  read-write
        STATUS  current
        DESCRIPTION
                "This variable is set through the CLI when the user
                 manually issues a PPTP dial-out."
        ::= { usrPptpConfigEntry 13 }

 usrPptpPnsFlag OBJECT-TYPE
      SYNTAX   INTEGER { enabled(1), disabled(2) }
      MAX-ACCESS   read-write 
      STATUS   current
      DESCRIPTION
             "Setting this object to a value of enabled(1) will enable      
              the PPTP pns enable feature. Setting this object to
              disabled(2) will disable the PPTP PNS feature."
     --CONFIGURABLE 
 ::= { usrPptpConfigEntry 14 }



usrPPTPStatsTable OBJECT-TYPE
           SYNTAX          SEQUENCE OF UsrPPTPStatsEntry 
           MAX-ACCESS      not-accessible
           STATUS          current
           DESCRIPTION
              ""
           ::= { usrPPTPGlobal 2 }

usrPptpStatsEntry OBJECT-TYPE
           SYNTAX          UsrPPTPStatsEntry 
           MAX-ACCESS      not-accessible
           STATUS          current
           DESCRIPTION
              "."
           INDEX           { usrPptpStatsIndex }
           ::= {usrPPTPStatsTable 1 }

UsrPPTPStatsEntry ::= SEQUENCE {
           usrPptpStatsIndex
                   INTEGER,
           usrPptpNumActiveTunnels
                   INTEGER,
           usrPptpStatsNumActiveSessions
                   INTEGER,
           usrPptpStatsMalformedPackets
                   Counter32,
           usrPptpStatsControlTunnelRecvPackets
                   Counter32,
           usrPptpStatsProcessedControlTunnelRecvPackets
                   Counter32,
           usrPptpStatsControlTunnelSendPackets
                   Counter32,
           usrPptpStatsDataTunnelRecvPackets
                   Counter32,
           usrPptpStatsDataTunnelWithdataRecvPackets
                   Counter32,
           usrPptpStatsDataTunnelWithoutdataRecvPackets
                   Counter32,
           usrPptpStatsProcessedDataTunnelRecvPackets
                   Counter32,
           usrPptpStatsInSequenceDataTunnelRecvPackets
                   Counter32,
           usrPptpStatsOutSequenceDataTunnelRecvPackets
                   Counter32,
           usrPptpStatsInOrderDataTunnelRecvPackets
                   Counter32,
           usrPptpStatsOutOfOrderDataTunnelRecvPackets
                   Counter32,
           usrPptpStatsFlowDiscardedDataTunnelRecvPackets
                   Counter32,
           usrPptpStatsOutOfOrderDiscardedDataTunnelRecvPackets
                   Counter32,
           usrPptpStatsDataTunnelSendPackets
                   Counter32,
           usrPptpStatsDataTunnelWithdataSendPackets
                   Counter32,
           usrPptpStatsDataTunnelWithoutdataSendPackets
                   Counter32,
           usrPptpStatsDataTunnelFlowControlTimeouts
                   Counter32,
           usrPptpStatsLocalDataTunnelFlowControlEnables
                   Counter32,
           usrPptpStatsRemoteDataTunnelFlowControlEnables
                   Counter32,
           usrPptpStatsDataTunnelReassemblyTimeouts
                   Counter32 }

 usrPptpStatsIndex          OBJECT-TYPE
           SYNTAX          INTEGER
           MAX-ACCESS      read-only
           STATUS          current
           DESCRIPTION
              " Should be the same value as pptpConfigIndex to
              reference the same logical pptp protocol stack. "
           ::= { usrPptpStatsEntry 1 }

 usrPptpNumActiveTunnels  OBJECT-TYPE
           SYNTAX          INTEGER
           MAX-ACCESS      read-only
           STATUS          current
           DESCRIPTION
              "This object returns the number of PPTP tunnels
              that are currently active. "
           ::= { usrPptpStatsEntry 2 }

 usrPptpStatsNumActiveSessions  OBJECT-TYPE
           SYNTAX          INTEGER
           MAX-ACCESS      read-only
           STATUS          current
           DESCRIPTION
              "This object returns the number of PPTP sessions
              that are currently active. "
           ::= { usrPptpStatsEntry 3 }

 usrPptpStatsMalformedPackets    OBJECT-TYPE
           SYNTAX          Counter32
           MAX-ACCESS      read-only
           STATUS          current
           DESCRIPTION
              "This object returns a count of the number of malformed
              packets received by this PPTP stack since it was last
              initialized.   "
           ::= { usrPptpStatsEntry 4 }

  usrPptpStatsControlTunnelRecvPackets   OBJECT-TYPE
           SYNTAX          Counter32
           MAX-ACCESS      read-only
           STATUS          current
           DESCRIPTION
              " This object returns a count of the number of control
              packets received by this PPTP stack since it was last
              initialized."
           ::= { usrPptpStatsEntry 5 }

 usrPptpStatsProcessedControlTunnelRecvPackets   OBJECT-TYPE
           SYNTAX          Counter32
           MAX-ACCESS      read-only
           STATUS          current
           DESCRIPTION
              " This object returns a count of the number of received
              control packets that were processed by this PPTP stack
              since it was last initialized."
           ::= { usrPptpStatsEntry 6 }

 usrPptpStatsControlTunnelSendPackets   OBJECT-TYPE
           SYNTAX          Counter32
           MAX-ACCESS      read-only
           STATUS          current
           DESCRIPTION
              " This object returns a count of the number of control
              packets that were transmitted by this PPTP stack since
              it was last initialized. "
           ::= { usrPptpStatsEntry 7 }

  usrPptpStatsDataTunnelRecvPackets     OBJECT-TYPE
           SYNTAX          Counter32
           MAX-ACCESS      read-only
           STATUS          current
           DESCRIPTION
              " This object returns a count of the number of data
              packets that were received by this PPTP stack since
              it was last initialized. "
           ::= { usrPptpStatsEntry 8 }

   usrPptpStatsDataTunnelWithdataRecvPackets     OBJECT-TYPE
           SYNTAX          Counter32
           MAX-ACCESS      read-only
           STATUS          current
           DESCRIPTION
              " This object returns a count of the number of data
              packets that were received with data by this PPTP stack
              since it was last initialized. "
           ::= { usrPptpStatsEntry 9 }

   usrPptpStatsDataTunnelWithoutdataRecvPackets    OBJECT-TYPE
           SYNTAX          Counter32
           MAX-ACCESS      read-only
           STATUS          current
           DESCRIPTION
              " This object returns a count of the number of Zero
              Length data packets that were received by this PPTP
              stack since it was last initialized. "
           ::= { usrPptpStatsEntry 10 }

    usrPptpStatsProcessedDataTunnelRecvPackets  OBJECT-TYPE
           SYNTAX          Counter32
           MAX-ACCESS      read-only
           STATUS          current
           DESCRIPTION
              " This object returns a count of the number of data
              packets that were received and processed by this PPTP
              stack since it was last initialized."
           ::= { usrPptpStatsEntry 11 }

    usrPptpStatsInSequenceDataTunnelRecvPackets    OBJECT-TYPE
           SYNTAX          Counter32
           MAX-ACCESS      read-only
           STATUS          current
           DESCRIPTION
              " This object returns a count of the number of data
              packets that were received in sequence by this PPTP
              stack since it was last initialized. "
           ::= { usrPptpStatsEntry 12 }

     usrPptpStatsOutSequenceDataTunnelRecvPackets    OBJECT-TYPE
           SYNTAX          Counter32
           MAX-ACCESS      read-only
           STATUS          current
           DESCRIPTION
              " This object returns a count of the number of data
              packets that were received out of sequence by this
              PPTP stack since it was last initialized."
           ::= { usrPptpStatsEntry 13 }

     usrPptpStatsInOrderDataTunnelRecvPackets   OBJECT-TYPE
           SYNTAX          Counter32
           MAX-ACCESS      read-only
           STATUS          current
           DESCRIPTION
              " This object returns a count of the number of data
              packets that were received in order by this PPTP
              stack since it was last initialized. "
           ::= { usrPptpStatsEntry 14 }

       usrPptpStatsOutOfOrderDataTunnelRecvPackets     OBJECT-TYPE
           SYNTAX          Counter32
           MAX-ACCESS      read-only
           STATUS          current
           DESCRIPTION
              " This object returns a count of the number of data
              packets that were received out of order by this PPTP
              stack since it was last initialized. "
           ::= { usrPptpStatsEntry 15 }

         usrPptpStatsFlowDiscardedDataTunnelRecvPackets    OBJECT-TYPE
           SYNTAX          Counter32
           MAX-ACCESS      read-only
           STATUS          current
           DESCRIPTION
              " This object returns a count of the number of data
              packets that were received and discarded due to flow
              control by this PPTP stack since it was last initialized."
           ::= { usrPptpStatsEntry 16 }

         usrPptpStatsOutOfOrderDiscardedDataTunnelRecvPackets   OBJECT-TYPE
           SYNTAX          Counter32
           MAX-ACCESS      read-only
           STATUS          current
           DESCRIPTION
              " This object returns a count of the number of data
              packets that were received and discarded due to
              ordering by this PPTP stack since it was last initialized."
           ::= { usrPptpStatsEntry 17 }

        usrPptpStatsDataTunnelSendPackets    OBJECT-TYPE
           SYNTAX          Counter32
           MAX-ACCESS      read-only
           STATUS          current
           DESCRIPTION
              " This object returns a count of the number of data
              packets that were transmitted on the data Tunnel by
              this PPTP stack since it was last initialized."
           ::= { usrPptpStatsEntry 18 }
 
      usrPptpStatsDataTunnelWithdataSendPackets    OBJECT-TYPE
           SYNTAX          Counter32
           MAX-ACCESS      read-only
           STATUS          current
           DESCRIPTION
              " This object returns a count of the number of data
              packets that were transmitted with data by this PPTP
              stack since it was last initialized. "
           ::= { usrPptpStatsEntry 19 }

       usrPptpStatsDataTunnelWithoutdataSendPackets    OBJECT-TYPE
           SYNTAX          Counter32
           MAX-ACCESS      read-only
           STATUS          current
           DESCRIPTION
              " This object returns a count of the number of Zero
              length data packets that were transmitted by this PPTP
              stack since it was last initialized."
           ::= { usrPptpStatsEntry 20 }

       usrPptpStatsDataTunnelFlowControlTimeouts      OBJECT-TYPE
           SYNTAX          Counter32
           MAX-ACCESS      read-only
           STATUS          current
           DESCRIPTION
              " This object returns a count of the number of data
              Tunnel flow control time-outs seen by this PPTP stack
              since it was last initialized.  "
           ::= { usrPptpStatsEntry 21 }

         usrPptpStatsLocalDataTunnelFlowControlEnables    OBJECT-TYPE
           SYNTAX          Counter32
           MAX-ACCESS      read-only
           STATUS          current
           DESCRIPTION
              " This object returns a count of the number of local
              data Tunnel flow control enables seen by this PPTP
              stack since it was last initialized."
           ::= { usrPptpStatsEntry 22 }
 
         usrPptpStatsRemoteDataTunnelFlowControlEnables    OBJECT-TYPE
           SYNTAX          Counter32
           MAX-ACCESS      read-only
           STATUS          current
           DESCRIPTION
              " This object returns a count of the number of remote
              data Tunnel flow control enables seen by this PPTP
              stack since it was last initialized. "
           ::= { usrPptpStatsEntry 23 }

         usrPptpStatsDataTunnelReassemblyTimeouts    OBJECT-TYPE
           SYNTAX          Counter32
           MAX-ACCESS      read-only
           STATUS          current
           DESCRIPTION
              " This object returns a count of the number of data
              Tunnel re-assembly time-outs seen by this PPTP stack
              since it was last initialized.  "
           ::= { usrPptpStatsEntry 24 }

usrPptpHostTable OBJECT-TYPE
	SYNTAX SEQUENCE OF UsrPptpHostEntry
	MAX-ACCESS not-accessible
	STATUS current
	DESCRIPTION
		"The table of PPTP Hosts. "
::= { usrPptp 2 }

usrPptpHostEntry OBJECT-TYPE
	SYNTAX UsrPptpHostEntry
	MAX-ACCESS not-accessible
	STATUS current
	DESCRIPTION
		"A (conceptual) entry for one pptp Host."
	INDEX { usrPptpHostIndex }
::= { usrPptpHostTable 1 }

UsrPptpHostEntry ::= SEQUENCE {
	usrPptpHostIndex	INTEGER,
	usrPptpHostAddress	IpAddress,
	usrPptpHostStatus      RowStatus
	}

usrPptpHostIndex OBJECT-TYPE
	SYNTAX		INTEGER
	MAX-ACCESS	not-accessible
	STATUS		current
	DESCRIPTION
		"The logical identifier of the Host Table. "
::= { usrPptpHostEntry 1 }

usrPptpHostAddress OBJECT-TYPE
	SYNTAX		IpAddress
	MAX-ACCESS	read-write
	STATUS		current
	DESCRIPTION
		"The specified or resolved ip address of the named Host. "
	--CONFIGURABLE
::= { usrPptpHostEntry 2 }

usrPptpHostStatus OBJECT-TYPE
	SYNTAX		RowStatus
	MAX-ACCESS	read-write
	STATUS		current
	DESCRIPTION
		"The status of this row of the Host Table. "
	--CONFIGURABLE
::= { usrPptpHostEntry 3 }


usrPptpTunnel OBJECT IDENTIFIER ::= {usrPptp 3}
   
   usrPptpTunnelQueryTable OBJECT-TYPE
           SYNTAX          SEQUENCE OF UsrPptpTunnelQueryEntry
           MAX-ACCESS      not-accessible
           STATUS          current
           DESCRIPTION
              "A table containing the READ ONLY propietary extension
                           parameters for PPTP Tunnel MIB."
           ::= { usrPptpTunnel 1 }

  usrPptpTunnelQueryEntry OBJECT-TYPE
           SYNTAX          UsrPptpTunnelQueryEntry
           MAX-ACCESS      not-accessible
           STATUS          current
           DESCRIPTION
              "  "
           INDEX           { usrPptpTunnelLogicalStackIndex,
                             usrPptpTunnelLocalControlTunnelId }
           ::= { usrPptpTunnelQueryTable 1 }

   UsrPptpTunnelQueryEntry ::= SEQUENCE {
           usrPptpTunnelLogicalStackIndex
                   INTEGER,
           usrPptpTunnelLocalControlTunnelId
                   INTEGER,
           usrPptpTunnelControlTunnelState
                   INTEGER,
           usrPptpTunnelLocalInitConnection
                   TruthValue,
           usrPptpTunnelIpAddress
                   IpAddress,
           usrPptpTunnelControlTunnelRecvPkts
                   Counter32,
           usrPptpTunnelProcessedControlTunnelRecvPkts
                   Counter32,
           usrPptpTunnelCtlTunnelSndPkts
                   Counter32,
           usrPptpTunnelRemoteHostName
               OCTET STRING,
           usrPptpTunnelDisconnect
                   INTEGER,
	usrPptpTunnelRemoteHostName  
                   OCTET STRING,
                   usrPptpTunnelNumActiveSessions
                   INTEGER,
                   usrPptpTunnelStartTime 
                   INTEGER,     
           usrPptpTunnelDomainName   
                   OCTET STRING }


   usrPptpTunnelLogicalStackIndex OBJECT-TYPE
           SYNTAX          INTEGER
           MAX-ACCESS      read-only
           STATUS          current
           DESCRIPTION
              "This object contains a reference to the logical
              pptp protocol stack and must be the same as the
              usrNppptpConfigIndex."
           ::= { usrPptpTunnelQueryEntry 1 }

   usrPptpTunnelLocalControlTunnelId OBJECT-TYPE
           SYNTAX          INTEGER
           MAX-ACCESS      read-only
           STATUS          current
           DESCRIPTION
              "This object contains the local tunnel Identifier."
           ::= { usrPptpTunnelQueryEntry 2 }


   usrPptpTunnelControlTunnelState OBJECT-TYPE
           SYNTAX          INTEGER{
                                    noState(1),
                                    tunnelAllocated(2),
                                    tunnelConnecting(3),
                                    tunnelStartingSession(4),
                                    tunnelEstablished(5),
                                    tunnelStoppingSession(6),
                                    tunnelDisconnecting(7),
                                    tunnelLost(8),
                                    idleTimeOut(9)
                                  }
           MAX-ACCESS      read-only
           STATUS          current
           DESCRIPTION
              "This field contains the current state of
              the control tunnel. "
           ::= { usrPptpTunnelQueryEntry 3 }

   usrPptpTunnelLocalInitConnection OBJECT-TYPE
           SYNTAX          TruthValue
           MAX-ACCESS      read-only
           STATUS          current
           DESCRIPTION
              "This object indicates whether the tunnel was
              generated locally or not.  When this object
              returns a value of true(1) the tunnel was
              locally generated."
           ::= { usrPptpTunnelQueryEntry 4 }
 
   usrPptpTunnelIpAddress OBJECT-TYPE
            SYNTAX          IpAddress
            MAX-ACCESS      read-only
            STATUS          current
            DESCRIPTION
              "IP address of the remote peer."
            ::= { usrPptpTunnelQueryEntry 5 }

   usrPptpTunnelControlTunnelRecvPkts OBJECT-TYPE
           SYNTAX          Counter32
           MAX-ACCESS      read-only
           STATUS          current
           DESCRIPTION
              "This object contains the number of control packets
              received on the control tunnel."
           ::= { usrPptpTunnelQueryEntry 6 }
 
    usrPptpTunnelProcessedControlTunnelRecvPkts OBJECT-TYPE
            SYNTAX          Counter32
            MAX-ACCESS      read-only
            STATUS          current
            DESCRIPTION
               "This object contains the number of received packets
               which were processed."
            ::= { usrPptpTunnelQueryEntry 7 }

     usrPptpTunnelCtlTunnelSndPkts OBJECT-TYPE
           SYNTAX          Counter32
           MAX-ACCESS      read-only
           STATUS          current
           DESCRIPTION
              "This object contains the number of packets transmitted."
           ::= { usrPptpTunnelQueryEntry 8 }
 
    usrPptpTunnelRemoteHostName OBJECT-TYPE
             SYNTAX          OCTET STRING
             MAX-ACCESS      read-only
             STATUS          current
             DESCRIPTION
              "This object contains the host name of the PPTP peer."
           ::= { usrPptpTunnelQueryEntry 9 }
 

    usrPptpTunnelDisconnect OBJECT-TYPE
           SYNTAX          INTEGER
           MAX-ACCESS      read-write
           STATUS          current
           DESCRIPTION
              "This object is used to disconnect a specific tunnel."
           ::= { usrPptpTunnelQueryEntry 10 }

   usrPptpTunnelNumActiveSessions OBJECT-TYPE
           SYNTAX          INTEGER
           MAX-ACCESS      read-only
           STATUS          current
           DESCRIPTION   
              "This object contains the number of sessions beloning to the tunnel."
           ::= { usrPptpTunnelQueryEntry 11 }
          
   usrPptpTunnelStartTime OBJECT-TYPE
           SYNTAX          INTEGER
           MAX-ACCESS      read-only
           STATUS          current  
           DESCRIPTION   
              "This object contains the time elapsed since the tunnel was set up."
           ::= { usrPptpTunnelQueryEntry 12 }
           
   usrPptpTunnelDomainName OBJECT-TYPE
           SYNTAX          OCTET STRING
           MAX-ACCESS      read-only
           STATUS          current
           DESCRIPTION
              "This object contains the Domain Name of the L2TP peer."
          ::= { usrPptpTunnelQueryEntry 13 }
 
   usrPptpSession OBJECT-IDENTITY
          STATUS         current 
          DESCRIPTION           
             "The root of PPTP Session Module Object-identifiers."
          ::= { usrPptp 4 }
   
    usrPptpSessionTable OBJECT-TYPE
           SYNTAX    SEQUENCE OF UsrPptpSessionEntry
           MAX-ACCESS not-accessible
           STATUS current
           DESCRIPTION
              ""
           ::= { usrPptpSession 1 }

     usrPptpSessionEntry OBJECT-TYPE
           SYNTAX          UsrPptpSessionEntry
           MAX-ACCESS      not-accessible
           STATUS          current
           DESCRIPTION
              "."
           INDEX          {usrPptpSessionLogicalStackIndex,
                           usrPptpSessionTunnelID , usrPptpSessionLocalCallID }
           ::= { usrPptpSessionTable 1 }


       UsrPptpSessionEntry ::= SEQUENCE {
          usrPptpSessionLogicalStackIndex
                   INTEGER,
          usrPptpSessionTunnelID
                   INTEGER,
          usrPptpSessionLocalCallID
                   INTEGER,
          usrPptpSessionRemoteCallID
                   INTEGER,
	  usrPptpSessionPeerName
                   DisplayString,
          usrPptpSessionDuration
                   MilliSeconds,
          usrPptpSessionLineState
                   INTEGER,
          usrPptpSessionCallDeviceNumber
                   INTEGER,
          usrPptpSessionCallSerialNumber
                   DisplayString,
          usrPptpSessionConnectBps
                   INTEGER,
          usrPptpSessionCallBearerType
                   INTEGER,
          usrPptpSessionFramingType
                   INTEGER,
          usrPptpSessionLocalRecvPacketWindow
                   INTEGER,
          usrPptpSessionRemoteRecvPacketWindow
                   INTEGER,
          usrPptpSessionDataTunnelRecvPackets
                   Counter32,
          usrPptpSessionDisconnect
                   INTEGER,
           usrPptpSessionDomainName   
                   OCTET STRING }

    usrPptpSessionLogicalStackIndex OBJECT-TYPE
           SYNTAX          INTEGER
           MAX-ACCESS      read-only
           STATUS          current
           DESCRIPTION
              "This object contains a reference to the logical
              pptp protocol stack and must be the same as the
              pptpConfigIndex and pptpTunelLogicalStackIndex."
           ::= { usrPptpSessionEntry 1 }

    usrPptpSessionTunnelID OBJECT-TYPE
           SYNTAX          INTEGER
           MAX-ACCESS      read-only
           STATUS          current
           DESCRIPTION
              "This object contains the control Channel Tunnel
              identifier for this session"
           ::= { usrPptpSessionEntry 2 }

      usrPptpSessionLocalCallID  OBJECT-TYPE
           SYNTAX          INTEGER
           MAX-ACCESS      read-only
           STATUS          current
           DESCRIPTION
              "This object contains the local call identifier
              for the session.  "
           ::= { usrPptpSessionEntry 3 }

      usrPptpSessionRemoteCallID OBJECT-TYPE
           SYNTAX          INTEGER
           MAX-ACCESS      read-only
           STATUS          current
           DESCRIPTION
              "This object contains the remote call identifier
              for the session.  "
           ::= { usrPptpSessionEntry 4 }

      usrPptpSessionPeerName  OBJECT-TYPE
           SYNTAX          DisplayString
           MAX-ACCESS      read-only
           STATUS          current
           DESCRIPTION
              " identifies the peer session name on this interface.
              This is typically the login name of the remote user "
           ::= { usrPptpSessionEntry 5 }
 
      usrPptpSessionDuration     OBJECT-TYPE
           SYNTAX          MilliSeconds
           MAX-ACCESS      read-only
           STATUS          current
           DESCRIPTION
           " Number of milliseconds the session has been up on this
           interface "
           ::= { usrPptpSessionEntry 6 }

      usrPptpSessionLineState  OBJECT-TYPE
           SYNTAX          INTEGER {
                                    noState(1),
                                    allocated(2),
                                    waitingControlTunnel(3),
                                    calling(4),
                                    offering(5),
                                    answering(6),
                                    connected(7),
                                    disconnectingLocal(8),
                                    disconnectingRemote(9),
                                    lostControlTunnel(10)
                                   }
           MAX-ACCESS      read-only
           STATUS          current
           DESCRIPTION
              "This object contains the current state of the
              control Tunnel. "
           ::= { usrPptpSessionEntry 7 }

       usrPptpSessionCallDeviceNumber    OBJECT-TYPE
           SYNTAX          INTEGER
           MAX-ACCESS      read-only
           STATUS          current
           DESCRIPTION
              "NO DESCRIPTION PROVIDED"
           ::= { usrPptpSessionEntry 8 }
 
       usrPptpSessionCallSerialNumber    OBJECT-TYPE
           SYNTAX          DisplayString
           MAX-ACCESS      read-only
           STATUS          current
           DESCRIPTION
              "This object contains the serial number that applies
              to the session.  "
           ::= { usrPptpSessionEntry 9 }

       usrPptpSessionConnectBps   OBJECT-TYPE
           SYNTAX          INTEGER
           MAX-ACCESS      read-only
           STATUS          current
           DESCRIPTION
              "This object returns the baud rate which this session
              was established at."
           ::= { usrPptpSessionEntry 10 }
 
        usrPptpSessionCallBearerType    OBJECT-TYPE
            SYNTAX          INTEGER {
                                    digital(2),
                                    analog(1)
                                     }
            MAX-ACCESS      read-only
            STATUS          current
            DESCRIPTION
               "This object returns the bearer type that applies to
                this session."
           ::= { usrPptpSessionEntry 11 }

         usrPptpSessionFramingType  OBJECT-TYPE
           SYNTAX          INTEGER {
                                    asynchronous(1),
                                    synchronous(2)
                                    }
           MAX-ACCESS      read-only
           STATUS          current
           DESCRIPTION
              "This object returns the framing type used for this
              session.  "
           ::= { usrPptpSessionEntry 12 }

   usrPptpSessionLocalRecvPacketWindow    OBJECT-TYPE
           SYNTAX          INTEGER
           MAX-ACCESS      read-only
           STATUS          current
           DESCRIPTION
              "This object returns the local send window size for
              this session."
           ::= { usrPptpSessionEntry 13 }
 
   usrPptpSessionRemoteRecvPacketWindow    OBJECT-TYPE
           SYNTAX          INTEGER
           MAX-ACCESS      read-only
           STATUS          current
           DESCRIPTION
              "This object returns the remote send window size for
              this session."
           ::= { usrPptpSessionEntry 14 }

  usrPptpSessionDataTunnelRecvPackets    OBJECT-TYPE
           SYNTAX          Counter32
           MAX-ACCESS      read-only
           STATUS          current
           DESCRIPTION
              "This object returns the total number of packets received
              on the data Tunnel for this session. "
           ::= { usrPptpSessionEntry 15 }
 
   usrPptpSessionDataTunnelWithDataRecvPackets    OBJECT-TYPE
           SYNTAX          Counter32
           MAX-ACCESS      read-only
           STATUS          current
           DESCRIPTION
              "This object returns the total number of packets received
              on the data Tunnel for this session which contained data. "
           ::= { usrPptpSessionEntry 16 }

    
   usrPptpSessionDataTunnelWithoutDataRecvPackets    OBJECT-TYPE
           SYNTAX          Counter32
           MAX-ACCESS      read-only
           STATUS          current
           DESCRIPTION
              "This object returns the total number of Zero Length
              packets received on the data Tunnel for this session. "
           ::= { usrPptpSessionEntry 17 }
 
   usrPptpSessionProcessedDataTunnelRecvPackets    OBJECT-TYPE
           SYNTAX          Counter32
           MAX-ACCESS      read-only
           STATUS          current
           DESCRIPTION
              "This object returns the total number of packets
              received on the data Tunnel for this session which
              were processed. "
           ::= { usrPptpSessionEntry 18 }

    usrPptpSessionInSequenceDataTunnelRecvPackets    OBJECT-TYPE
           SYNTAX          Counter32
           MAX-ACCESS      read-only
           STATUS          current
           DESCRIPTION
              "This object returns the total number of packets
              received on the data Tunnel for this session which
              were received in sequence.  "
           ::= { usrPptpSessionEntry 19 }
 
    usrPptpSessionOutSequenceDataTunnelRecvPackets    OBJECT-TYPE
           SYNTAX          Counter32
           MAX-ACCESS      read-only
           STATUS          current
           DESCRIPTION
              "This object returns the total number of packets
              received on the data Tunnel for this session which
              were received out of sequence. "
           ::= { usrPptpSessionEntry 20 }

    usrPptpSessionInOrderDatTunnelRecvPackets    OBJECT-TYPE
           SYNTAX          Counter32
           MAX-ACCESS      read-only
           STATUS          current
           DESCRIPTION
              "This object returns the total number of packets
              received on the data Tunnel for this session which
              were received in order. "
           ::= { usrPptpSessionEntry 21 }
 
   usrPptpSessionOutOfOrderDataTunnelRecvPackets    OBJECT-TYPE
           SYNTAX          Counter32
           MAX-ACCESS      read-only
           STATUS          current
           DESCRIPTION
              "This object returns the total number of packets
              received on the data Tunnel for this session which
              were received out of order. "
           ::= { usrPptpSessionEntry 22 }
    

    usrPptpSessionFlowDiscardedDataTunnelRecvPackets    OBJECT-TYPE
           SYNTAX          Counter32
           MAX-ACCESS      read-only
           STATUS          current
           DESCRIPTION
              "This object returns the total number of packets
              received on the data Tunnel for this session which
              were discarded due to flow control. "
           ::= { usrPptpSessionEntry 23 }
 
    usrPptpSessionOutOfOrderDiscardedDataTunnelRecvPackets        OBJECT-TYPE
           SYNTAX          Counter32
           MAX-ACCESS      read-only
           STATUS          current
           DESCRIPTION
              "This object returns the total number of packets
              received on the data Tunnel for this session which
              were discarded due to ordering. "
           ::= { usrPptpSessionEntry 24 }
  
  usrPptpSessionDataTunnelSendPackets    OBJECT-TYPE
           SYNTAX          Counter32
           MAX-ACCESS      read-only
           STATUS          current
           DESCRIPTION
              "This object returns the total number of packets
              transmitted on the data Tunnel for this session.  "
           ::= { usrPptpSessionEntry 25 }
 
   usrPptpSessionDataTunnelWithDataSendPackets    OBJECT-TYPE
           SYNTAX          Counter32
           MAX-ACCESS      read-only
           STATUS          current
           DESCRIPTION
              "This object returns the total number of packets
              transmitted on the data Tunnel for this session
              which contained data.  "
           ::= { usrPptpSessionEntry 26 }

     usrPptpSessionDataTunnelWithoutDataSendPackets    OBJECT-TYPE
           SYNTAX          Counter32
           MAX-ACCESS      read-only
           STATUS          current
           DESCRIPTION
              "This object returns the total number of Zero
              Length packets transmitted on the data Tunnel
              for this session.  "
           ::= { usrPptpSessionEntry 27 }
 
    usrPptpSessionDataTunnelFlowControlTimeouts    OBJECT-TYPE
           SYNTAX          Counter32
           MAX-ACCESS      read-only
           STATUS          current
           DESCRIPTION
              "This object returns the total number of flow
              control time-outs seen on the data Tunnel for
              this session.  "
           ::= { usrPptpSessionEntry 28 }

   usrPptpSessionLocalDataTunnelFlowControlOn    OBJECT-TYPE
           SYNTAX          TruthValue
           MAX-ACCESS      read-only
           STATUS          current
           DESCRIPTION
              "This object returns the current local flow control
              state for the data Tunnel of this session."
           ::= { usrPptpSessionEntry 29 }
 
   usrPptpSessionLocalDataTunnelFlowControlEnables    OBJECT-TYPE
           SYNTAX          Counter32
           MAX-ACCESS      read-only
           STATUS          current
           DESCRIPTION
              "This object returns the total number of  local flow
              control enables seen on the data Tunnel for this session. "
           ::= { usrPptpSessionEntry 30 }

    usrPptpSessionRemoteDataTunnelFlowwControlOn    OBJECT-TYPE
           SYNTAX          TruthValue
           MAX-ACCESS      read-only
           STATUS          current
           DESCRIPTION
              "This object returns the current remote flow control
              state for the data Tunnel of this session."
           ::= { usrPptpSessionEntry 31 }
 
    usrPptpSessionRemoteDataTunnelFlowControlEnables    OBJECT-TYPE
           SYNTAX          Counter32
           MAX-ACCESS      read-only
           STATUS          current
           DESCRIPTION
              "This object returns the number of  remote flow control
              enables seen on the data Tunnel for this session."
           ::= { usrPptpSessionEntry 32 }

     usrPptpSessionDataTunnelReassemblyTimeouts    OBJECT-TYPE
           SYNTAX          Counter32
           MAX-ACCESS      read-only
           STATUS          current
           DESCRIPTION
              "This object returns the nubmer of re-assembly time-outs
              seen on the data Tunnel for this session."
           ::= { usrPptpSessionEntry 33 }

      usrPptpSessionDisconnect OBJECT-TYPE
           SYNTAX          INTEGER
           MAX-ACCESS      read-write
           STATUS          current
           DESCRIPTION
              "This object is used to disconnect a specific tunnel."
           ::= { usrPptpSessionEntry 34 }

   usrPptpSessionDomainName OBJECT-TYPE
           SYNTAX          OCTET STRING
           MAX-ACCESS      read-only
           STATUS          current
           DESCRIPTION
              "This object contains the Domain Name of the L2TP peer."
          ::= { usrPptpSessionEntry 35 }

      usrPPTPConfigFileName OBJECT-TYPE
            SYNTAX      DisplayString
            MAX-ACCESS  read-write
            STATUS      current
            DESCRIPTION
           "The name of a ConfigFile to read/write permanent database records.
            If the value of this object is an empty string, then the
            PPTP process uses the default name `@file://PptpProcess.cfg'. "
            ::= { usrPptp 5 }
 
 usrPPTPCFMStatusFlag  OBJECT-TYPE
          SYNTAX         UsrConfigStatus
          MAX-ACCESS     read-write
          STATUS         current
          DESCRIPTION
                 "CFM Config Flag"
          ::= { usrPptp 6 }

END         -- End USR-DNS-MIB definitions

--
USR-PPPOE-MIB DEFINITIONS ::= BEGIN
 
        IMPORTS
           OBJECT-IDENTITY, OBJECT-TYPE FROM SNMPv2-SMI
             Counter
                  FROM RFC1155-SMI
                TruthValue
                           FROM SNMPv2-TC
          DisplayString, usrPPPoE, UsrConfigStatus
                  FROM USR-DEFINITIONS-MIB;
 
 
   -- Begin managed object definitions here...

usrPPPoEInterfaceTable OBJECT-TYPE
    SYNTAX     SEQUENCE OF UsrPPPoEInterfaceEntry
    MAX-ACCESS not-accessible
    STATUS     current
    DESCRIPTION
    "The table listing the interfaces on which PPPoE is enabled."
    ::= { usrPPPoE 1 }
    
usrPPPoEInterfaceEntry OBJECT-TYPE
    SYNTAX     UsrPPPoEInterfaceEntry
    MAX-ACCESS not-accessible
    STATUS     current
    DESCRIPTION
    "An entry representing an interface on which PPPoE is enabled."
    INDEX      { usrPPPoEInterfaceName }
    ::= { usrPPPoEInterfaceTable 1 }


UsrPPPoEInterfaceEntry ::= SEQUENCE {
    usrPPPoEInterfaceName       DisplayString,
    usrPPPoEInterfaceEnabled      TruthValue
}   
 
usrPPPoEInterfaceName OBJECT-TYPE
    SYNTAX     DisplayString (SIZE (1..32))
    MAX-ACCESS not-accessible
    STATUS     current
    DESCRIPTION
            "The interface name for which PPPoE is enabled."
::= { usrPPPoEInterfaceEntry 1 }
    
usrPPPoEInterfaceEnabled OBJECT-TYPE
    SYNTAX     TruthValue
    MAX-ACCESS read-write
    STATUS     current
    DESCRIPTION
             "Whether PPPoE is enabled or not."
    DEFVAL    { false }
    --CONFIGURABLE
::= { usrPPPoEInterfaceEntry 2 }

usrPPPoEConfigFileName OBJECT-TYPE
          SYNTAX      DisplayString
          MAX-ACCESS  read-write
          STATUS      current
          DESCRIPTION
          "The name of a ConfigFile to read/write permanent database records.
           If the value of this object is an empty string, then the
           PPPoE process uses the default name `@file://PPPoEProcess.cfg'. "
          ::= { usrPPPoE 2 }

usrPPPoECFMStatusFlag  OBJECT-TYPE
          SYNTAX         UsrConfigStatus
          MAX-ACCESS     read-write
          STATUS         current
          DESCRIPTION
                 "CFM Config Flag"
          ::= { usrPPPoE 3 }                   

usrPPPoENumberSessions   OBJECT-TYPE
    SYNTAX  Counter
    MAX-ACCESS  read-only
    STATUS  current
    DESCRIPTION
        "The number of Active PPPoE Sessions"
    ::= { usrPPPoE 4 }

usrPPPoETotalNumberSessions   OBJECT-TYPE
    SYNTAX  Counter
    MAX-ACCESS  read-only
    STATUS  current
    DESCRIPTION
        "The toal number of PPPoE Sessions since reboot"
    ::= { usrPPPoE 5 }

usrPPPoENumberPADIRejected   OBJECT-TYPE
    SYNTAX  Counter
    MAX-ACCESS  read-only
    STATUS  current
    DESCRIPTION
        "The number of PADI discarded"
    ::= { usrPPPoE 6 }

usrPPPoENumberPADIReceived   OBJECT-TYPE
    SYNTAX  Counter
    MAX-ACCESS  read-only
    STATUS  current
    DESCRIPTION
        "The number of PPPoE PADI received"
    ::= { usrPPPoE 7 }

usrPPPoENumberPADRRejected   OBJECT-TYPE
    SYNTAX  Counter
    MAX-ACCESS  read-only
    STATUS  current
    DESCRIPTION
        "The number of PPPoE PADR discarded"
    ::= { usrPPPoE 8 }

usrPPPoENumberPADRReceived   OBJECT-TYPE
    SYNTAX  Counter
    MAX-ACCESS  read-only
    STATUS  current
    DESCRIPTION
        "The number of PPPoE PADR received"
    ::= { usrPPPoE 9 }

usrPPPoENumberPADOTransmitted   OBJECT-TYPE
    SYNTAX  Counter
    MAX-ACCESS  read-only
    STATUS  current
    DESCRIPTION
        "The number of PPPoE PADO transmitted"
    ::= { usrPPPoE 10 }

usrPPPoENumberPADSTransmitted   OBJECT-TYPE
    SYNTAX  Counter
    MAX-ACCESS  read-only
    STATUS  current
    DESCRIPTION
        "The number of PPPoE PADS transmitted"
    ::= { usrPPPoE 11 }

usrPPPoENumberPADT   OBJECT-TYPE
    SYNTAX  Counter
    MAX-ACCESS  read-only
    STATUS  current
    DESCRIPTION
        "The number of PPPoE PADT exchanged"
    ::= { usrPPPoE 12 }

usrPPPoENumberBadPackets   OBJECT-TYPE
    SYNTAX  Counter
    MAX-ACCESS  read-only
    STATUS  current
    DESCRIPTION
        "The number of bad PPPoE packets"
    ::= { usrPPPoE 13 }

usrPPPoECounterResetTime   OBJECT-TYPE
    SYNTAX  Counter
    MAX-ACCESS  read-write
    STATUS  current
    DESCRIPTION
        "The last time PPPoE counters were reset"
    ::= { usrPPPoE 14 }

usrPPPoEMaxTotalSessions   OBJECT-TYPE
    SYNTAX  INTEGER (1..450)
    MAX-ACCESS  read-write
    STATUS  current
    DESCRIPTION
        "The number of maximum allowed PPPoE sessions"
    --CONFIGURABLE
    ::= { usrPPPoE 15 }

usrPPPoEMaxSessionsPerHost   OBJECT-TYPE
    SYNTAX  INTEGER (1..450)
    MAX-ACCESS  read-write
    STATUS  current
    DESCRIPTION
        "The number of maximum allowed PPPoE sessions to a peer"
    --CONFIGURABLE
    ::= { usrPPPoE 16 }

usrPPPoESession OBJECT-IDENTITY      
          STATUS         current    
          DESCRIPTION               
             "The root of PPPoE Session Table"
    ::= { usrPPPoE 17 }
                                    
usrPPPoESessionTable OBJECT-TYPE    
           SYNTAX    SEQUENCE OF UsrPPPoESessionEntry
           MAX-ACCESS not-accessible
           STATUS current
           DESCRIPTION
              ""
           ::= { usrPPPoESession 1 }
 
usrPPPoESessionEntry OBJECT-TYPE
           SYNTAX          UsrPPPoESessionEntry
           MAX-ACCESS      not-accessible
           STATUS          current 
           DESCRIPTION
              "Table of PPPoE sessions in the Access Concentrator"
           INDEX           { usrPPPoESessionID}
           ::= { usrPPPoESessionTable 1 }
 
UsrPPPoESessionEntry ::= SEQUENCE {
       usrPPPoESessionID
                   INTEGER,
	usrPPPoEPeerAddress
                   DisplayString
	}

usrPPPoESessionID OBJECT-TYPE
           SYNTAX          INTEGER
           MAX-ACCESS      read-only
           STATUS          current
           DESCRIPTION
              "This object contains the session
              identifier for this session"
           ::= { usrPPPoESessionEntry 1 }
 
usrPPPoEPeerAddress  OBJECT-TYPE
           SYNTAX          DisplayString
           MAX-ACCESS      read-only
           STATUS          current
           DESCRIPTION
              "This object contains the MAC address for the session peer."
           ::= { usrPPPoESessionEntry 2 }

usrPPPoEServiceNameTable OBJECT-TYPE
    SYNTAX     SEQUENCE OF UsrPPPoEServiceNameEntry
    MAX-ACCESS not-accessible
    STATUS     current
    DESCRIPTION
    "The table listing the service names configured for PPPoE."
    ::= { usrPPPoE 18 }
    
usrPPPoEServiceNameEntry OBJECT-TYPE
    SYNTAX     UsrPPPoEServiceNameEntry
    MAX-ACCESS not-accessible
    STATUS     current
    DESCRIPTION
    "An entry representing service name enabled for PPPoE"
    INDEX      { usrPPPoEServiceName }
    ::= { usrPPPoEServiceNameTable 1 }


UsrPPPoEServiceNameEntry ::= SEQUENCE {
    usrPPPoEServiceName       DisplayString,
    usrPPPoEServiceNameStatus      TruthValue
}   
 
usrPPPoEServiceName OBJECT-TYPE
    SYNTAX     DisplayString (SIZE (1..32))
    MAX-ACCESS not-accessible
    STATUS     current
    DESCRIPTION
            "The service name enabled for PPPoE."
::= { usrPPPoEServiceNameEntry 1 }
    
usrPPPoEServiceNameStatus OBJECT-TYPE
    SYNTAX     TruthValue
    MAX-ACCESS read-write
    STATUS     current
    DESCRIPTION
             "Whether pppoe service name is enabled or not."
    DEFVAL    { false }
    --CONFIGURABLE
::= { usrPPPoEServiceNameEntry 2 }

END         -- End Template MIB definitions

   RS-232-MIB DEFINITIONS ::= BEGIN

   IMPORTS
       MODULE-IDENTITY, OBJECT-TYPE,
       Counter32, Integer32
           FROM SNMPv2-SMI
       InterfaceIndex
           FROM USR-DEFINITIONS-MIB
       transmission
           FROM RFC1213-MIB
       MODULE-COMPLIANCE, OBJECT-GROUP
           FROM SNMPv2-CONF;


   rs232 MODULE-IDENTITY
       LAST-UPDATED "9405261700Z"
       ORGANIZATION "IETF Character MIB Working Group"
       CONTACT-INFO
               "        Bob Stewart
                Postal: Xyplex, Inc.
                        295 Foster Street
                        Littleton, MA 01460

                   Tel: 508-952-4816
                   Fax: 508-952-4887
                E-mail: rlstewart@eng.xyplex.com"
       DESCRIPTION
               "The MIB module for RS-232-like hardware devices."
       ::= { transmission 33 }


   -- Generic RS-232-like information

   rs232Number OBJECT-TYPE
       SYNTAX Integer32
       MAX-ACCESS read-only
       STATUS current
       DESCRIPTION
           "The number of ports (regardless of their current
           state) in the RS-232-like general port table."
       ::= { rs232 1 }


   -- RS-232-like General Port Table

   rs232PortTable OBJECT-TYPE
       SYNTAX SEQUENCE OF Rs232PortEntry
       MAX-ACCESS not-accessible
       STATUS current
       DESCRIPTION
           "A list of port entries.  The number of entries is
           given by the value of rs232Number."
       ::= { rs232 2 }

   rs232PortEntry OBJECT-TYPE
       SYNTAX Rs232PortEntry
       MAX-ACCESS not-accessible
       STATUS current
       DESCRIPTION
           "Status and parameter values for a port."
       INDEX { rs232PortIndex }
       --INSTANCE-REGISTRATION
       ::= { rs232PortTable 1 }

   Rs232PortEntry ::=
       SEQUENCE {
           rs232PortIndex
               InterfaceIndex,
           rs232PortType
               INTEGER,
           rs232PortInSigNumber
               Integer32,
           rs232PortOutSigNumber
               Integer32,
           rs232PortInSpeed
               Integer32,
           rs232PortOutSpeed
               Integer32,
           rs232PortInFlowType
               INTEGER,
           rs232PortOutFlowType
               INTEGER
       }

   rs232PortIndex OBJECT-TYPE
       SYNTAX InterfaceIndex
       MAX-ACCESS read-only
       STATUS current
       DESCRIPTION
           "The value of ifIndex for the port.  By convention
           and if possible, hardware port numbers map directly
           to external connectors.  The value for each port must
           remain constant at least from one re-initialization
           of the network management agent to the next."
       ::= { rs232PortEntry 1 }

   rs232PortType OBJECT-TYPE
       SYNTAX INTEGER { other(1), rs232(2), rs422(3),
                        rs423(4), v35(5), x21(6) }
       MAX-ACCESS read-only
       STATUS current
       DESCRIPTION
           "The port's hardware type."
       ::= { rs232PortEntry 2 }

   rs232PortInSigNumber OBJECT-TYPE
       SYNTAX Integer32
       MAX-ACCESS read-only
       STATUS current
       DESCRIPTION
           "The number of input signals for the port in the
           input signal table (rs232PortInSigTable).  The table
           contains entries only for those signals the software
           can detect and that are useful to observe."
       ::= { rs232PortEntry 3 }

   rs232PortOutSigNumber OBJECT-TYPE
       SYNTAX Integer32
       MAX-ACCESS read-only
       STATUS current
       DESCRIPTION
           "The number of output signals for the port in the
           output signal table (rs232PortOutSigTable).  The
           table contains entries only for those signals the
           software can assert and that are useful to observe."
       ::= { rs232PortEntry 4 }

   rs232PortInSpeed OBJECT-TYPE
       SYNTAX Integer32
       MAX-ACCESS read-write
       STATUS current
       DESCRIPTION
           "The port's input speed in bits per second.  Note that
           non-standard values, such as 9612, are probably not allowed
           on most implementations."
	--CONFIGURABLE
       ::= { rs232PortEntry 5 }

   rs232PortOutSpeed OBJECT-TYPE
       SYNTAX Integer32
       MAX-ACCESS read-write
       STATUS current
       DESCRIPTION
           "The port's output speed in bits per second.  Note that
           non-standard values, such as 9612, are probably not allowed
           on most implementations."
       ::= { rs232PortEntry 6 }

   rs232PortInFlowType OBJECT-TYPE
       SYNTAX INTEGER { none(1), ctsRts(2), dsrDtr(3) }
       MAX-ACCESS read-write
       STATUS current
       DESCRIPTION
           "The port's type of input flow control.  'none'
           indicates no flow control at this level.
           'ctsRts' and 'dsrDtr' indicate use of the indicated
           hardware signals."
	--CONFIGURABLE
       ::= { rs232PortEntry 7 }

   rs232PortOutFlowType OBJECT-TYPE
       SYNTAX INTEGER { none(1), ctsRts(2), dsrDtr(3) }
       MAX-ACCESS read-write
       STATUS current
       DESCRIPTION
           "The port's type of output flow control.  'none'
           indicates no flow control at this level.
           'ctsRts' and 'dsrDtr' indicate use of the indicated
           hardware signals."
       ::= { rs232PortEntry 8 }


   -- RS-232-like Asynchronous Port Table

   rs232AsyncPortTable OBJECT-TYPE
       SYNTAX SEQUENCE OF Rs232AsyncPortEntry
       MAX-ACCESS not-accessible
       STATUS current
       DESCRIPTION
           "A list of asynchronous port entries.  Entries need
           not exist for synchronous ports."
       ::= { rs232 3 }

   rs232AsyncPortEntry OBJECT-TYPE
       SYNTAX Rs232AsyncPortEntry
       MAX-ACCESS not-accessible
       STATUS current
       DESCRIPTION
           "Status and parameter values for an asynchronous
           port."
       INDEX { rs232AsyncPortIndex }
       --INSTANCE-REGISTRATION
       ::= { rs232AsyncPortTable 1 }

   Rs232AsyncPortEntry ::=
       SEQUENCE {
           rs232AsyncPortIndex
               InterfaceIndex,
           rs232AsyncPortBits
               INTEGER,
           rs232AsyncPortStopBits
               INTEGER,
           rs232AsyncPortParity
               INTEGER,
           rs232AsyncPortAutobaud
               INTEGER,
           rs232AsyncPortParityErrs
               Counter32,
           rs232AsyncPortFramingErrs
               Counter32,
           rs232AsyncPortOverrunErrs
               Counter32

       }

   rs232AsyncPortIndex OBJECT-TYPE
       SYNTAX InterfaceIndex
       MAX-ACCESS read-only
       STATUS current
       DESCRIPTION
           "A unique value for each port.  Its value is the
           same as rs232PortIndex for the port."
       ::= { rs232AsyncPortEntry 1 }

   rs232AsyncPortBits OBJECT-TYPE
       SYNTAX INTEGER (5..8)
       MAX-ACCESS read-write
       STATUS current
       DESCRIPTION
           "The port's number of bits in a character."
       ::= { rs232AsyncPortEntry 2 }

   rs232AsyncPortStopBits OBJECT-TYPE
       SYNTAX INTEGER { one(1), two(2),
                        oneAndHalf(3), dynamic(4) }
       MAX-ACCESS read-write
       STATUS current
       DESCRIPTION
           "The port's number of stop bits."
       ::= { rs232AsyncPortEntry 3 }

   rs232AsyncPortParity OBJECT-TYPE
       SYNTAX INTEGER { none(1), odd(2), even(3),
                        mark(4), space(5) }
       MAX-ACCESS read-write
       STATUS current
       DESCRIPTION
           "The port's sense of a character parity bit."
       ::= { rs232AsyncPortEntry 4 }

   rs232AsyncPortAutobaud OBJECT-TYPE
       SYNTAX INTEGER { enabled(1), disabled(2) }
       MAX-ACCESS read-write
       STATUS current
       DESCRIPTION
           "A control for the port's ability to automatically
           sense input speed.

           When rs232PortAutoBaud is 'enabled', a port may
           autobaud to values different from the set values for
           speed, parity, and character size.  As a result a
           network management system may temporarily observe
           values different from what was previously set."
       ::= { rs232AsyncPortEntry 5 }

   rs232AsyncPortParityErrs OBJECT-TYPE
       SYNTAX Counter32
       MAX-ACCESS read-only
       STATUS current
       DESCRIPTION
           "Total number of characters with a parity error,
           input from the port since system re-initialization
           and while the port state was 'up' or 'test'."
       ::= { rs232AsyncPortEntry 6 }

   rs232AsyncPortFramingErrs OBJECT-TYPE
       SYNTAX Counter32
       MAX-ACCESS read-only
       STATUS current
       DESCRIPTION
           "Total number of characters with a framing error,
           input from the port since system re-initialization
           and while the port state was 'up' or 'test'."
       ::= { rs232AsyncPortEntry 7 }

   rs232AsyncPortOverrunErrs OBJECT-TYPE
       SYNTAX Counter32
       MAX-ACCESS read-only
       STATUS current
       DESCRIPTION
           "Total number of characters with an overrun error,
           input from the port since system re-initialization
           and while the port state was 'up' or 'test'."
       ::= { rs232AsyncPortEntry 8 }


   -- RS-232-like Synchronous Port Table

   rs232SyncPortTable OBJECT-TYPE
       SYNTAX SEQUENCE OF Rs232SyncPortEntry
       MAX-ACCESS not-accessible
       STATUS current
       DESCRIPTION
           "A list of asynchronous port entries.  Entries need
           not exist for synchronous ports."
       ::= { rs232 4 }

   rs232SyncPortEntry OBJECT-TYPE
       SYNTAX Rs232SyncPortEntry
       MAX-ACCESS not-accessible
       STATUS current
       DESCRIPTION
           "Status and parameter values for a synchronous
           port."
       INDEX { rs232SyncPortIndex }
       --INSTANCE-REGISTRATION

       ::= { rs232SyncPortTable 1 }

   Rs232SyncPortEntry ::=
       SEQUENCE {
           rs232SyncPortIndex
               InterfaceIndex,
           rs232SyncPortClockSource
               INTEGER,
           rs232SyncPortFrameCheckErrs
               Counter32,
           rs232SyncPortTransmitUnderrunErrs
               Counter32,
           rs232SyncPortReceiveOverrunErrs
               Counter32,
           rs232SyncPortInterruptedFrames
               Counter32,
           rs232SyncPortAbortedFrames
               Counter32,
           rs232SyncPortRole
               INTEGER,
           rs232SyncPortEncoding
               INTEGER,
           rs232SyncPortRTSControl
               INTEGER,
           rs232SyncPortRTSCTSDelay
               Integer32,
           rs232SyncPortMode
               INTEGER,
           rs232SyncPortIdlePattern
               INTEGER,
           rs232SyncPortMinFlags
               Integer32
       }

   rs232SyncPortIndex OBJECT-TYPE
       SYNTAX InterfaceIndex
       MAX-ACCESS read-only
       STATUS current
       DESCRIPTION
           "A unique value for each port.  Its value is the
           same as rs232PortIndex for the port."
       ::= { rs232SyncPortEntry 1 }

   rs232SyncPortClockSource OBJECT-TYPE
       SYNTAX INTEGER { internal(1), external(2), split(3) }
       MAX-ACCESS read-write
       STATUS current
       DESCRIPTION
           "Source of the port's bit rate clock. 'split' means
           the tranmit clock is internal and the receive clock
           is external."
 	--CONFIGURABLE
       ::= { rs232SyncPortEntry 2 }

   rs232SyncPortFrameCheckErrs OBJECT-TYPE
       SYNTAX Counter32
       MAX-ACCESS read-only
       STATUS current
       DESCRIPTION
           "Total number of frames with an invalid frame check
           sequence, input from the port since system
           re-initialization and while the port state was 'up'
           or 'test'."
       ::= { rs232SyncPortEntry 3 }

   rs232SyncPortTransmitUnderrunErrs OBJECT-TYPE
       SYNTAX Counter32
       MAX-ACCESS read-only
       STATUS current
       DESCRIPTION
           "Total number of frames that failed to be
           transmitted on the port since system
           re-initialization and while the port state was 'up'
           or 'test' because data was not available to the
           transmitter in time."
       ::= { rs232SyncPortEntry 4 }

   rs232SyncPortReceiveOverrunErrs OBJECT-TYPE
       SYNTAX Counter32
       MAX-ACCESS read-only
       STATUS current
       DESCRIPTION
           "Total number of frames that failed to be received
           on the port since system re-initialization and while
           the port state was 'up' or 'test' because the
           receiver did not accept the data in time."
       ::= { rs232SyncPortEntry 5 }

   rs232SyncPortInterruptedFrames OBJECT-TYPE
       SYNTAX Counter32
       MAX-ACCESS read-only
       STATUS current
       DESCRIPTION
           "Total number of frames that failed to be received
           or transmitted on the port due to loss of modem
           signals since system re-initialization and while the
           port state was 'up' or 'test'."
       ::= { rs232SyncPortEntry 6 }

   rs232SyncPortAbortedFrames OBJECT-TYPE
       SYNTAX Counter32
       MAX-ACCESS read-only
       STATUS current
       DESCRIPTION
           "Number of frames aborted on the port due to
           receiving an abort sequence since system
           re-initialization and while the port state was 'up'
           or 'test'."
       ::= { rs232SyncPortEntry 7 }

   rs232SyncPortRole OBJECT-TYPE
       SYNTAX INTEGER  { dte(1), dce(2) }
       MAX-ACCESS read-write
       STATUS current
       DESCRIPTION
           "The role the device is playing that is using this port.
              dte    means the device is performing the role of
                     data terminal equipment
              dce    means the device is performing the role of
                     data circuit-terminating equipment."
       DEFVAL { dce }
       ::= { rs232SyncPortEntry 8 }

   rs232SyncPortEncoding OBJECT-TYPE
       SYNTAX INTEGER  { nrz(1), nrzi(2) }
       MAX-ACCESS read-write
       STATUS current
       DESCRIPTION
           "The bit stream encoding technique that is in effect
            for this port.
              nrz    for Non-Return to Zero encoding
              nrzi   for Non-Return to Zero Inverted encoding."
       DEFVAL { nrz }
	--CONFIGURABLE
       ::= { rs232SyncPortEntry 9 }

   rs232SyncPortRTSControl OBJECT-TYPE
       SYNTAX INTEGER  { controlled(1), constant(2) }
       MAX-ACCESS read-write
       STATUS current
       DESCRIPTION
           "The method used to control the Request To Send (RTS)
            signal.

              controlled  when the DTE is asserts RTS each time
                          data needs to be transmitted and drops
                          RTS at some point after data
                          transmission begins.

                          If rs232SyncPortRole is 'dte', the
                          RTS is an output signal. The device
                          will issue a RTS and wait for a CTS
                          from the DCE before starting to
                          transmit.

                          If rs232SyncPortRole is 'dce', the
                          RTS is an input signal. The device
                          will issue a CTS only after having
                          received RTS and waiting the
                          rs232SyncPortRTSCTSDelay interval.

              constant    when the DTE constantly asserts RTS."
       DEFVAL { constant }
	--CONFIGURABLE
       ::= { rs232SyncPortEntry 10 }

   rs232SyncPortRTSCTSDelay OBJECT-TYPE
       SYNTAX Integer32
       MAX-ACCESS read-write
       STATUS current
       DESCRIPTION
           "The interval (in milliseconds) that the DCE must wait
            after it sees RTS asserted before asserting CTS.  This
            object exists in support of older synchronous devices
            that cannot recognize CTS within a certain interval
            after it asserts RTS."
       DEFVAL { 0 }
	--CONFIGURABLE
       ::= { rs232SyncPortEntry 11 }

   rs232SyncPortMode OBJECT-TYPE
       SYNTAX INTEGER  { fdx(1), hdx(2), simplex-receive(3),
                         simplex-send(4) }
       MAX-ACCESS read-write
       STATUS current
       DESCRIPTION
           "The mode of operation of the port with respect to the
            direction and simultaneity of data transfer.

              fdx              when frames on the data link can be
                               transmitted and received at the same
                               time

              hdx              when frames can either be received
                               from the data link or transmitted
                               onto the data link but not at the
                               same time.

              simplex-receive  when frames can only be received on
                               this data link.

              simplex-send     when frames can only be sent on this
                               data link."
       DEFVAL { fdx }
	--CONFIGURABLE
       ::= { rs232SyncPortEntry 12 }

   rs232SyncPortIdlePattern OBJECT-TYPE
       SYNTAX INTEGER  { mark(1), space(2) }
       MAX-ACCESS read-write
       STATUS current
       DESCRIPTION
           "The bit pattern used to indicate an idle line."
       DEFVAL { space }
	--CONFIGURABLE
       ::= { rs232SyncPortEntry 13 }

   rs232SyncPortMinFlags OBJECT-TYPE
       SYNTAX Integer32
       MAX-ACCESS read-write
       STATUS current
       DESCRIPTION
           "The minimum number of flag patterns this port needs in
            order to recognize the end of one frame and the start
            of the next.  Plausible values are 1 and 2."
       DEFVAL { 2 }
	--CONFIGURABLE
       ::= { rs232SyncPortEntry 14 }


   -- Input Signal Table

   rs232InSigTable OBJECT-TYPE
       SYNTAX SEQUENCE OF Rs232InSigEntry
       MAX-ACCESS not-accessible
       STATUS current
       DESCRIPTION
           "A list of port input control signal entries
           implemented and visible to the software on the port,
           and useful to monitor."
       ::= { rs232 5 }

   rs232InSigEntry OBJECT-TYPE
       SYNTAX Rs232InSigEntry
       MAX-ACCESS not-accessible
       STATUS current
       DESCRIPTION
           "Input control signal status for a hardware port."
       INDEX { rs232InSigPortIndex, rs232InSigName }
       --INSTANCE-REGISTRATION

       ::= { rs232InSigTable 1 }

   Rs232InSigEntry ::=
       SEQUENCE {
           rs232InSigPortIndex
               InterfaceIndex,
           rs232InSigName
               INTEGER,
           rs232InSigState
               INTEGER,
           rs232InSigChanges
               Counter32
       }

   rs232InSigPortIndex OBJECT-TYPE
       SYNTAX InterfaceIndex
       MAX-ACCESS read-only
       STATUS current
       DESCRIPTION
           "The value of rs232PortIndex for the port to which
           this entry belongs."
       ::= { rs232InSigEntry 1 }

   rs232InSigName OBJECT-TYPE
       SYNTAX INTEGER { rts(1), cts(2), dsr(3), dtr(4), ri(5),
                        dcd(6), sq(7), srs(8), srts(9),
                        scts(10), sdcd(11) }
       MAX-ACCESS read-only
       STATUS current
       DESCRIPTION
           "Identification of a hardware signal, as follows:

               rts    Request to Send
               cts    Clear to Send
               dsr    Data Set Ready
               dtr    Data Terminal Ready
               ri     Ring Indicator
               dcd    Received Line Signal Detector
               sq     Signal Quality Detector
               srs    Data Signaling Rate Selector
               srts   Secondary Request to Send
               scts   Secondary Clear to Send
               sdcd   Secondary Received Line Signal Detector
           "
       REFERENCE
           "EIA Standard RS-232-C, August 1969."
       ::= { rs232InSigEntry 2 }

   rs232InSigState OBJECT-TYPE
       SYNTAX INTEGER { none(1), on(2), off(3) }
       MAX-ACCESS read-only
       STATUS current
       DESCRIPTION
           "The current signal state."
       ::= { rs232InSigEntry 3 }

   rs232InSigChanges OBJECT-TYPE
       SYNTAX Counter32
       MAX-ACCESS read-only
       STATUS current
       DESCRIPTION
           "The number of times the signal has changed from
           'on' to 'off' or from 'off' to 'on'."
       ::= { rs232InSigEntry 4 }


   -- Output Signal Table

   rs232OutSigTable OBJECT-TYPE
       SYNTAX SEQUENCE OF Rs232OutSigEntry
       MAX-ACCESS not-accessible
       STATUS current
       DESCRIPTION
           "A list of port output control signal entries
           implemented and visible to the software on the port,
           and useful to monitor."
       ::= { rs232 6 }

   rs232OutSigEntry OBJECT-TYPE
       SYNTAX Rs232OutSigEntry
       MAX-ACCESS not-accessible
       STATUS current
       DESCRIPTION
           "Output control signal status for a hardware port."
       INDEX { rs232OutSigPortIndex, rs232OutSigName }
       --INSTANCE-REGISTRATION

       ::= { rs232OutSigTable 1 }

   Rs232OutSigEntry ::=
       SEQUENCE {
           rs232OutSigPortIndex
               InterfaceIndex,
           rs232OutSigName
               INTEGER,
           rs232OutSigState
               INTEGER,
           rs232OutSigChanges
               Counter32
       }

   rs232OutSigPortIndex OBJECT-TYPE
       SYNTAX InterfaceIndex
       MAX-ACCESS read-only
       STATUS current
       DESCRIPTION
           "The value of rs232PortIndex for the port to which
           this entry belongs."
       ::= { rs232OutSigEntry 1 }

   rs232OutSigName OBJECT-TYPE
       SYNTAX INTEGER { rts(1), cts(2), dsr(3), dtr(4), ri(5),
                        dcd(6), sq(7), srs(8), srts(9),
                        scts(10), sdcd(11) }
       MAX-ACCESS read-only
       STATUS current
       DESCRIPTION
           "Identification of a hardware signal, as follows:

               rts    Request to Send
               cts    Clear to Send
               dsr    Data Set Ready
               dtr    Data Terminal Ready
               ri     Ring Indicator
               dcd    Received Line Signal Detector
               sq     Signal Quality Detector
               srs    Data Signaling Rate Selector
               srts   Secondary Request to Send
               scts   Secondary Clear to Send
               sdcd   Secondary Received Line Signal Detector
           "
       REFERENCE
           "EIA Standard RS-232-C, August 1969."
       ::= { rs232OutSigEntry 2 }

   rs232OutSigState OBJECT-TYPE
       SYNTAX INTEGER { none(1), on(2), off(3) }
       MAX-ACCESS read-only
       STATUS current
       DESCRIPTION
           "The current signal state."
       ::= { rs232OutSigEntry 3 }

   rs232OutSigChanges OBJECT-TYPE
       SYNTAX Counter32
       MAX-ACCESS read-only
       STATUS current
       DESCRIPTION
           "The number of times the signal has changed from
           'on' to 'off' or from 'off' to 'on'."
       ::= { rs232OutSigEntry 4 }


   -- conformance information

   rs232Conformance OBJECT IDENTIFIER ::= { rs232 7 }

   rs232Groups      OBJECT IDENTIFIER ::= { rs232Conformance 1 }
   rs232Compliances OBJECT IDENTIFIER ::= { rs232Conformance 2 }


   -- compliance statements

   rs232Compliance MODULE-COMPLIANCE
       STATUS  current
       DESCRIPTION
               "The compliance statement for SNMPv2 entities
               which have RS-232-like hardware interfaces."

       MODULE  -- this module
           MANDATORY-GROUPS { rs232Group }

           GROUP   rs232AsyncGroup
           DESCRIPTION
               "The Asynch group is mandatory only for those
                SNMPv2 entities which have asynchronous
                interfaces Rs-232-like."

           GROUP   rs232SyncGroup
           DESCRIPTION
               "The Synch group is mandatory only for those
                SNMPv2 entities which have synchronous
                interfaces Rs-232-like."
       ::= { rs232Compliances 1 }

   -- units of conformance

   rs232Group    OBJECT-GROUP
       OBJECTS { rs232Number, rs232PortIndex, rs232PortType,
                 rs232PortInSigNumber, rs232PortOutSigNumber,
                 rs232PortInSpeed, rs232PortOutSpeed,
                 rs232PortInFlowType, rs232PortOutFlowType,
                 rs232InSigPortIndex, rs232InSigName,
                 rs232InSigState, rs232InSigChanges,
                 rs232OutSigPortIndex, rs232OutSigName,
                 rs232OutSigState, rs232OutSigChanges }
       STATUS  current
       DESCRIPTION
               "A collection of objects providing information
                applicable to all RS-232-like interfaces."
       ::= { rs232Groups 1 }

   rs232AsyncGroup OBJECT-GROUP
       OBJECTS { rs232AsyncPortIndex, rs232AsyncPortBits,
                 rs232AsyncPortStopBits, rs232AsyncPortParity,
                 rs232AsyncPortAutobaud, rs232AsyncPortParityErrs,
                 rs232AsyncPortFramingErrs, rs232AsyncPortOverrunErrs }
       STATUS  current
       DESCRIPTION
               "A collection of objects providing information
                applicable to asynchronous RS-232-like interfaces."
       ::= { rs232Groups 2 }

   rs232SyncGroup OBJECT-GROUP
       OBJECTS { rs232SyncPortIndex, rs232SyncPortClockSource,
                 rs232SyncPortFrameCheckErrs,
                 rs232SyncPortTransmitUnderrunErrs,
                 rs232SyncPortReceiveOverrunErrs,
                 rs232SyncPortInterruptedFrames,
                 rs232SyncPortAbortedFrames }
       STATUS  current
       DESCRIPTION
               "A collection of objects providing information
                applicable to synchronous RS-232-like interfaces."
       ::= { rs232Groups 3 }

   rs232SyncSDLCGroup OBJECT-GROUP
       OBJECTS { rs232SyncPortRole,
                 rs232SyncPortEncoding,
                 rs232SyncPortRTSControl,
                 rs232SyncPortRTSCTSDelay,
                 rs232SyncPortMode,
                 rs232SyncPortIdlePattern,
                 rs232SyncPortMinFlags }
       STATUS  current
       DESCRIPTION
               "A collection of objects providing information
                applicable to synchronous RS-232-like interfaces
                running SDLC."
       ::= { rs232Groups 4 }

   END
     RFC1406-MIB DEFINITIONS ::= BEGIN
     IMPORTS
             Gauge
                     FROM RFC1155-SMI
             transmission, DisplayString
                     FROM RFC1213-MIB
             OBJECT-TYPE
                     FROM RFC-1212;

     --  This MIB module uses the extended OBJECT-TYPE macro as
     --  defined in RFC 1212.

     --  this is the MIB module for the DS1 objects

     ds1 OBJECT IDENTIFIER ::= { transmission 18 }

     -- note that this subsumes cept (19); there is no separate CEPT MIB


     -- The DS1 Near End Group

     -- Implementation of this group is mandatory for all systems
     -- that attach to a DS1 Interface.

     -- The DS1 Near End Group consists of four tables:
     --    DS1 Configuration
     --    DS1 Current
     --    DS1 Interval
     --    DS1 Total

     -- the DS1 Configuration Table

         dsx1ConfigTable OBJECT-TYPE
             SYNTAX  SEQUENCE OF Dsx1ConfigEntry
             ACCESS  not-accessible
             STATUS  mandatory
             DESCRIPTION
                "The DS1 Configuration table."
            ::= { ds1 6 }


         dsx1ConfigEntry OBJECT-TYPE
             SYNTAX  Dsx1ConfigEntry
             ACCESS  not-accessible
             STATUS  mandatory
             DESCRIPTION
                "An entry in the DS1 Configuration table."
            INDEX   { dsx1LineIndex }
            --INSTANCE-REGISTRATION
            ::= { dsx1ConfigTable 1 }

     Dsx1ConfigEntry ::=
         SEQUENCE {
             dsx1LineIndex
                 INTEGER,
             dsx1IfIndex
                 INTEGER,
             dsx1TimeElapsed
                 INTEGER,
             dsx1ValidIntervals
                 INTEGER,
             dsx1LineType
                 INTEGER,
             dsx1LineCoding
                 INTEGER,
             dsx1SendCode
                 INTEGER,
             dsx1CircuitIdentifier
                 DisplayString,
             dsx1LoopbackConfig
                 INTEGER,
             dsx1LineStatus
                 INTEGER,
             dsx1SignalMode
                 INTEGER,
             dsx1TransmitClockSource
                 INTEGER,
             dsx1Fdl
                 INTEGER
         }

         dsx1LineIndex OBJECT-TYPE
             SYNTAX  INTEGER (1..'7fffffff'h)
             ACCESS  read-only
             STATUS  mandatory
             DESCRIPTION
                "This object is the identifier of a DS1  Inter-
                face on a managed device.  If there is an ifEn-
                try that is directly associated with  this  and
                only  this  DS1  interface,  it should have the
                same value as ifIndex.   Otherwise,  the  value
                exceeds  ifNumber,  and  is a unique identifier
                following this rule: inside  interfaces  (e.g.,
                equipment  side)  with even numbers and outside
                interfaces  (e.g.,  network   side)   with   odd
                numbers."
            ::= { dsx1ConfigEntry 1 }


         dsx1IfIndex OBJECT-TYPE
             SYNTAX  INTEGER (1..'7fffffff'h)
             ACCESS  read-only
             STATUS  mandatory
             DESCRIPTION
                "This value for this object  is  equal  to  the
                value  of  ifIndex from the Interfaces table of
                MIB II (RFC 1213)."
            ::= { dsx1ConfigEntry 2 }


         dsx1TimeElapsed OBJECT-TYPE
             SYNTAX  INTEGER (0..899)
             ACCESS  read-only
             STATUS  mandatory
             DESCRIPTION
                "The number of seconds that have elapsed  since
                the  beginning of the current error-measurement
                period."
            ::= { dsx1ConfigEntry 3 }


         dsx1ValidIntervals OBJECT-TYPE
             SYNTAX  INTEGER (0..96)
             ACCESS  read-only
             STATUS  mandatory
             DESCRIPTION
                "The number of  previous  intervals  for  which
                valid data was collected.  The value will be 96
                unless the interface was brought on-line within
                the last 24 hours, in which case the value will
                be the number of complete 15  minute  intervals
                the since interface has been online."
            ::= { dsx1ConfigEntry 4 }


         dsx1LineType OBJECT-TYPE
             SYNTAX  INTEGER {
                         other(1),
                         dsx1ESF(2),
                         dsx1D4(3),
                         dsx1E1(4),
                         dsx1E1-CRC(5),
                         dsx1E1-MF(6),
                         dsx1E1-CRC-MF(7)
                     }
             ACCESS  read-write
             STATUS  mandatory
             DESCRIPTION
                "This variable indicates  the  variety  of  DS1
                Line  implementing  this  circuit.  The type of
                circuit affects the number of bits  per  second
                that  the circuit can reasonably carry, as well
                as the interpretation of the  usage  and  error
                statistics.  The values, in sequence, describe:

                TITLE:        SPECIFICATION:
                dsx1ESF       Extended SuperFrame DS1
                dsx1D4        AT&T D4 format DS1
                dsx1E1        CCITT Recommendation G.704
                                (Table 4a)
                dsx1E1-CRC    CCITT Recommendation G.704
                                (Table 4b)
                dsxE1-MF      G.704 (Table 4a) with TS16
                                multiframing enabled
                dsx1E1-CRC-MF G.704 (Table 4b) with TS16
                                multiframing enabled"

		--CONFIGURABLE
                    ::= { dsx1ConfigEntry 5 }


         dsx1LineCoding OBJECT-TYPE
             SYNTAX  INTEGER {
                         dsx1JBZS (1),
                         dsx1B8ZS (2),
                         dsx1HDB3 (3),
                         dsx1ZBTSI (4),
                         dsx1AMI (5),
                         other(6)
                     }
             ACCESS  read-write
             STATUS  mandatory
             DESCRIPTION
                "This variable describes the  variety  of  Zero
                Code  Suppression  used  on  the link, which in
                turn affects a number of its characteristics.

                dsx1JBZS refers the Jammed  Bit  Zero  Suppres-
                sion,  in  which  the  AT&T specification of at
                least one pulse every 8 bit periods is literal-
                ly  implemented  by forcing a pulse in bit 8 of
                each channel.  Thus, only seven bits per  chan-
                nel, or 1.344 Mbps, is available for data.

                dsx1B8ZS refers to the use of a specified  pat-
                tern  of  normal  bits  and  bipolar violations
                which are used to replace a sequence  of  eight
                zero bits.

                ANSI Clear Channels may use dsx1ZBTSI, or  Zero
                Byte Time Slot Interchange.

                E1 links, with or without CRC, use dsx1HDB3  or
                dsx1AMI.

                dsx1AMI refers to a mode wherein no  zero  code
                suppression  is  present  and the line encoding
                does not solve the problem directly.   In  this
                application, the higher layer must provide data
                which meets or exceeds the  pulse  density  re-
                quirements, such as inverting HDLC data."
		--CONFIGURABLE
            ::= { dsx1ConfigEntry 6 }


         dsx1SendCode OBJECT-TYPE
             SYNTAX  INTEGER {
                         dsx1SendNoCode(1),
                         dsx1SendLineCode(2),
                         dsx1SendPayloadCode(3),
                         dsx1SendResetCode(4),
                         dsx1SendQRS(5),
                         dsx1Send511Pattern(6),
                         dsx1Send3in24Pattern(7),
                         dsx1SendOtherTestPattern(8)
                     }
             ACCESS  read-write
             STATUS  mandatory
             DESCRIPTION
                "This variable indicates what type of  code  is
                being sent across the DS1 interface by the dev-
                ice.  The values mean:

                dsx1SendNoCode
                     sending looped or normal data

                dsx1SendLineCode
                     sending a request for a line loopback

                dsx1SendPayloadCode
                     sending a request for a payload loopback

                dsx1SendResetCode
                     sending a loopback termination request

                dsx1SendQRS
                     sending a Quasi-Random Signal  (QRS)  test
                     pattern

                dsx1Send511Pattern
                     sending a 511 bit fixed test pattern

                dsx1Send3in24Pattern
                     sending a fixed test pattern of 3 bits set
                     in 24

                dsx1SendOtherTestPattern
                     sending a test pattern  other  than  those
                     described by this object"
            ::= { dsx1ConfigEntry 7 }


         dsx1CircuitIdentifier OBJECT-TYPE
             SYNTAX  DisplayString (SIZE (0..255))
             ACCESS  read-write
             STATUS  mandatory
             DESCRIPTION
                "This  variable   contains   the   transmission
                vendor's circuit identifier, for the purpose of
                facilitating troubleshooting."
		--CONFIGURABLE
            ::= { dsx1ConfigEntry 8 }


         dsx1LoopbackConfig OBJECT-TYPE
             SYNTAX  INTEGER {
                         dsx1NoLoop(1),
                         dsx1PayloadLoop(2),
                         dsx1LineLoop(3),
                         dsx1OtherLoop(4)
                     }
             ACCESS  read-write
             STATUS  mandatory
             DESCRIPTION
                "This variable represents the  loopback  confi-
                guration of the DS1 interface.  Agents support-
                ing read/write access should return badValue in
                response to a requested loopback state that the
                interface does not support.  The values mean:

                dsx1NoLoop
                     Not in the loopback state.  A device  that
                     is not capable of performing a loopback on
                     the interface shall always return this  as
                     it's value.

                dsx1PayloadLoop
                     The received signal at this  interface  is
                     looped  through  the device. Typically the
                     received signal is  looped  back  for  re-
                     transmission  after  it has passed through
                     the device's framing function.

                dsx1LineLoop
                     The received signal at this interface does
                     not  go  through the device (minimum pene-
                     tration) but is looped back out.

                dsx1OtherLoop
                     Loopbacks that are not defined here."
            ::= { dsx1ConfigEntry 9 }


         dsx1LineStatus OBJECT-TYPE
             SYNTAX  INTEGER (1..8191)
             ACCESS  read-only
             STATUS  mandatory
             DESCRIPTION
                "This variable indicates the Line Status of the
                interface.   It contains loopback, failure, re-
                ceived 'alarm'  and transmitted 'alarm'  infor-
                mation.

     The dsx1LineStatus is a bit  map  represented  as  a  sum,
     therefore, it can represent multiple failures (alarms) and
     a LoopbackState simultaneously.

     dsx1NoAlarm should be set if and only if no other flag  is
     set.

     If the dsx1LoopbackState bit is set, the loopback  in  ef-
     fect can be determined from the dsx1LoopbackConfig object.

     The various bit positions are:
          1     dsx1NoAlarm           No Alarm Present
          2     dsx1RcvFarEndLOF      Far end LOF (a.k.a., Yellow Alarm)
          4     dsx1XmtFarEndLOF      Near end sending LOF Indication
          8     dsx1RcvAIS            Far end sending AIS
         16     dsx1XmtAIS            Near end sending AIS
         32     dsx1LossOfFrame       Near end LOF (a.k.a., Red Alarm)
         64     dsx1LossOfSignal      Near end Loss Of Signal
        128     dsx1LoopbackState     Near end is looped
        256     dsx1T16AIS            E1 TS16 AIS
        512     dsx1RcvFarEndLOMF     Far End Sending TS16 LOMF
       1024     dsx1XmtFarEndLOMF     Near End Sending TS16 LOMF
       2048     dsx1RcvTestCode       Near End detects a test code
       4096     dsx1OtherFailure      any line status not defined here"
         ::= { dsx1ConfigEntry 10 }


         dsx1SignalMode OBJECT-TYPE
             SYNTAX  INTEGER {
                         none (1),
                         robbedBit (2),
                         bitOriented (3),
                         messageOriented (4)
                     }
             ACCESS  read-write
             STATUS  mandatory
             DESCRIPTION
                "'none' indicates that no bits are reserved for
                signaling on this channel.

                 'robbedBit' indicates that T1 Robbed Bit  Sig-
                naling is in use.

                 'bitOriented' indicates that E1 Channel  Asso-
                ciated Signaling is in use.

                 'messageOriented' indicates that Common  Chan-
                nel Signaling is in use either on channel 16 of
                an E1 link or channel 24 of a T1."
            ::= { dsx1ConfigEntry 11 }


         dsx1TransmitClockSource OBJECT-TYPE
             SYNTAX  INTEGER {
                         loopTiming (1),
                         localTiming (2),
                         throughTiming (3)
                     }
             ACCESS  read-write
             STATUS  mandatory
             DESCRIPTION
                "The source of Tranmit Clock.

                 'loopTiming' indicates that the recovered  re-
                ceive clock is used as the transmit clock.

                 'localTiming' indicates  that  a  local  clock
                source is used.

                 'throughTiming' indicates that  recovered  re-
                ceive  clock  from another interface is used as
                the transmit clock."
		--CONFIGURABLE
            ::= { dsx1ConfigEntry 12 }


         dsx1Fdl OBJECT-TYPE
             SYNTAX  INTEGER {
                           other(1),
                           dsx1Ansi-T1-403(2),
                           dsx1Att-54016(4),
                           dsx1Fdl-none(8)
                     }
             ACCESS  read-write
             STATUS  mandatory
             DESCRIPTION
                "This bitmap describes the use of  the  facili-
                ties data link, and is the sum of the capabili-
                ties:

                 'other' indicates that a protocol  other  than
                one following is used.

                 'dsx1Ansi-T1-403' refers to the  FDL  exchange
                recommended by ANSI.

                 'dsx1Att-54016' refers to ESF FDL exchanges.

                 'dsx1Fdl-none' indicates that the device  does
                not use the FDL."
		--CONFIGURABLE
            ::= { dsx1ConfigEntry 13 }


     -- the DS1 Current Table

     -- The DS1 current table contains various statistics being
     -- collected for the current 15 minute interval.

         dsx1CurrentTable OBJECT-TYPE
             SYNTAX  SEQUENCE OF Dsx1CurrentEntry
             ACCESS  not-accessible
             STATUS  mandatory
             DESCRIPTION
                "The DS1 Current table."
            ::= { ds1 7 }


         dsx1CurrentEntry OBJECT-TYPE
             SYNTAX  Dsx1CurrentEntry
             ACCESS  not-accessible
             STATUS  mandatory
             DESCRIPTION
                "An entry in the DS1 Current table."
            INDEX   { dsx1CurrentIndex }
            --INSTANCE-REGISTRATION
            ::= { dsx1CurrentTable 1 }

     Dsx1CurrentEntry ::=
         SEQUENCE {
             dsx1CurrentIndex
                 INTEGER,
             dsx1CurrentESs
                 Gauge,
             dsx1CurrentSESs
                 Gauge,
             dsx1CurrentSEFSs
                 Gauge,
             dsx1CurrentUASs
                 Gauge,
             dsx1CurrentCSSs
                 Gauge,
             dsx1CurrentPCVs
                 Gauge,
             dsx1CurrentLESs
                 Gauge,
             dsx1CurrentBESs
                 Gauge,
             dsx1CurrentDMs
                 Gauge,
             dsx1CurrentLCVs
                 Gauge
         }

         dsx1CurrentIndex OBJECT-TYPE
             SYNTAX  INTEGER (1..'7fffffff'h)
             ACCESS  read-only
             STATUS  mandatory
             DESCRIPTION
                "The index value which uniquely identifies  the
                DS1  interface  to which this entry is applica-
                ble.  The interface identified by a  particular
                value  of  this  index is the same interface as
                identified by the same value as a dsx1LineIndex
                object instance."
            ::= { dsx1CurrentEntry 1 }


         dsx1CurrentESs OBJECT-TYPE
             SYNTAX  Gauge
             ACCESS  read-only
             STATUS  mandatory
             DESCRIPTION
                "The number of Errored Seconds, encountered  by
                a DS1 interface in the current 15 minute inter-
                val."
            ::= { dsx1CurrentEntry 2 }


         dsx1CurrentSESs OBJECT-TYPE
             SYNTAX  Gauge
             ACCESS  read-only
             STATUS  mandatory
             DESCRIPTION
                "The number of Severely Errored Seconds encoun-
                tered  by  a  DS1  interface  in the current 15
                minute interval."
            ::= { dsx1CurrentEntry 3 }


         dsx1CurrentSEFSs OBJECT-TYPE
             SYNTAX  Gauge
             ACCESS  read-only
             STATUS  mandatory
             DESCRIPTION
                "The number of Severely Errored Framing Seconds
                encountered  by  a DS1 interface in the current
                15 minute interval."
            ::= { dsx1CurrentEntry 4 }


         dsx1CurrentUASs OBJECT-TYPE
             SYNTAX  Gauge
             ACCESS  read-only
             STATUS  mandatory
             DESCRIPTION
                "The number of Unavailable Seconds  encountered
                by a DS1 interface in the current 15 minute in-
                terval."
            ::= { dsx1CurrentEntry 5 }

         dsx1CurrentCSSs OBJECT-TYPE
             SYNTAX  Gauge
             ACCESS  read-only
             STATUS  mandatory
             DESCRIPTION
                "The number of Controlled Slip Seconds  encoun-
                tered  by  a  DS1  interface  in the current 15
                minute interval."
            ::= { dsx1CurrentEntry 6 }


         dsx1CurrentPCVs OBJECT-TYPE
             SYNTAX  Gauge
             ACCESS  read-only
             STATUS  mandatory
             DESCRIPTION
                "The number of Path Coding  Violations  encoun-
                tered  by  a  DS1  interface  in the current 15
                minute interval."
            ::= { dsx1CurrentEntry 7 }


         dsx1CurrentLESs OBJECT-TYPE
             SYNTAX  Gauge
             ACCESS  read-only
             STATUS  mandatory
             DESCRIPTION
                "The number of Line Errored Seconds encountered
                by a DS1 interface in the current 15 minute in-
                terval."
            ::= { dsx1CurrentEntry 8 }


         dsx1CurrentBESs OBJECT-TYPE
             SYNTAX Gauge
             ACCESS read-only
             STATUS mandatory
             DESCRIPTION
                "The number of Bursty  Errored  Seconds  (BESs)
                encountered  by  a DS1 interface in the current
                15 minute interval."
            ::= {dsx1CurrentEntry 9 }


         dsx1CurrentDMs OBJECT-TYPE
             SYNTAX Gauge
             ACCESS read-only
             STATUS mandatory
             DESCRIPTION
                "The number of Degraded Minutes  (DMs)  encoun-
                tered  by  a  DS1  interface  in the current 15
                minute interval."
            ::= { dsx1CurrentEntry 10 }


         dsx1CurrentLCVs OBJECT-TYPE
             SYNTAX Gauge
             ACCESS read-only
             STATUS mandatory
             DESCRIPTION
                "The number of Line Code Violations (LCVs)  en-
                countered  by a DS1 interface in the current 15
                minute interval."
         ::= {dsx1CurrentEntry 11 }


     -- the DS1 Interval

     -- The DS1 Interval Table contains various statistics
     -- collected by each DS1 Interface over the previous 24 hours of
     -- operation.  The past 24 hours are broken into 96 completed
     -- 15 minute intervals.

         dsx1IntervalTable OBJECT-TYPE
             SYNTAX  SEQUENCE OF Dsx1IntervalEntry
             ACCESS  not-accessible
             STATUS  mandatory
             DESCRIPTION
                "The DS1 Interval table."
            ::= { ds1 8 }


         dsx1IntervalEntry OBJECT-TYPE
             SYNTAX  Dsx1IntervalEntry
             ACCESS  not-accessible
             STATUS  mandatory
             DESCRIPTION
                "An entry in the DS1 Interval table."
            INDEX   { dsx1IntervalIndex, dsx1IntervalNumber }
            --INSTANCE-REGISTRATION
            ::= { dsx1IntervalTable 1 }

     Dsx1IntervalEntry ::=
         SEQUENCE {
             dsx1IntervalIndex
                 INTEGER,
             dsx1IntervalNumber
                 INTEGER,
             dsx1IntervalESs
                 Gauge,
             dsx1IntervalSESs
                 Gauge,
             dsx1IntervalSEFSs
                 Gauge,
             dsx1IntervalUASs
                 Gauge,
             dsx1IntervalCSSs
                 Gauge,
             dsx1IntervalPCVs
                 Gauge,
             dsx1IntervalLESs
                 Gauge,
             dsx1IntervalBESs
                 Gauge,
             dsx1IntervalDMs
                 Gauge,
             dsx1IntervalLCVs
                 Gauge
         }

         dsx1IntervalIndex OBJECT-TYPE
             SYNTAX  INTEGER (1..'7fffffff'h)
             ACCESS  read-only
             STATUS  mandatory
             DESCRIPTION
                "The index value which uniquely identifies  the
                DS1  interface  to which this entry is applica-
                ble.  The interface identified by a  particular
                value  of  this  index is the same interface as
                identified by the same value as a dsx1LineIndex
                object instance."
            ::= { dsx1IntervalEntry 1 }


         dsx1IntervalNumber OBJECT-TYPE
             SYNTAX  INTEGER (1..96)
             ACCESS  read-only
             STATUS  mandatory
             DESCRIPTION
                "A number between 1 and 96, where 1 is the most
                recently completed 15 minute interval and 96 is
                the least recently completed 15 minutes  inter-
                val   (assuming   that  all  96  intervals  are
                valid)."
            ::= { dsx1IntervalEntry 2 }


         dsx1IntervalESs OBJECT-TYPE
             SYNTAX  Gauge
             ACCESS  read-only
             STATUS  mandatory
             DESCRIPTION
                "The number of Errored Seconds encountered by a
                DS1  interface in one of the previous 96, indi-
                vidual 15 minute, intervals."
            ::= { dsx1IntervalEntry 3 }


         dsx1IntervalSESs OBJECT-TYPE
             SYNTAX  Gauge
             ACCESS  read-only
             STATUS  mandatory
             DESCRIPTION
                "The number of Severely Errored Seconds encoun-
                tered by a DS1 interface in one of the previous
                96, individual 15 minute, intervals."
            ::= { dsx1IntervalEntry 4 }


         dsx1IntervalSEFSs OBJECT-TYPE
             SYNTAX  Gauge
             ACCESS  read-only
             STATUS  mandatory
             DESCRIPTION
                "The number of Severely Errored Framing Seconds
                encountered  by  a  DS1 interface in one of the
                previous 96, individual 15 minute, intervals."
            ::= { dsx1IntervalEntry 5 }


         dsx1IntervalUASs OBJECT-TYPE
             SYNTAX  Gauge
             ACCESS  read-only
             STATUS  mandatory
             DESCRIPTION
                "The number of Unavailable Seconds  encountered
                by  a  DS1 interface in one of the previous 96,
                individual 15 minute, intervals."
            ::= { dsx1IntervalEntry 6 }


         dsx1IntervalCSSs OBJECT-TYPE
             SYNTAX  Gauge
             ACCESS  read-only
             STATUS  mandatory
             DESCRIPTION
                "The number of Controlled Slip Seconds  encoun-
                tered by a DS1 interface in one of the previous
                96, individual 15 minute, intervals."
            ::= { dsx1IntervalEntry 7 }


         dsx1IntervalPCVs OBJECT-TYPE
             SYNTAX  Gauge
             ACCESS  read-only
             STATUS  mandatory
             DESCRIPTION
                "The number of Path Coding  Violations  encoun-
                tered by a DS1 interface in one of the previous
                96, individual 15 minute, intervals."
            ::= { dsx1IntervalEntry 8 }


         dsx1IntervalLESs OBJECT-TYPE
             SYNTAX  Gauge
             ACCESS  read-only
             STATUS  mandatory
             DESCRIPTION
                "The number of Line Errored Seconds encountered
                by  a  DS1 interface in one of the previous 96,
                individual 15 minute, intervals."
            ::= { dsx1IntervalEntry 9 }


         dsx1IntervalBESs OBJECT-TYPE
             SYNTAX Gauge
             ACCESS read-only
             STATUS mandatory
             DESCRIPTION
                "The number of Bursty  Errored  Seconds  (BESs)
                encountered  by  a  DS1 interface in one of the
                previous 96, individual 15 minute, intervals."
            ::= {dsx1IntervalEntry 10 }


         dsx1IntervalDMs OBJECT-TYPE
             SYNTAX Gauge
             ACCESS read-only
             STATUS mandatory
             DESCRIPTION
                "The number of Degraded Minutes  (DMs)  encoun-
                tered by a DS1 interface in one of the previous
                96, individual 15 minute, intervals."
            ::= { dsx1IntervalEntry 11 }


         dsx1IntervalLCVs OBJECT-TYPE
             SYNTAX Gauge
             ACCESS read-only
             STATUS mandatory
             DESCRIPTION
                "The number of Line Code Violations (LCVs)  en-
                countered  by a DS1 interface in the current 15
                minute interval."
         ::= {dsx1IntervalEntry 12 }


     -- the DS1 Total

     -- The DS1 Total Table contains the cumulative sum of the
     -- various statistics for the 24 hour period preceding the
     -- current interval.

         dsx1TotalTable OBJECT-TYPE
             SYNTAX  SEQUENCE OF Dsx1TotalEntry
             ACCESS  not-accessible
             STATUS  mandatory
             DESCRIPTION
                "The DS1 Total table.  24 hour interval."
            ::= { ds1 9 }


         dsx1TotalEntry OBJECT-TYPE
             SYNTAX  Dsx1TotalEntry
             ACCESS  not-accessible
             STATUS  mandatory
             DESCRIPTION
                "An entry in the DS1 Total table."
            INDEX   { dsx1TotalIndex }
            --INSTANCE-REGISTRATION
            ::= { dsx1TotalTable 1 }

     Dsx1TotalEntry ::=
         SEQUENCE {
             dsx1TotalIndex
                 INTEGER,
             dsx1TotalESs
                 Gauge,
             dsx1TotalSESs
                 Gauge,
             dsx1TotalSEFSs
                 Gauge,
             dsx1TotalUASs
                 Gauge,
             dsx1TotalCSSs
                 Gauge,
             dsx1TotalPCVs
                 Gauge,
             dsx1TotalLESs
                 Gauge,
             dsx1TotalBESs
                 Gauge,
             dsx1TotalDMs
                 Gauge,
             dsx1TotalLCVs
                 Gauge
         }

         dsx1TotalIndex OBJECT-TYPE
             SYNTAX  INTEGER (1..'7fffffff'h)
             ACCESS  read-only
             STATUS  mandatory
             DESCRIPTION
                "The index value which uniquely identifies  the
                DS1  interface  to which this entry is applica-
                ble.  The interface identified by a  particular
                value  of  this  index is the same interface as
                identified by the same value as a dsx1LineIndex
                object instance."
            ::= { dsx1TotalEntry 1 }


         dsx1TotalESs OBJECT-TYPE
             SYNTAX  Gauge
             ACCESS  read-only
             STATUS  mandatory
             DESCRIPTION
                "The number of Errored Seconds encountered by a
                DS1 interface in the previous 24 hour interval"
            ::= { dsx1TotalEntry 2 }


         dsx1TotalSESs OBJECT-TYPE
             SYNTAX  Gauge
             ACCESS  read-only
             STATUS  mandatory
             DESCRIPTION
                "The number of Severely Errored Seconds encoun-
                tered  by  a  DS1  interface in the previous 24
                hour interval."
            ::= { dsx1TotalEntry 3 }


         dsx1TotalSEFSs OBJECT-TYPE
             SYNTAX  Gauge
             ACCESS  read-only
             STATUS  mandatory
             DESCRIPTION
                "The number of Severely Errored Framing Seconds
                encountered  by a DS1 interface in the previous
                24 hour interval."
            ::= { dsx1TotalEntry 4 }


         dsx1TotalUASs OBJECT-TYPE
             SYNTAX  Gauge
             ACCESS  read-only
             STATUS  mandatory
             DESCRIPTION
                "The number of Unavailable Seconds  encountered
                by  a DS1 interface in the previous 24 hour in-
                terval."
            ::= { dsx1TotalEntry 5 }


         dsx1TotalCSSs OBJECT-TYPE
             SYNTAX  Gauge
             ACCESS  read-only
             STATUS  mandatory
             DESCRIPTION
                "The number of Controlled Slip Seconds  encoun-
                tered  by  a  DS1  interface in the previous 24
                hour interval."
            ::= { dsx1TotalEntry 6 }


         dsx1TotalPCVs OBJECT-TYPE
             SYNTAX  Gauge
             ACCESS  read-only
             STATUS  mandatory
             DESCRIPTION
                "The number of Path Coding  Violations  encoun-
                tered  by  a  DS1  interface in the previous 24
                hour interval."
            ::= { dsx1TotalEntry 7 }


         dsx1TotalLESs OBJECT-TYPE
             SYNTAX  Gauge
             ACCESS  read-only
             STATUS  mandatory
             DESCRIPTION
                "The number of Line Errored Seconds encountered
                by  a DS1 interface in the previous 24 hour in-
                terval."
            ::= { dsx1TotalEntry 8 }


         dsx1TotalBESs OBJECT-TYPE
             SYNTAX Gauge
             ACCESS read-only
             STATUS mandatory
             DESCRIPTION
                "The number of Bursty  Errored  Seconds  (BESs)
                encountered  by a DS1 interface in the previous
                24 hour interval."
            ::= { dsx1TotalEntry 9 }


         dsx1TotalDMs OBJECT-TYPE
             SYNTAX Gauge
             ACCESS read-only
             STATUS mandatory
             DESCRIPTION
                "The number of Degraded Minutes  (DMs)  encoun-
                tered  by  a  DS1  interface in the previous 24
                hour interval."
            ::= { dsx1TotalEntry 10 }


         dsx1TotalLCVs OBJECT-TYPE
             SYNTAX Gauge
             ACCESS read-only
             STATUS mandatory
             DESCRIPTION
                "The number of Line Code Violations (LCVs)  en-
                countered  by a DS1 interface in the current 15
                minute interval."
         ::= {dsx1TotalEntry 11 }


     -- The DS1 Far End Group

     -- Implementation of this group is optional for all systems
     -- that attach to a DS1 Interface.
     -- The DS1 Far End Group consists of three tables:
     --   DS1 Far End Current
     --   DS1 Far End Interval
     --   DS1 Far End Total

     -- The DS1 Far End Current Table

     -- The DS1 Far End Current table contains various statistics
     -- being collected for the current 15 minute interval.
     -- The statistics are collected from the far end messages on the
     -- Facilities Data Link.  The definitions are the same as
     -- described for the near-end information.

         dsx1FarEndCurrentTable OBJECT-TYPE
             SYNTAX  SEQUENCE OF Dsx1FarEndCurrentEntry
             ACCESS  not-accessible
             STATUS  mandatory
             DESCRIPTION
                "The DS1 Far End Current table."
            ::= { ds1 10 }


         dsx1FarEndCurrentEntry OBJECT-TYPE
             SYNTAX  Dsx1FarEndCurrentEntry
             ACCESS  not-accessible
             STATUS  mandatory
             DESCRIPTION
                "An entry in the DS1 Far End Current table."
            INDEX   { dsx1FarEndCurrentIndex }
            --INSTANCE-REGISTRATION
            ::= { dsx1FarEndCurrentTable 1 }

      Dsx1FarEndCurrentEntry ::=
         SEQUENCE {
             dsx1FarEndCurrentIndex
                 INTEGER,
             dsx1FarEndTimeElapsed
                 INTEGER,
             dsx1FarEndValidIntervals
                 INTEGER,
             dsx1FarEndCurrentESs
                 Gauge,
             dsx1FarEndCurrentSESs
                 Gauge,
             dsx1FarEndCurrentSEFSs
                 Gauge,
             dsx1FarEndCurrentUASs
                 Gauge,
             dsx1FarEndCurrentCSSs
                 Gauge,
             dsx1FarEndCurrentLESs
                 Gauge,
             dsx1FarEndCurrentPCVs
                 Gauge,
             dsx1FarEndCurrentBESs
                 Gauge,
             dsx1FarEndCurrentDMs
                 Gauge
         }

         dsx1FarEndCurrentIndex OBJECT-TYPE
             SYNTAX  INTEGER (1..'7fffffff'h)
             ACCESS  read-only
             STATUS  mandatory
             DESCRIPTION
                "The index value which uniquely identifies  the
                DS1  interface  to which this entry is applica-
                ble.  The interface identified by a  particular
                value  of  this  index is the same interface as
                identified by the same value  an  dsx1LineIndex
                object instance."
            ::= { dsx1FarEndCurrentEntry 1 }


         dsx1FarEndTimeElapsed OBJECT-TYPE
             SYNTAX  INTEGER (0..899)
             ACCESS  read-only
             STATUS  mandatory
             DESCRIPTION
                     "The number of seconds that  have  elapsed
                     since the beginning of the far end current
                     error-measurement period."
            ::= { dsx1FarEndCurrentEntry 2 }


         dsx1FarEndValidIntervals OBJECT-TYPE
             SYNTAX  INTEGER (0..96)
             ACCESS  read-only
             STATUS  mandatory
             DESCRIPTION
                     "The number of previous far end  intervals
                     for  which  valid data was collected.  The
                     value will be 96 unless the interface  was
                     brought  online  within the last 24 hours,
                     in which case the value will be the number
                     of  complete  15  minute far end intervals
                     since the interface has been online."
            ::= { dsx1FarEndCurrentEntry 3 }


         dsx1FarEndCurrentESs OBJECT-TYPE
             SYNTAX  Gauge
             ACCESS  read-only
             STATUS  mandatory
             DESCRIPTION
                "The number of Far Far End Errored Seconds  en-
                countered  by a DS1 interface in the current 15
                minute interval."
            ::= { dsx1FarEndCurrentEntry 4 }


         dsx1FarEndCurrentSESs OBJECT-TYPE
             SYNTAX  Gauge
             ACCESS  read-only
             STATUS  mandatory
             DESCRIPTION
                "The number of Far End Severely Errored Seconds
                encountered  by  a DS1 interface in the current
                15 minute interval."
            ::= { dsx1FarEndCurrentEntry 5 }


         dsx1FarEndCurrentSEFSs OBJECT-TYPE
             SYNTAX  Gauge
             ACCESS  read-only
             STATUS  mandatory
             DESCRIPTION
                "The number of Far End Severely Errored Framing
                Seconds  encountered  by a DS1 interface in the
                current 15 minute interval."
            ::= { dsx1FarEndCurrentEntry 6 }


         dsx1FarEndCurrentUASs OBJECT-TYPE
             SYNTAX  Gauge
             ACCESS  read-only
             STATUS  mandatory
             DESCRIPTION
                "The number of Unavailable Seconds  encountered
                by a DS1 interface in the current 15 minute in-
                terval."
            ::= { dsx1FarEndCurrentEntry 7 }


         dsx1FarEndCurrentCSSs OBJECT-TYPE
             SYNTAX  Gauge
             ACCESS  read-only
             STATUS  mandatory
             DESCRIPTION
                "The number of Far End Controlled Slip  Seconds
                encountered  by  a DS1 interface in the current
                15 minute interval."
            ::= { dsx1FarEndCurrentEntry 8 }


         dsx1FarEndCurrentLESs OBJECT-TYPE
             SYNTAX  Gauge
             ACCESS  read-only
             STATUS  mandatory
             DESCRIPTION
                "The number of Far End Line Errored Seconds en-
                countered  by a DS1 interface in the current 15
                minute interval."
            ::= { dsx1FarEndCurrentEntry 9 }


         dsx1FarEndCurrentPCVs OBJECT-TYPE
             SYNTAX  Gauge
             ACCESS  read-only
             STATUS  mandatory
             DESCRIPTION
                "The number of Far End Path  Coding  Violations
                reported  via the far end block error count en-
                countered by a DS1 interface in the current  15
                minute interval."
            ::= { dsx1FarEndCurrentEntry 10 }


         dsx1FarEndCurrentBESs OBJECT-TYPE
             SYNTAX Gauge
             ACCESS read-only
             STATUS mandatory
             DESCRIPTION
                "The number of Bursty  Errored  Seconds  (BESs)
                encountered  by  a DS1 interface in the current
                15 minute interval."
            ::= {dsx1FarEndCurrentEntry 11 }


         dsx1FarEndCurrentDMs OBJECT-TYPE
             SYNTAX Gauge
             ACCESS read-only
             STATUS mandatory
             DESCRIPTION
                "The number of Degraded Minutes  (DMs)  encoun-
                tered  by  a  DS1  interface  in the current 15
                minute interval."
            ::= { dsx1FarEndCurrentEntry 12 }


     -- The DS1 Far End Interval Table

     -- The DS1 Far End Interval Table contains various statistics
     -- collected by each DS1 interface over the previous 24 hours of
     -- operation.  The past 24 hours are broken into 96
     -- completed 15 minute intervals.

         dsx1FarEndIntervalTable OBJECT-TYPE
             SYNTAX  SEQUENCE OF Dsx1FarEndIntervalEntry
             ACCESS  not-accessible
             STATUS  mandatory
             DESCRIPTION
                "The DS1 Far End Interval table."
            ::= { ds1 11 }


         dsx1FarEndIntervalEntry OBJECT-TYPE
             SYNTAX  Dsx1FarEndIntervalEntry
             ACCESS  not-accessible
             STATUS  mandatory
             DESCRIPTION
                "An entry in the DS1 Far End Interval table."
            INDEX   { dsx1FarEndIntervalIndex,
                      dsx1FarEndIntervalNumber }
            --INSTANCE-REGISTRATION
            ::= { dsx1FarEndIntervalTable 1 }

     Dsx1FarEndIntervalEntry ::=
         SEQUENCE {
             dsx1FarEndIntervalIndex
                 INTEGER,
             dsx1FarEndIntervalNumber
                 INTEGER,
             dsx1FarEndIntervalESs
                 Gauge,
             dsx1FarEndIntervalSESs
                 Gauge,
             dsx1FarEndIntervalSEFSs
                 Gauge,
             dsx1FarEndIntervalUASs
                 Gauge,
             dsx1FarEndIntervalCSSs
                 Gauge,
             dsx1FarEndIntervalLESs
                 Gauge,
             dsx1FarEndIntervalPCVs
                 Gauge,
             dsx1FarEndIntervalBESs
                 Gauge,
             dsx1FarEndIntervalDMs
                 Gauge
         }

         dsx1FarEndIntervalIndex OBJECT-TYPE
             SYNTAX  INTEGER (1..'7fffffff'h)
             ACCESS  read-only
             STATUS  mandatory
             DESCRIPTION
                "The index value which uniquely identifies  the
                DS1  interface  to which this entry is applica-
                ble.  The interface identified by a  particular
                value  of  this  index is the same interface as
                identified by the same value as a dsx1LineIndex
                object instance."
            ::= { dsx1FarEndIntervalEntry 1 }


         dsx1FarEndIntervalNumber OBJECT-TYPE
             SYNTAX  INTEGER (1..96)
             ACCESS  read-only
             STATUS  mandatory
             DESCRIPTION
                "A number between 1 and 96, where 1 is the most
                recently completed 15 minute interval and 96 is
                the least recently completed 15 minutes  inter-
                val   (assuming   that  all  96  intervals  are
                valid)."
            ::= { dsx1FarEndIntervalEntry 2 }


         dsx1FarEndIntervalESs OBJECT-TYPE
             SYNTAX  Gauge
             ACCESS  read-only
             STATUS  mandatory
             DESCRIPTION
                "The number of Far End Errored Seconds  encoun-
                tered by a DS1 interface in one of the previous
                96, individual 15 minute, intervals."
            ::= { dsx1FarEndIntervalEntry 3 }


         dsx1FarEndIntervalSESs OBJECT-TYPE
             SYNTAX  Gauge
             ACCESS  read-only
             STATUS  mandatory
             DESCRIPTION
                "The number of Far End Severely Errored Seconds
                encountered  by  a  DS1 interface in one of the
                previous 96, individual 15 minute, intervals."
            ::= { dsx1FarEndIntervalEntry 4 }


         dsx1FarEndIntervalSEFSs OBJECT-TYPE
             SYNTAX  Gauge
             ACCESS  read-only
             STATUS  mandatory
             DESCRIPTION
                "The number of Far End Severely Errored Framing
                Seconds  encountered  by a DS1 interface in one
                of the previous 96, individual 15  minute,  in-
                tervals."
            ::= { dsx1FarEndIntervalEntry 5 }


         dsx1FarEndIntervalUASs OBJECT-TYPE
             SYNTAX  Gauge
             ACCESS  read-only
             STATUS  mandatory
             DESCRIPTION
                "The number of Unavailable Seconds  encountered
                by  a  DS1 interface in one of the previous 96,
                individual 15 minute, intervals."
            ::= { dsx1FarEndIntervalEntry 6 }


         dsx1FarEndIntervalCSSs OBJECT-TYPE
             SYNTAX  Gauge
             ACCESS  read-only
             STATUS  mandatory
             DESCRIPTION
                "The number of Far End Controlled Slip  Seconds
                encountered  by  a  DS1 interface in one of the
                previous 96, individual 15 minute, intervals."
            ::= { dsx1FarEndIntervalEntry 7 }


         dsx1FarEndIntervalLESs OBJECT-TYPE
             SYNTAX  Gauge
             ACCESS  read-only
             STATUS  mandatory
             DESCRIPTION
                "The number of Far End Line Errored Seconds en-
                countered by a DS1 interface in one of the pre-
                vious 96, individual 15 minute, intervals."
            ::= { dsx1FarEndIntervalEntry 8 }


         dsx1FarEndIntervalPCVs OBJECT-TYPE
             SYNTAX  Gauge
             ACCESS  read-only
             STATUS  mandatory
             DESCRIPTION
                "The number of Far End Path  Coding  Violations
                reported  via the far end block error count en-
                countered by a DS1 interface in one of the pre-
                vious 96, individual 15 minute, intervals."
            ::= { dsx1FarEndIntervalEntry 9 }


         dsx1FarEndIntervalBESs OBJECT-TYPE
             SYNTAX Gauge
             ACCESS read-only
             STATUS mandatory
             DESCRIPTION
                "The number of Bursty  Errored  Seconds  (BESs)
                encountered  by  a  DS1 interface in one of the
                previous 96, individual 15 minute, intervals."
            ::= {dsx1FarEndIntervalEntry 10 }


         dsx1FarEndIntervalDMs OBJECT-TYPE
             SYNTAX Gauge
             ACCESS read-only
             STATUS mandatory
             DESCRIPTION
                "The number of Degraded Minutes  (DMs)  encoun-
                tered by a DS1 interface in one of the previous
                96, individual 15 minute, intervals."
            ::= { dsx1FarEndIntervalEntry 11 }


     -- The DS1 Far End Total Table

     -- The DS1 Far End Total Table contains the cumulative sum of the
     -- various statistics for the 24 hour period preceding the
     -- current interval.


         dsx1FarEndTotalTable OBJECT-TYPE
             SYNTAX  SEQUENCE OF Dsx1FarEndTotalEntry
             ACCESS  not-accessible
             STATUS  mandatory
             DESCRIPTION
                "The DS1 Far End Total table."
            ::= { ds1 12 }


         dsx1FarEndTotalEntry OBJECT-TYPE
             SYNTAX  Dsx1FarEndTotalEntry
             ACCESS  not-accessible
             STATUS  mandatory
             DESCRIPTION
                "An entry in the DS1 Far End Total table."
            INDEX   { dsx1FarEndTotalIndex }
            --INSTANCE-REGISTRATION
            ::= { dsx1FarEndTotalTable 1 }

     Dsx1FarEndTotalEntry ::=
         SEQUENCE {
             dsx1FarEndTotalIndex
                 INTEGER,
             dsx1FarEndTotalESs
                 Gauge,
             dsx1FarEndTotalSESs
                 Gauge,
             dsx1FarEndTotalSEFSs
                 Gauge,
             dsx1FarEndTotalUASs
                 Gauge,
             dsx1FarEndTotalCSSs
                 Gauge,
             dsx1FarEndTotalLESs
                 Gauge,
             dsx1FarEndTotalPCVs
                 Gauge,
             dsx1FarEndTotalBESs
                 Gauge,
             dsx1FarEndTotalDMs
                 Gauge
         }

         dsx1FarEndTotalIndex OBJECT-TYPE
             SYNTAX  INTEGER (1..'7fffffff'h)
             ACCESS  read-only
             STATUS  mandatory
             DESCRIPTION
                "The index value which uniquely identifies  the
                DS1  interface  to which this entry is applica-
                ble.  The interface identified by a  particular
                value  of  this  index is the same interface as
                identified by the same value  an  dsx1LineIndex
                object instance."
            ::= { dsx1FarEndTotalEntry 1 }


         dsx1FarEndTotalESs OBJECT-TYPE
             SYNTAX  Gauge
             ACCESS  read-only
             STATUS  mandatory
             DESCRIPTION
                "The number of Far End Errored Seconds  encoun-
                tered  by  a  DS1  interface in the previous 24
                hour interval."
            ::= { dsx1FarEndTotalEntry 2 }


         dsx1FarEndTotalSESs OBJECT-TYPE
             SYNTAX  Gauge
             ACCESS  read-only
             STATUS  mandatory
             DESCRIPTION
                "The number of Far End Severely Errored Seconds
                encountered  by a DS1 interface in the previous
                24 hour interval."
            ::= { dsx1FarEndTotalEntry 3 }


         dsx1FarEndTotalSEFSs OBJECT-TYPE
             SYNTAX  Gauge
             ACCESS  read-only
             STATUS  mandatory
             DESCRIPTION
                "The number of Far End Severely Errored Framing
                Seconds  encountered  by a DS1 interface in the
                previous 24 hour interval."
            ::= { dsx1FarEndTotalEntry 4 }


         dsx1FarEndTotalUASs OBJECT-TYPE
             SYNTAX  Gauge
             ACCESS  read-only
             STATUS  mandatory
             DESCRIPTION
                "The number of Unavailable Seconds  encountered
                by  a DS1 interface in the previous 24 hour in-
                terval."
            ::= { dsx1FarEndTotalEntry 5 }


         dsx1FarEndTotalCSSs OBJECT-TYPE
             SYNTAX  Gauge
             ACCESS  read-only
             STATUS  mandatory
             DESCRIPTION
                "The number of Far End Controlled Slip  Seconds
                encountered  by a DS1 interface in the previous
                24 hour interval."
            ::= { dsx1FarEndTotalEntry 6 }


         dsx1FarEndTotalLESs OBJECT-TYPE
             SYNTAX  Gauge
             ACCESS  read-only
             STATUS  mandatory
             DESCRIPTION
                "The number of Far End Line Errored Seconds en-
                countered by a DS1 interface in the previous 24
                hour interval."
            ::= { dsx1FarEndTotalEntry 7 }


         dsx1FarEndTotalPCVs OBJECT-TYPE
             SYNTAX  Gauge
             ACCESS  read-only
             STATUS  mandatory
             DESCRIPTION
                "The number of Far End Path  Coding  Violations
                reported  via the far end block error count en-
                countered by a DS1 interface in the previous 24
                hour interval."
            ::= { dsx1FarEndTotalEntry 8 }


         dsx1FarEndTotalBESs OBJECT-TYPE
             SYNTAX Gauge
             ACCESS read-only
             STATUS mandatory
             DESCRIPTION
                "The number of Bursty  Errored  Seconds  (BESs)
                encountered  by a DS1 interface in the previous
                24 hour interval."
            ::= { dsx1FarEndTotalEntry 9 }


         dsx1FarEndTotalDMs OBJECT-TYPE
             SYNTAX Gauge
             ACCESS read-only
             STATUS mandatory
             DESCRIPTION
                "The number of Degraded Minutes  (DMs)  encoun-
                tered  by  a  DS1  interface in the previous 24
                hour interval."
            ::= { dsx1FarEndTotalEntry 10 }


     -- the DS1 Fractional Group

     -- Implementation of this group is mandatory for those
     -- systems dividing a DS1 into channels containing different
     -- data streams that are of local interest.  Systems which
     -- are indifferent to data content, such as CSUs, need not
     -- implement it.

     -- The DS1 fractional table identifies which DS1 channels
     -- associated with a CSU are being used to support a
     -- logical interface, i.e., an entry in the interfaces table
     -- from the Internet-standard MIB.

     -- For example, consider an application managing a North
     -- American ISDN Primary Rate link whose division is a 384 kbit/s
     -- H1 "B" Channel for Video, a second H1 for data to a primary
     -- routing peer, and 12 64 kbit/s H0 "B" Channels. Consider that
     -- some subset of the H0 channels are used for voice and the
     -- remainder are available for dynamic data calls.

     -- we count a total of 14 interfaces multiplexed onto the DS1
     -- interface. Six DS1 channels (for the sake of the example,
     -- channels 1..6) are used for Video, six more (7..11 and 13)
     -- are used for data, and the remaining 12 are are in channels
     -- 12 and 14..24.

     -- Let us further imagine that ifIndex 2 is of type DS1 and
     -- refers to the DS1 interface, and that the interfaces layered
     -- onto it are numbered 3..16.

     -- We might describe the allocation of channels, in the
     -- dsx1FracTable, as follows:

     -- dsx1FracIfIndex.2. 1 = 3    dsx1FracIfIndex.2.13 = 4
     -- dsx1FracIfIndex.2. 2 = 3    dsx1FracIfIndex.2.14 = 6
     -- dsx1FracIfIndex.2. 3 = 3    dsx1FracIfIndex.2.15 = 7
     -- dsx1FracIfIndex.2. 4 = 3    dsx1FracIfIndex.2.16 = 8
     -- dsx1FracIfIndex.2. 5 = 3    dsx1FracIfIndex.2.17 = 9
     -- dsx1FracIfIndex.2. 6 = 3    dsx1FracIfIndex.2.18 = 10
     -- dsx1FracIfIndex.2. 7 = 4    dsx1FracIfIndex.2.19 = 11
     -- dsx1FracIfIndex.2. 8 = 4    dsx1FracIfIndex.2.20 = 12
     -- dsx1FracIfIndex.2. 9 = 4    dsx1FracIfIndex.2.21 = 13
     -- dsx1FracIfIndex.2.10 = 4    dsx1FracIfIndex.2.22 = 14
     -- dsx1FracIfIndex.2.11 = 4    dsx1FracIfIndex.2.23 = 15
     -- dsx1FracIfIndex.2.12 = 5    dsx1FracIfIndex.2.24 = 16


     --      For North American (DS1) interfaces, there are 24 legal
     --      channels, numbered 1 through 24.

     --      For G.704 interfaces, there are 31 legal channels,
     --      numbered 1 through 31.  The channels (1..31) correspond
     --      directly to the equivalently numbered time-slots.

         dsx1FracTable OBJECT-TYPE
             SYNTAX  SEQUENCE OF Dsx1FracEntry
             ACCESS  not-accessible
             STATUS  mandatory
             DESCRIPTION
                "The DS1 Fractional table."
            ::= { ds1 13 }


         dsx1FracEntry OBJECT-TYPE
             SYNTAX  Dsx1FracEntry
             ACCESS  not-accessible
             STATUS  mandatory
             DESCRIPTION
                "An entry in the DS1 Fractional table."
            INDEX   { dsx1FracIndex, dsx1FracNumber }
            --INSTANCE-REGISTRATION
            ::= { dsx1FracTable 1 }

     Dsx1FracEntry ::=
         SEQUENCE {
             dsx1FracIndex
                 INTEGER,
             dsx1FracNumber
                 INTEGER,
             dsx1FracIfIndex
                 INTEGER
         }


         dsx1FracIndex OBJECT-TYPE
             SYNTAX  INTEGER (1..'7fffffff'h)
             ACCESS  read-only
             STATUS  mandatory
             DESCRIPTION
                "The index value which uniquely identifies  the
                DS1  interface  to which this entry is applica-
                ble.  The interface identified by a  particular
                value  of  this  index is the same interface as
                identified by the same value  an  dsx1LineIndex
                object instance."
            ::= { dsx1FracEntry 1 }


         dsx1FracNumber OBJECT-TYPE
             SYNTAX  INTEGER (1..31)
             ACCESS  read-only
             STATUS  mandatory
             DESCRIPTION
                "The channel number for this entry."
            ::= { dsx1FracEntry 2 }


         dsx1FracIfIndex OBJECT-TYPE
             SYNTAX  INTEGER (1..'7fffffff'h)
             ACCESS  read-write
             STATUS  mandatory
             DESCRIPTION
                "An index value that uniquely identifies an in-
                terface.  The interface identified by a partic-
                ular value of this index is the same  interface
                as  identified by the same value an ifIndex ob-
                ject instance. If no interface is currently us-
                ing  a channel, the value should be zero.  If a
                single interface occupies more  than  one  time
                slot,  that ifIndex value will be found in mul-
                tiple time slots."
		--CONFIGURABLE
            ::= { dsx1FracEntry 3 }

     END
   DNS-SERVER-MIB DEFINITIONS ::= BEGIN

   IMPORTS
       mib-2
           FROM RFC1213-MIB
       MODULE-IDENTITY, OBJECT-TYPE, OBJECT-IDENTITY,
       IpAddress, Counter32, Gauge32
           FROM SNMPv2-SMI
       TEXTUAL-CONVENTION, RowStatus, DisplayString, TruthValue
           FROM SNMPv2-TC
       MODULE-COMPLIANCE, OBJECT-GROUP
           FROM SNMPv2-CONF;

   dns OBJECT-IDENTITY
       STATUS  current
       DESCRIPTION
               "The OID assigned to DNS MIB work by the IANA."
       ::= { mib-2 32 }

   dnsServMIB MODULE-IDENTITY
       LAST-UPDATED "9401282251Z"
       ORGANIZATION "IETF DNS Working Group"
       CONTACT-INFO
               "       Rob Austein
               Postal: Epilogue Technology Corporation
                       268 Main Street, Suite 283
                       North Reading, MA 10864
                       US
                  Tel: +1 617 245 0804
                  Fax: +1 617 245 8122
               E-Mail: sra@epilogue.com

                       Jon Saperia
               Postal: Digital Equipment Corporation
                       110 Spit Brook Road
                       ZKO1-3/H18
                       Nashua, NH 03062-2698
                       US
                  Tel: +1 603 881 0480
                  Fax: +1 603 881 0120
                Email: saperia@zko.dec.com"
       DESCRIPTION
               "The MIB module for entities implementing the server side
               of the Domain Name System (DNS) protocol."
       ::= { dns 1 }

   dnsServMIBObjects       OBJECT IDENTIFIER ::= { dnsServMIB 1 }

   -- (Old-style) groups in the DNS server MIB.

   dnsServConfig           OBJECT IDENTIFIER ::= { dnsServMIBObjects 1 }
   dnsServCounter          OBJECT IDENTIFIER ::= { dnsServMIBObjects 2 }
   dnsServOptCounter       OBJECT IDENTIFIER ::= { dnsServMIBObjects 3 }
   dnsServZone             OBJECT IDENTIFIER ::= { dnsServMIBObjects 4 }


   -- Textual conventions

   DnsName ::= TEXTUAL-CONVENTION
       -- A DISPLAY-HINT would be nice, but difficult to express.
       STATUS  current
       DESCRIPTION
               "A DNS name is a sequence of labels.  When DNS names are
               displayed, the boundaries between labels are typically
               indicated by dots (e.g. `Acme' and `COM' are labels in
               the name `Acme.COM').  In the DNS protocol, however, no
               such separators are needed because each label is encoded
               as a length octet followed by the indicated number of
               octets of label.  For example, `Acme.COM' is encoded as
               the octet sequence { 4, 'A', 'c', 'm', 'e', 3, 'C', 'O',
               'M', 0 } (the final 0 is the length of the name of the
               root domain, which appears implicitly at the end of any
               DNS name).  This MIB uses the same encoding as the DNS
               protocol.

               A DnsName must always be a fully qualified name.  It is
               an error to encode a relative domain name as a DnsName
               without first making it a fully qualified name."
       REFERENCE
               "RFC-1034 section 3.1."
       SYNTAX  OCTET STRING (SIZE (0..255))

   DnsNameAsIndex ::= TEXTUAL-CONVENTION
       STATUS  current
       DESCRIPTION
               "This textual convention is like a DnsName, but is used
               as an index componant in tables.  Alphabetic characters
               in names of this type are restricted to uppercase: the
               characters 'a' through 'z' are mapped to the characters
               'A' through 'Z'.  This restriction is intended to make
               the lexical ordering imposed by SNMP useful when applied
               to DNS names.

               Note that it is theoretically possible for a valid DNS
               name to exceed the allowed length of an SNMP object
               identifer, and thus be impossible to represent in tables
               in this MIB that are indexed by DNS name.  Sampling of
               DNS names in current use on the Internet suggests that
               this limit does not pose a serious problem in practice."
       REFERENCE
               "RFC-1034 section 3.1, RFC-1448 section 4.1."
       SYNTAX  DnsName

   DnsClass ::= TEXTUAL-CONVENTION
       DISPLAY-HINT "2d"
       STATUS  current
       DESCRIPTION
               "This data type is used to represent the class values
               which appear in Resource Records in the DNS.  A 16-bit
               unsigned integer is used to allow room for new classes
               of records to be defined.  Existing standard classes are
               listed in the DNS specifications."
       REFERENCE
               "RFC-1035 section 3.2.4."
       SYNTAX  INTEGER (0..65535)

   DnsType ::= TEXTUAL-CONVENTION
       DISPLAY-HINT "2d"
       STATUS  current
       DESCRIPTION
               "This data type is used to represent the type values
               which appear in Resource Records in the DNS.  A 16-bit
               unsigned integer is used to allow room for new record
               types to be defined.  Existing standard types are listed
               in the DNS specifications."
       REFERENCE
               "RFC-1035 section 3.2.2."
       SYNTAX  INTEGER (0..65535)

   DnsQClass ::= TEXTUAL-CONVENTION
       DISPLAY-HINT "2d"
       STATUS  current
       DESCRIPTION
               "This data type is used to represent the QClass values
               which appear in Resource Records in the DNS.  A 16-bit
               unsigned integer is used to allow room for new QClass
               records to be defined.  Existing standard QClasses are
               listed in the DNS specification."
       REFERENCE
               "RFC-1035 section 3.2.5."
       SYNTAX  INTEGER (0..65535)

   DnsQType ::= TEXTUAL-CONVENTION
       DISPLAY-HINT "2d"
       STATUS  current
       DESCRIPTION
               "This data type is used to represent the QType values
               which appear in Resource Records in the DNS.  A 16-bit
               unsigned integer is used to allow room for new QType
               records to be defined.  Existing standard QTypes are
               listed in the DNS specification."
       REFERENCE
               "RFC-1035 section 3.2.3."
       SYNTAX  INTEGER (0..65535)

   DnsTime ::= TEXTUAL-CONVENTION
       STATUS  current
       DESCRIPTION
               "DnsTime values are 32-bit unsigned integers which
               measure time in seconds."
       REFERENCE
               "RFC-1035."
       SYNTAX  Gauge32


   DnsOpCode ::= TEXTUAL-CONVENTION
       STATUS  current
       DESCRIPTION
               "This textual convention is used to represent the DNS
               OPCODE values used in the header section of DNS
               messages.  Existing standard OPCODE values are listed in
               the DNS specifications."
       REFERENCE
               "RFC-1035 section 4.1.1."
       SYNTAX  INTEGER (0..15)

   DnsRespCode ::= TEXTUAL-CONVENTION
       STATUS  current
       DESCRIPTION
               "This data type is used to represent the DNS RCODE value
               in DNS response messages.  Existing standard RCODE
               values are listed in the DNS specifications."
       REFERENCE
               "RFC-1035 section 4.1.1."
       SYNTAX  INTEGER (0..15)

   -- Server Configuration Group

   dnsServConfigImplementIdent OBJECT-TYPE
       SYNTAX      DisplayString
       MAX-ACCESS  read-only
       STATUS      current
       DESCRIPTION
               "The implementation identification string for the DNS
               server software in use on the system, for example;
               `FNS-2.1'"
       ::= { dnsServConfig 1 }

   dnsServConfigRecurs  OBJECT-TYPE
       SYNTAX      INTEGER { available(1),
                             restricted(2),
                             unavailable(3) }
       MAX-ACCESS  read-write
       STATUS      current
       DESCRIPTION
               "This represents the recursion services offered by this
               name server.  The values that can be read or written
               are:

               available(1) - performs recursion on requests from
               clients.

               restricted(2) - recursion is performed on requests only
               from certain clients, for example; clients on an access
               control list.

               unavailable(3) - recursion is not available."
        ::= { dnsServConfig 2 }

   dnsServConfigUpTime OBJECT-TYPE
       SYNTAX      DnsTime
       MAX-ACCESS  read-only
       STATUS      current
       DESCRIPTION
               "If the server has a persistent state (e.g., a process),
               this value will be the time elapsed since it started.
               For software without persistant state, this value will
               be zero."
       ::= { dnsServConfig 3 }

   dnsServConfigResetTime OBJECT-TYPE
       SYNTAX      DnsTime
       MAX-ACCESS  read-only
       STATUS      current
       DESCRIPTION
               "If the server has a persistent state (e.g., a process)
               and supports a `reset' operation (e.g., can be told to
               re-read configuration files), this value will be the
               time elapsed since the last time the name server was
               `reset.'  For software that does not have persistence or
               does not support a `reset' operation, this value will be
               zero."
       ::= { dnsServConfig 4 }

   dnsServConfigReset OBJECT-TYPE
       SYNTAX      INTEGER { other(1),
                             reset(2),
                             initializing(3),
                             running(4) }
       MAX-ACCESS  read-write
       STATUS      current
       DESCRIPTION
               "Status/action object to reinitialize any persistant name
               server state.  When set to reset(2), any persistant
               name server state (such as a process) is reinitialized as
               if the name server had just been started.  This value
               will never be returned by a read operation.  When read,
               one of the following values will be returned:
                   other(1) - server in some unknown state;
                   initializing(3) - server (re)initializing;
                   running(4) - server currently running."
       ::= { dnsServConfig 5 }


   -- Server Counter Group

   dnsServCounterAuthAns OBJECT-TYPE
       SYNTAX      Counter32
       MAX-ACCESS  read-only
       STATUS      current
       DESCRIPTION
               "Number of queries which were authoritatively answered."
       ::= { dnsServCounter 2 }

   dnsServCounterAuthNoNames OBJECT-TYPE
       SYNTAX      Counter32
       MAX-ACCESS  read-only
       STATUS      current
       DESCRIPTION
               "Number of queries for which `authoritative no such name'
               responses were made."
       ::= { dnsServCounter 3 }

   dnsServCounterAuthNoDataResps OBJECT-TYPE
       SYNTAX      Counter32
       MAX-ACCESS  read-only
       STATUS      current
       DESCRIPTION
               "Number of queries for which `authoritative no such data'
               (empty answer) responses were made."
       ::= { dnsServCounter 4 }

   dnsServCounterNonAuthDatas OBJECT-TYPE
       SYNTAX      Counter32
       MAX-ACCESS  read-only
       STATUS      current
       DESCRIPTION
               "Number of queries which were non-authoritatively
               answered (cached data)."
       ::= { dnsServCounter 5 }

   dnsServCounterNonAuthNoDatas OBJECT-TYPE
       SYNTAX      Counter32
       MAX-ACCESS  read-only
       STATUS      current
       DESCRIPTION
               "Number of queries which were non-authoritatively
               answered with no data (empty answer)."
       ::= { dnsServCounter 6 }

   dnsServCounterReferrals OBJECT-TYPE
       SYNTAX      Counter32
       MAX-ACCESS  read-only
       STATUS      current
       DESCRIPTION
               "Number of requests that were referred to other servers."
       ::= { dnsServCounter 7 }

   dnsServCounterErrors OBJECT-TYPE
       SYNTAX      Counter32
       MAX-ACCESS  read-only
       STATUS      current
       DESCRIPTION
               "Number of requests the server has processed that were
               answered with errors (RCODE values other than 0 and 3)."
       REFERENCE
               "RFC-1035 section 4.1.1."
       ::= { dnsServCounter 8 }

   dnsServCounterRelNames OBJECT-TYPE
       SYNTAX      Counter32
       MAX-ACCESS  read-only
       STATUS      current
       DESCRIPTION
               "Number of requests received by the server for names that
               are only 1 label long (text form - no internal dots)."
       ::= { dnsServCounter 9 }

   dnsServCounterReqRefusals OBJECT-TYPE
       SYNTAX      Counter32
       MAX-ACCESS  read-only
       STATUS      current
       DESCRIPTION
               "Number of DNS requests refused by the server."
       ::= { dnsServCounter 10 }

   dnsServCounterReqUnparses OBJECT-TYPE
       SYNTAX      Counter32
       MAX-ACCESS  read-only
       STATUS      current
       DESCRIPTION
               "Number of requests received which were unparseable."
       ::= { dnsServCounter 11 }

   dnsServCounterOtherErrors OBJECT-TYPE
       SYNTAX      Counter32
       MAX-ACCESS  read-only
       STATUS      current
       DESCRIPTION
               "Number of requests which were aborted for other (local)
               server errors."
       ::= { dnsServCounter 12 }

   -- DNS Server Counter Table

   dnsServCounterTable OBJECT-TYPE
       SYNTAX      SEQUENCE OF DnsServCounterEntry
       MAX-ACCESS  not-accessible
       STATUS      current
       DESCRIPTION
               "Counter information broken down by DNS class and type."
       ::= { dnsServCounter 13 }

   dnsServCounterEntry OBJECT-TYPE
       SYNTAX      DnsServCounterEntry
       MAX-ACCESS  not-accessible
       STATUS      current
       DESCRIPTION
               "This table contains count information for each DNS class
               and type value known to the server.  The index allows
               management software to to create indices to the table to
               get the specific information desired, e.g., number of
               queries over UDP for records with type value `A' which
               came to this server.  In order to prevent an
               uncontrolled expansion of rows in the table; if
               dnsServCounterRequests is 0 and dnsServCounterResponses
               is 0, then the row does not exist and `no such' is
               returned when the agent is queried for such instances."
       INDEX     { dnsServCounterOpCode,
                   dnsServCounterQClass,
                   dnsServCounterQType,
                   dnsServCounterTransport }
       ::= { dnsServCounterTable 1 }

   DnsServCounterEntry ::=
       SEQUENCE {
           dnsServCounterOpCode
               DnsOpCode,
           dnsServCounterQClass
               DnsClass,
           dnsServCounterQType
               DnsType,
           dnsServCounterTransport
               INTEGER,
           dnsServCounterRequests
               Counter32,
           dnsServCounterResponses
               Counter32
           }

   dnsServCounterOpCode OBJECT-TYPE
       SYNTAX      DnsOpCode
       MAX-ACCESS  not-accessible
       STATUS      current
       DESCRIPTION
               "The DNS OPCODE being counted in this row of the table."
       ::= { dnsServCounterEntry 1 }

   dnsServCounterQClass OBJECT-TYPE
       SYNTAX      DnsClass
       MAX-ACCESS  not-accessible
       STATUS      current
       DESCRIPTION
               "The class of record being counted in this row of the
               table."
       ::= { dnsServCounterEntry 2 }

   dnsServCounterQType OBJECT-TYPE
       SYNTAX      DnsType
       MAX-ACCESS  not-accessible
       STATUS      current
       DESCRIPTION
               "The type of record which is being counted in this row in
               the table."
       ::= { dnsServCounterEntry 3 }

   dnsServCounterTransport OBJECT-TYPE
       SYNTAX      INTEGER { udp(1), tcp(2), other(3) }
       MAX-ACCESS  not-accessible
       STATUS      current
       DESCRIPTION
               "A value of udp(1) indicates that the queries reported on
               this row were sent using UDP.

               A value of tcp(2) indicates that the queries reported on
               this row were sent using TCP.

               A value of other(3) indicates that the queries reported
               on this row were sent using a transport that was neither
               TCP nor UDP."
       ::= { dnsServCounterEntry 4 }

   dnsServCounterRequests OBJECT-TYPE
       SYNTAX      Counter32
       MAX-ACCESS  read-only
       STATUS      current
       DESCRIPTION
               "Number of requests (queries) that have been recorded in
               this row of the table."
       ::= { dnsServCounterEntry 5 }

   dnsServCounterResponses OBJECT-TYPE
       SYNTAX      Counter32
       MAX-ACCESS  read-only
       STATUS      current
       DESCRIPTION
               "Number of responses made by the server since
               initialization for the kind of query identified on this
               row of the table."
       ::= { dnsServCounterEntry 6 }

   -- Server Optional Counter Group

   -- The Server Optional Counter Group is intended for those systems
   -- which make distinctions between the different sources of the DNS
   -- queries as defined below.
   --
   -- Objects in this group are implemented on servers which distinguish
   -- between queries which originate from the same host as the server,
   -- queries from one of an arbitrary group of hosts that are on an
   -- access list defined by the server, and queries from hosts that do
   -- not fit either of these descriptions.
   --
   -- The objects found in the Server Counter group are totals.  Thus if
   -- one wanted to identify, for example, the number of queries from
   -- `remote' hosts which have been given authoritative answers, one
   -- would subtract the current values of ServOptCounterFriendsAuthAns
   -- and ServOptCounterSelfAuthAns from servCounterAuthAns.
   --
   -- The purpose of these distinctions is to allow for implementations
   -- to group queries and responses on this basis.  One way in which
   -- servers may make these distinctions is by looking at the source IP
   -- address of the DNS query.  If the source of the query is `your
   -- own' then the query should be counted as `yourself' (local host).
   -- If the source of the query matches an `access list,' the query
   -- came from a friend.  What constitutes an `access list' is
   -- implementation dependent and could be as simple as a rule that all
   -- hosts on the same IP network as the DNS server are classed
   -- `friends.'
   --
   -- In order to avoid double counting, the following rules apply:
   --
   -- 1. No host is in more than one of the three groups defined above.
   --
   -- 2. All queries from the local host are always counted in the
   --    `yourself' group regardless of what the access list, if any,
   --    says.
   --
   -- 3. The access list should not define `your friends' in such a way
   --    that it includes all hosts.   That is, not everybody is your
   --    `friend.'

   dnsServOptCounterSelfAuthAns OBJECT-TYPE
       SYNTAX      Counter32
       MAX-ACCESS  read-only
       STATUS      current
       DESCRIPTION
               "Number of requests the server has processed which
               originated from a resolver on the same host for which
               there has been an authoritative answer."
       ::= { dnsServOptCounter 1 }

   dnsServOptCounterSelfAuthNoNames OBJECT-TYPE
       SYNTAX      Counter32
       MAX-ACCESS  read-only
       STATUS      current
       DESCRIPTION
               "Number of requests the server has processed which
               originated from a resolver on the same host for which
               there has been an authoritative no such name answer
               given."
       ::= { dnsServOptCounter 2 }

   dnsServOptCounterSelfAuthNoDataResps OBJECT-TYPE
       SYNTAX      Counter32
       MAX-ACCESS  read-only
       STATUS      current
       DESCRIPTION
               "Number of requests the server has processed which
               originated from a resolver on the same host for which
               there has been an authoritative no such data answer
               (empty answer) made."
       ::= { dnsServOptCounter 3 }

   dnsServOptCounterSelfNonAuthDatas OBJECT-TYPE
       SYNTAX      Counter32
       MAX-ACCESS  read-only
       STATUS      current
       DESCRIPTION
               "Number of requests the server has processed which
               originated from a resolver on the same host for which a
               non-authoritative answer (cached data) was made."
       ::= { dnsServOptCounter 4 }

   dnsServOptCounterSelfNonAuthNoDatas OBJECT-TYPE
       SYNTAX      Counter32
       MAX-ACCESS  read-only
       STATUS      current
       DESCRIPTION
               "Number of requests the server has processed which
               originated from a resolver on the same host for which a
               `non-authoritative, no such data' response was made
               (empty answer)."
       ::= { dnsServOptCounter 5 }

   dnsServOptCounterSelfReferrals OBJECT-TYPE
       SYNTAX      Counter32
       MAX-ACCESS  read-only
       STATUS      current
       DESCRIPTION
               "Number of queries the server has processed which
               originated from a resolver on the same host and were
               referred to other servers."
       ::= { dnsServOptCounter 6 }

   dnsServOptCounterSelfErrors OBJECT-TYPE
       SYNTAX      Counter32
       MAX-ACCESS  read-only
       STATUS      current
       DESCRIPTION
               "Number of requests the server has processed which
               originated from a resolver on the same host which have
               been answered with errors (RCODEs other than 0 and 3)."
       REFERENCE
               "RFC-1035 section 4.1.1."
       ::= { dnsServOptCounter 7 }

   dnsServOptCounterSelfRelNames OBJECT-TYPE
       SYNTAX      Counter32
       MAX-ACCESS  read-only
       STATUS      current
       DESCRIPTION
               "Number of requests received for names that are only 1
               label long (text form - no internal dots) the server has
               processed which originated from a resolver on the same
               host."
       ::= { dnsServOptCounter 8 }

   dnsServOptCounterSelfReqRefusals OBJECT-TYPE
       SYNTAX      Counter32
       MAX-ACCESS  read-only
       STATUS      current
       DESCRIPTION
               "Number of DNS requests refused by the server which
               originated from a resolver on the same host."
       ::= { dnsServOptCounter 9 }

   dnsServOptCounterSelfReqUnparses OBJECT-TYPE
       SYNTAX      Counter32
       MAX-ACCESS  read-only
       STATUS      current
       DESCRIPTION
               "Number of requests received which were unparseable and
               which originated from a resolver on the same host."
       ::= { dnsServOptCounter 10 }

   dnsServOptCounterSelfOtherErrors OBJECT-TYPE
       SYNTAX      Counter32
       MAX-ACCESS  read-only
       STATUS      current
       DESCRIPTION
               "Number of requests which were aborted for other (local)
               server errors and which originated on the same host."
       ::= { dnsServOptCounter 11 }

   dnsServOptCounterFriendsAuthAns OBJECT-TYPE
       SYNTAX      Counter32
       MAX-ACCESS  read-only
       STATUS      current
       DESCRIPTION
               "Number of queries originating from friends which were
               authoritatively answered.  The definition of friends is
               a locally defined matter."
       ::= { dnsServOptCounter 12 }

   dnsServOptCounterFriendsAuthNoNames OBJECT-TYPE
       SYNTAX      Counter32
       MAX-ACCESS  read-only
       STATUS      current
       DESCRIPTION
               "Number of queries originating from friends, for which
               authoritative `no such name' responses were made.  The
               definition of friends is a locally defined matter."
       ::= { dnsServOptCounter 13 }

   dnsServOptCounterFriendsAuthNoDataResps OBJECT-TYPE
       SYNTAX      Counter32
       MAX-ACCESS  read-only
       STATUS      current
       DESCRIPTION
               "Number of queries originating from friends for which
               authoritative no such data (empty answer) responses were
               made.  The definition of friends is a locally defined
               matter."
       ::= { dnsServOptCounter 14 }

   dnsServOptCounterFriendsNonAuthDatas OBJECT-TYPE
       SYNTAX      Counter32
       MAX-ACCESS  read-only
       STATUS      current
       DESCRIPTION
               "Number of queries originating from friends which were
               non-authoritatively answered (cached data). The
               definition of friends is a locally defined matter."
       ::= { dnsServOptCounter 15 }

   dnsServOptCounterFriendsNonAuthNoDatas OBJECT-TYPE
       SYNTAX      Counter32
       MAX-ACCESS  read-only
       STATUS      current
       DESCRIPTION
               "Number of queries originating from friends which were
               non-authoritatively answered with no such data (empty
               answer)."
       ::= { dnsServOptCounter 16 }

   dnsServOptCounterFriendsReferrals OBJECT-TYPE
       SYNTAX      Counter32
       MAX-ACCESS  read-only
       STATUS      current
       DESCRIPTION
               "Number of requests which originated from friends that
               were referred to other servers.  The definition of
               friends is a locally defined matter."
       ::= { dnsServOptCounter 17 }

   dnsServOptCounterFriendsErrors OBJECT-TYPE
       SYNTAX      Counter32
       MAX-ACCESS  read-only
       STATUS      current
       DESCRIPTION
               "Number of requests the server has processed which
               originated from friends and were answered with errors
               (RCODE values other than 0 and 3).  The definition of
               friends is a locally defined matter."
       REFERENCE
               "RFC-1035 section 4.1.1."
       ::= { dnsServOptCounter 18 }

   dnsServOptCounterFriendsRelNames OBJECT-TYPE
       SYNTAX      Counter32
       MAX-ACCESS  read-only
       STATUS      current
       DESCRIPTION
               "Number of requests received for names from friends that
               are only 1 label long (text form - no internal dots) the
               server has processed."
       ::= { dnsServOptCounter 19 }

   dnsServOptCounterFriendsReqRefusals OBJECT-TYPE
       SYNTAX      Counter32
       MAX-ACCESS  read-only
       STATUS      current
       DESCRIPTION
               "Number of DNS requests refused by the server which were
               received from `friends'."
       ::= { dnsServOptCounter 20 }

   dnsServOptCounterFriendsReqUnparses OBJECT-TYPE
       SYNTAX      Counter32
       MAX-ACCESS  read-only
       STATUS      current
       DESCRIPTION
               "Number of requests received which were unparseable and
               which originated from `friends'."
       ::= { dnsServOptCounter 21 }

   dnsServOptCounterFriendsOtherErrors OBJECT-TYPE
       SYNTAX      Counter32
       MAX-ACCESS  read-only
       STATUS      current
       DESCRIPTION
               "Number of requests which were aborted for other (local)
               server errors and which originated from `friends'."
       ::= { dnsServOptCounter 22 }


   -- Server Zone Group

   -- DNS Management Zone Configuration Table

   -- This table contains zone configuration information.

   dnsServZoneTable OBJECT-TYPE
       SYNTAX      SEQUENCE OF DnsServZoneEntry
       MAX-ACCESS  not-accessible
       STATUS      current
       DESCRIPTION
               "Table of zones for which this name server provides
               information.  Each of the zones may be loaded from stable
               storage via an implementation-specific mechanism or may
               be obtained from another name server via a zone transfer.

               If name server doesn't load any zones, this table is
               empty."
       ::= { dnsServZone 1 }

   dnsServZoneEntry OBJECT-TYPE
       SYNTAX      DnsServZoneEntry
       MAX-ACCESS  not-accessible
       STATUS      current
       DESCRIPTION
               "An entry in the name server zone table.  New rows may be
               added either via SNMP or by the name server itself."
       INDEX     { dnsServZoneName,
                   dnsServZoneClass }
       ::= { dnsServZoneTable 1 }

   DnsServZoneEntry ::=
       SEQUENCE {
           dnsServZoneName
               DnsNameAsIndex,
           dnsServZoneClass
               DnsClass,
           dnsServZoneLastReloadSuccess
               DnsTime,
           dnsServZoneLastReloadAttempt
               DnsTime,
           dnsServZoneLastSourceAttempt
               IpAddress,
           dnsServZoneStatus
               RowStatus,
           dnsServZoneSerial
               Counter32,
           dnsServZoneCurrent
               TruthValue,
           dnsServZoneLastSourceSuccess
               IpAddress
       }

   dnsServZoneName OBJECT-TYPE
       SYNTAX      DnsNameAsIndex
       MAX-ACCESS  not-accessible
       STATUS      current
       DESCRIPTION
               "DNS name of the zone described by this row of the table.
               This is the owner name of the SOA RR that defines the
               top of the zone. This is name is in uppercase:
               characters 'a' through 'z' are mapped to 'A' through 'Z'
               in order to make the lexical ordering useful."
       ::= { dnsServZoneEntry 1 }

   dnsServZoneClass OBJECT-TYPE
       SYNTAX      DnsClass
       MAX-ACCESS  not-accessible
       STATUS      current
       DESCRIPTION
               "DNS class of the RRs in this zone."
       ::= { dnsServZoneEntry 2 }

   dnsServZoneLastReloadSuccess OBJECT-TYPE
       SYNTAX      DnsTime
       MAX-ACCESS  read-only
       STATUS      current
       DESCRIPTION
               "Elapsed time in seconds since last successful reload of
               this zone."
       ::= { dnsServZoneEntry 3 }

   dnsServZoneLastReloadAttempt OBJECT-TYPE
       SYNTAX      DnsTime
       MAX-ACCESS  read-only
       STATUS      current
       DESCRIPTION
               "Elapsed time in seconds since last attempted reload of
               this zone."
       ::= { dnsServZoneEntry 4 }

   dnsServZoneLastSourceAttempt OBJECT-TYPE
       SYNTAX      IpAddress
       MAX-ACCESS  read-only
       STATUS      current
       DESCRIPTION
               "IP address of host from which most recent zone transfer
               of this zone was attempted.  This value should match the
               value of dnsServZoneSourceSuccess if the attempt was
               succcessful.  If zone transfer has not been attempted
               within the memory of this name server, this value should
               be 0.0.0.0."
       ::= { dnsServZoneEntry 5 }

   dnsServZoneStatus OBJECT-TYPE
       SYNTAX      RowStatus
       MAX-ACCESS  read-create
       STATUS      current
       DESCRIPTION
               "The status of the information represented in this row of
               the table."
       ::= { dnsServZoneEntry 6 }

   dnsServZoneSerial OBJECT-TYPE
       SYNTAX      Counter32
       MAX-ACCESS  read-only
       STATUS      current
       DESCRIPTION
               "Zone serial number (from the SOA RR) of the zone
               represented by this row of the table.  If the zone has
               not been successfully loaded within the memory of this
               name server, the value of this variable is zero."
       ::= { dnsServZoneEntry 7 }

   dnsServZoneCurrent OBJECT-TYPE
       SYNTAX      TruthValue
       MAX-ACCESS  read-only
       STATUS      current
       DESCRIPTION
               "Whether the server's copy of the zone represented by
               this row of the table is currently valid.  If the zone
               has never been successfully loaded or has expired since
               it was last succesfully loaded, this variable will have
               the value false(2), otherwise this variable will have
               the value true(1)."
       ::= { dnsServZoneEntry 8 }

   dnsServZoneLastSourceSuccess OBJECT-TYPE
       SYNTAX      IpAddress
       MAX-ACCESS  read-only
       STATUS      current
       DESCRIPTION
               "IP address of host which was the source of the most
               recent successful zone transfer for this zone.  If
               unknown (e.g., zone has never been successfully
               transfered) or irrelevant (e.g., zone was loaded from
               stable storage), this value should be 0.0.0.0."
       ::= { dnsServZoneEntry 9 }

   -- DNS Zone Source Table

   dnsServZoneSrcTable OBJECT-TYPE
       SYNTAX      SEQUENCE OF DnsServZoneSrcEntry
       MAX-ACCESS  not-accessible
       STATUS      current
       DESCRIPTION
               "This table is a list of IP addresses from which the
               server will attempt to load zone information using DNS
               zone transfer operations.  A reload may occur due to SNMP
               operations that create a row in dnsServZoneTable or a
               SET to object dnsServZoneReload.  This table is only
               used when the zone is loaded via zone transfer."
       ::= { dnsServZone 2 }

   dnsServZoneSrcEntry OBJECT-TYPE
       SYNTAX      DnsServZoneSrcEntry
       MAX-ACCESS  not-accessible
       STATUS      current
       DESCRIPTION
               "An entry in the name server zone source table."
       INDEX     { dnsServZoneSrcName,
                   dnsServZoneSrcClass,
                   dnsServZoneSrcAddr }
       ::= { dnsServZoneSrcTable 1 }

   DnsServZoneSrcEntry ::=
       SEQUENCE {
           dnsServZoneSrcName
               DnsNameAsIndex,
           dnsServZoneSrcClass
               DnsClass,
           dnsServZoneSrcAddr
               IpAddress,
           dnsServZoneSrcStatus
               RowStatus
       }

   dnsServZoneSrcName OBJECT-TYPE
       SYNTAX      DnsNameAsIndex
       MAX-ACCESS  not-accessible
       STATUS      current
       DESCRIPTION
               "DNS name of the zone to which this entry applies."
       ::= { dnsServZoneSrcEntry 1 }

   dnsServZoneSrcClass OBJECT-TYPE
       SYNTAX      DnsClass
       MAX-ACCESS  not-accessible
       STATUS      current
       DESCRIPTION
               "DNS class of zone to which this entry applies."
       ::= { dnsServZoneSrcEntry 2 }

   dnsServZoneSrcAddr OBJECT-TYPE
       SYNTAX      IpAddress
       MAX-ACCESS  not-accessible
       STATUS      current
       DESCRIPTION
               "IP address of name server host from which this zone
               might be obtainable."
       ::= { dnsServZoneSrcEntry 3 }

   dnsServZoneSrcStatus OBJECT-TYPE
       SYNTAX      RowStatus
       MAX-ACCESS  read-create
       STATUS      current
       DESCRIPTION
               "The status of the information represented in this row of
               the table."
       ::= { dnsServZoneSrcEntry 4 }


   -- SNMPv2 groups.

   dnsServMIBGroups        OBJECT IDENTIFIER ::= { dnsServMIB 2 }

   dnsServConfigGroup OBJECT-GROUP
       OBJECTS   { dnsServConfigImplementIdent,
                   dnsServConfigRecurs,
                   dnsServConfigUpTime,
                   dnsServConfigResetTime,
                   dnsServConfigReset }
       STATUS      current
       DESCRIPTION
               "A collection of objects providing basic configuration
               control of a DNS name server."
       ::= { dnsServMIBGroups 1 }

   dnsServCounterGroup OBJECT-GROUP
       OBJECTS   { dnsServCounterAuthAns,
                   dnsServCounterAuthNoNames,
                   dnsServCounterAuthNoDataResps,
                   dnsServCounterNonAuthDatas,
                   dnsServCounterNonAuthNoDatas,
                   dnsServCounterReferrals,
                   dnsServCounterErrors,
                   dnsServCounterRelNames,
                   dnsServCounterReqRefusals,
                   dnsServCounterReqUnparses,
                   dnsServCounterOtherErrors,
                   dnsServCounterOpCode,
                   dnsServCounterQClass,
                   dnsServCounterQType,
                   dnsServCounterTransport,
                   dnsServCounterRequests,
                   dnsServCounterResponses }
       STATUS      current
       DESCRIPTION
               "A collection of objects providing basic instrumentation
               of a DNS name server."
       ::= { dnsServMIBGroups 2 }

   dnsServOptCounterGroup OBJECT-GROUP
       OBJECTS   { dnsServOptCounterSelfAuthAns,
                   dnsServOptCounterSelfAuthNoNames,
                   dnsServOptCounterSelfAuthNoDataResps,
                   dnsServOptCounterSelfNonAuthDatas,
                   dnsServOptCounterSelfNonAuthNoDatas,
                   dnsServOptCounterSelfReferrals,
                   dnsServOptCounterSelfErrors,
                   dnsServOptCounterSelfRelNames,
                   dnsServOptCounterSelfReqRefusals,
                   dnsServOptCounterSelfReqUnparses,
                   dnsServOptCounterSelfOtherErrors,
                   dnsServOptCounterFriendsAuthAns,
                   dnsServOptCounterFriendsAuthNoNames,
                   dnsServOptCounterFriendsAuthNoDataResps,
                   dnsServOptCounterFriendsNonAuthDatas,
                   dnsServOptCounterFriendsNonAuthNoDatas,
                   dnsServOptCounterFriendsReferrals,
                   dnsServOptCounterFriendsErrors,
                   dnsServOptCounterFriendsRelNames,
                   dnsServOptCounterFriendsReqRefusals,
                   dnsServOptCounterFriendsReqUnparses,
                   dnsServOptCounterFriendsOtherErrors }
       STATUS      current
       DESCRIPTION
               "A collection of objects providing extended
               instrumentation of a DNS name server."
       ::= { dnsServMIBGroups 3 }

   dnsServZoneGroup OBJECT-GROUP
       OBJECTS   { dnsServZoneName,
                   dnsServZoneClass,
                   dnsServZoneLastReloadSuccess,
                   dnsServZoneLastReloadAttempt,
                   dnsServZoneLastSourceAttempt,
                   dnsServZoneLastSourceSuccess,
                   dnsServZoneStatus,
                   dnsServZoneSerial,
                   dnsServZoneCurrent,
                   dnsServZoneSrcName,
                   dnsServZoneSrcClass,
                   dnsServZoneSrcAddr,
                   dnsServZoneSrcStatus }
       STATUS      current
       DESCRIPTION
               "A collection of objects providing configuration control
               of a DNS name server which loads authoritative zones."
       ::= { dnsServMIBGroups 4 }

   -- Compliances.

   dnsServMIBCompliances OBJECT IDENTIFIER ::= { dnsServMIB 3 }

   dnsServMIBCompliance MODULE-COMPLIANCE
       STATUS      current
       DESCRIPTION
               "The compliance statement for agents implementing the DNS
               name server MIB extensions."
       MODULE -- This MIB module
           MANDATORY-GROUPS { dnsServConfigGroup, dnsServCounterGroup }
           GROUP   dnsServOptCounterGroup
           DESCRIPTION
               "The server optional counter group is unconditionally
               optional."
           GROUP   dnsServZoneGroup
           DESCRIPTION
               "The server zone group is mandatory for any name server
               that acts as an authoritative server for any DNS zone."
           OBJECT  dnsServConfigRecurs
           MIN-ACCESS      read-only
           DESCRIPTION
               "This object need not be writable."
           OBJECT  dnsServConfigReset
           MIN-ACCESS      read-only
           DESCRIPTION
               "This object need not be writable."
       ::= { dnsServMIBCompliances 1 }

   END
    USR-GWCWAN-MIB DEFINITIONS ::= BEGIN

    IMPORTS
        OBJECT-TYPE
            FROM SNMPv2-SMI
        IpAddress
            FROM RFC1155-SMI
        DisplayString
            FROM RFC1213-MIB
        InterfaceIndex, usrGwcwan
            FROM USR-DEFINITIONS-MIB
       TRAP-TYPE
           FROM RFC-1215;

--  usrTraps could be imported if the Enterprise field for Traps has to be
--  set to usrTraps. It is currently not being used because this convention
--  is not followed by Hipe ARC


-- Gwcwan virtual interface table

    usrGwcwanIfTable OBJECT-TYPE
        SYNTAX SEQUENCE OF UsrGwcwanIfEntry
        MAX-ACCESS not-accessible
        STATUS current
        DESCRIPTION
            "A list of Gwcwan interface entries."
        ::= { usrGwcwan 1 }

    usrGwcwanIfEntry OBJECT-TYPE
        SYNTAX UsrGwcwanIfEntry
        MAX-ACCESS not-accessible
        STATUS current
        DESCRIPTION
            "Parameter values for a Gwcwan interfaces."
        INDEX { usrGwcwanIfIndex }
        ::= { usrGwcwanIfTable 1 }

    UsrGwcwanIfEntry ::=
        SEQUENCE 
            {
            usrGwcwanIfIndex
		InterfaceIndex,
            usrGwcwanIfName
               DisplayString,
            usrGwcwanIfType
		INTEGER
            }

    usrGwcwanIfIndex OBJECT-TYPE
        SYNTAX InterfaceIndex
        MAX-ACCESS read-only
        STATUS current
        DESCRIPTION
            "The value of ifIndex for the port.  By convention
            and if possible, hardware port numbers map directly
            to external connectors.  The value for each port must
            remain constant at least from one re-initialization
            of the network management agent to the next."
        ::= { usrGwcwanIfEntry 1 }

   usrGwcwanIfName OBJECT-TYPE
       SYNTAX DisplayString (SIZE (0..32))
       MAX-ACCESS read-only
       STATUS current
       DESCRIPTION
           "The textual name of the interface.  It is of the form
	    wan:# for physical interfaces and of the form wan:#/linkname
	    for logicalinterfaces where # is the physical
            interface this logical interface resides on, and
            linkname is assigned by the administrator."
	--CONFIGURABLE
       ::= { usrGwcwanIfEntry 2 }

    usrGwcwanIfType OBJECT-TYPE
        SYNTAX INTEGER 
            {
            usrGwcwanV35(1),
            usrGwcwanDS1(2),
            usrGwcwanWSOCK(3)
            }
        MAX-ACCESS read-only
        STATUS current
        DESCRIPTION
            "This helps determine the type of physical interface /
             NIC Type/ WAN Driver Type."
        ::= { usrGwcwanIfEntry 3 }


   usrGwcwanV35IfTable OBJECT-TYPE
       SYNTAX SEQUENCE OF UsrGwcwanV35IfEntry
       MAX-ACCESS not-accessible
       STATUS current
       DESCRIPTION
           "A list of Gwcwan V35 virtual interface entries."
       ::= { usrGwcwan 2 }

   usrGwcwanV35IfEntry OBJECT-TYPE
       SYNTAX UsrGwcwanV35IfEntry
       MAX-ACCESS not-accessible
       STATUS current
       DESCRIPTION
           "Parameter values for V35 Gwcwan virtual interface."
       INDEX { usrGwcwanV35IfIndex }
       ::= { usrGwcwanV35IfTable 1 }

   UsrGwcwanV35IfEntry ::=
       SEQUENCE {
           usrGwcwanV35IfIndex
               InterfaceIndex,
           usrGwcwanV35ClockRefMode
		INTEGER,
    	   usrGwcwanV35ClockInvertedMode
        	INTEGER,
           usrGwcwanV35FlagIdlePattern
                INTEGER,
           usrGwcwanV35PortType
               INTEGER
       }

   usrGwcwanV35IfIndex OBJECT-TYPE
       SYNTAX InterfaceIndex
       MAX-ACCESS read-only
       STATUS current
       DESCRIPTION
           "The value of ifIndex for the port.  By convention
           and if possible, hardware port numbers map directly
           to external connectors.  The value for each port must
           remain constant at least from one re-initialization
           of the network management agent to the next."
       ::= { usrGwcwanV35IfEntry 1 }

    usrGwcwanV35ClockRefMode OBJECT-TYPE
        SYNTAX INTEGER
            {
            usrGwcwanDTELoopBack(1),
            usrGwcwanDCELoopBack(2)
            }
        MAX-ACCESS read-write
        STATUS current
        DESCRIPTION
            "Valid only when usrGwcwanIfType is usrGwcwanV35.
             The clock ref mode of this v35 interface"
        --CONFIGURABLE
       ::= { usrGwcwanV35IfEntry 2 }
            
    usrGwcwanV35ClockInvertedMode OBJECT-TYPE
        SYNTAX INTEGER
            {
            usrGwcwanNoneInverted(1),
            usrGwcwanClockInverted(2)
            }
        MAX-ACCESS read-write
        STATUS current
        DESCRIPTION
            "Valid only when usrGwcwanIfType is usrGwcwanV35.
             The Clock inverted mode"
        --CONFIGURABLE
       ::= { usrGwcwanV35IfEntry 3 }
            
     usrGwcwanV35FlagIdlePattern OBJECT-TYPE
        SYNTAX INTEGER 
            {
            usrGwcwanFlagIdlePattern(1),
            usrGwcwanFlagIdlePatternInvalid(2)
            } 
        MAX-ACCESS read-write
        STATUS current
        DESCRIPTION
            "Valid only when usrGwcwanIfType is usrGwcwanV35.
             This mib is an addon to rfc1659 rs232SyncPortIdlePattern mib.
             rfc1659 does not support idle pattern as flag (7F).
             If this flag is set to flagIdlePattern, then Pilgrim sets wapi
             idle pattern to flag. Other wise, Pilgrim sets wapi according
             the value set in rs232SyncPortIdlePattern."
        --CONFIGURABLE
       ::= { usrGwcwanV35IfEntry 4 }

     usrGwcwanV35PortType OBJECT-TYPE
       SYNTAX INTEGER {
			rs232(2), rs422(3), v35(5), x21(6)
		      }
        MAX-ACCESS read-write
        STATUS current
        DESCRIPTION
           "The port's hardware type. This is actually a subset of
   	    rs232PortType parameter defined by RFC1659. It was
	    necessary to re-define this variable since Write access
	    is not allowed to the parameter defined by RFC1659."
        --CONFIGURABLE
       ::= { usrGwcwanV35IfEntry 5 }

   usrGwcwanT1E1IfTable OBJECT-TYPE
       SYNTAX SEQUENCE OF UsrGwcwanT1E1IfEntry
       MAX-ACCESS not-accessible
       STATUS current
       DESCRIPTION
           "A list of Gwcwan T1E1 virtual interface entries."
       ::= { usrGwcwan 3 }

   usrGwcwanT1E1IfEntry OBJECT-TYPE
       SYNTAX UsrGwcwanT1E1IfEntry
       MAX-ACCESS not-accessible
       STATUS current
       DESCRIPTION
           "Parameter values for T1E1 Gwcwan virtual interface."
       INDEX { usrGwcwanT1E1IfIndex }
       ::= { usrGwcwanT1E1IfTable 1 }

   UsrGwcwanT1E1IfEntry ::=
       SEQUENCE {
           usrGwcwanT1E1IfIndex
               InterfaceIndex,
    	   usrGwcwanDS1CableLen
               INTEGER,
    	   usrGwcwanDS1LineBuildout
               INTEGER
       }

   usrGwcwanT1E1IfIndex OBJECT-TYPE
       SYNTAX InterfaceIndex
       MAX-ACCESS read-only
       STATUS current
       DESCRIPTION
           "The value of ifIndex for the port.  By convention
           and if possible, hardware port numbers map directly
           to external connectors.  The value for each port must
           remain constant at least from one re-initialization
           of the network management agent to the next."
       ::= { usrGwcwanT1E1IfEntry 1 }

    usrGwcwanDS1CableLen OBJECT-TYPE
        SYNTAX INTEGER
            {
	    usrGwcwanDS1CableLen0to131ft(1),
            usrGwcwanDS1CableLen131to262ft(2),
            usrGwcwanDS1CableLen262to393ft(3),
            usrGwcwanDS1CableLen393to524ft(4),
            usrGwcwanDS1CableLen524to655ft(5),
            usrGwcwanDS1CableLen655to786ft(6),
            usrGwcwanDS1CableLenLongHaul(7)
            }
        MAX-ACCESS read-write
        STATUS current
        DESCRIPTION
            "Valid only when usrGwcwanIfType is usrGwcwanDS1.
             The cable length of DS1 interface. If the interface is
             long haul, use usrGwcwanDS1CableLenLongHaul. Otherwise,
             use specified cable length."
        --CONFIGURABLE
        ::= { usrGwcwanT1E1IfEntry 2 }

    usrGwcwanDS1LineBuildout OBJECT-TYPE
        SYNTAX INTEGER
            {
            usrGwcwanDS1linebuildout0db(1),
            usrGwcwanDS1linebuildout7d5db(2),
            usrGwcwanDS1linebuildout15db(3),
            usrGwcwanDS1linebuildout22d5db(4)
            }
        MAX-ACCESS read-write
        STATUS current
        DESCRIPTION
            "Valid only when usrGwcwanIfType is usrGwcwanDS1.
             The line build out of DS1 interface."
        --CONFIGURABLE
        ::= { usrGwcwanT1E1IfEntry 3 }

    usrGwcwanWSOCKIfTable OBJECT-TYPE
        SYNTAX SEQUENCE OF UsrGwcwanWSOCKIfEntry
        MAX-ACCESS not-accessible
        STATUS current
        DESCRIPTION
            "A list of Gwcwan WSOCK virtual interface entries."
        ::= { usrGwcwan 4 }

    usrGwcwanWSOCKIfEntry OBJECT-TYPE
        SYNTAX UsrGwcwanWSOCKIfEntry
        MAX-ACCESS not-accessible
        STATUS current
        DESCRIPTION
            "Parameter values for WSOCK Gwcwan virtual interface."
        INDEX { usrGwcwanWSOCKIfIndex }
        ::= { usrGwcwanWSOCKIfTable 1 }

    UsrGwcwanWSOCKIfEntry ::=
        SEQUENCE {
            usrGwcwanWSOCKIfIndex   InterfaceIndex,
            usrGwcwanIPConnType     INTEGER,
            usrGwcwanRemoteIp       IpAddress,
            usrGwcwanRemotePort     INTEGER,
            usrGwcwanLocalPort      INTEGER
            }

    usrGwcwanWSOCKIfIndex OBJECT-TYPE
        SYNTAX InterfaceIndex
        MAX-ACCESS read-only
        STATUS current
        DESCRIPTION
            "The value of ifIndex for the port.  By convention
            and if possible, hardware port numbers map directly
            to external connectors.  The value for each port must
            remain constant at least from one re-initialization
            of the network management agent to the next."
        ::= { usrGwcwanWSOCKIfEntry 1 }

    usrGwcwanIPConnType OBJECT-TYPE
        SYNTAX INTEGER 
            {
            usrGwcwanUDP(1),
            usrGwcwanTCP(2)
            }
        MAX-ACCESS read-write
        STATUS current
        DESCRIPTION
            "Valid only when usrGwcwanIfType is usrGwcwanWSOCK.
             The type of IP service to use to make the sockets
             connection (UDP or TCP)."
        --CONFIGURABLE
        ::= { usrGwcwanWSOCKIfEntry 2 }

    usrGwcwanRemoteIp OBJECT-TYPE
        SYNTAX IpAddress
        MAX-ACCESS read-write
        STATUS current
        DESCRIPTION
            "Valid only when usrGwcwanIfType is usrGwcwanWSOCK.
             The remote IP address this virtual port sends to."
        --CONFIGURABLE
        ::= { usrGwcwanWSOCKIfEntry 3 }

    usrGwcwanRemotePort OBJECT-TYPE
        SYNTAX INTEGER
        MAX-ACCESS read-write
        STATUS current
        DESCRIPTION
            "Valid only when usrGwcwanIfType is usrGwcwanWSOCK.
             The remote UDP/IP port this virtual port sends to."
        --CONFIGURABLE
        ::= { usrGwcwanWSOCKIfEntry 4 }

    usrGwcwanLocalPort OBJECT-TYPE
        SYNTAX INTEGER
        MAX-ACCESS read-write
        STATUS current
        DESCRIPTION
            "Valid only when usrGwcwanIfType is usrGwcwanWSOCK.
             The local UDP/IP port this virtual port listens to."
        --CONFIGURABLE
        ::= { usrGwcwanWSOCKIfEntry 5 }


    usrGwcwanT1E1TrapEnaTable OBJECT-TYPE
	SYNTAX SEQUENCE OF UsrGwcwanT1E1TrapEnaEntry
	MAX-ACCESS not-accessible
	STATUS current
	DESCRIPTION
	"A trap enable table that defines a column for every trap 
	that a DS1 entity can generate."
        ::= { usrGwcwan 5 }

    usrGwcwanT1E1TrapEnaEntry OBJECT-TYPE
	SYNTAX UsrGwcwanT1E1TrapEnaEntry
	MAX-ACCESS not-accessible
	STATUS current
	DESCRIPTION
	"There is one entry in this table for every DS1 that exists 
	in the chassis."
	INDEX { usrGwcwanT1E1TrapEnaDS1Index }
	::= { usrGwcwanT1E1TrapEnaTable 1 }

    UsrGwcwanT1E1TrapEnaEntry ::=
	SEQUENCE {
	    usrGwcwanT1E1TrapEnaDS1Index
		INTEGER,
	    usrGwcwanT1E1TrapEnaYellowAlarm
		INTEGER,
	    usrGwcwanT1E1TrapEnaSndYellowAlarm
		INTEGER,
	    usrGwcwanT1E1TrapEnaAlarmIndSignal
		INTEGER,
	    usrGwcwanT1E1TrapEnaSndAlarmIndSignal
		INTEGER,
	    usrGwcwanT1E1TrapEnaRedAlarm
		INTEGER,
	    usrGwcwanT1E1TrapEnaLossOfSignal
		INTEGER,
	    usrGwcwanT1E1TrapEnaloopBack
		INTEGER,
	    usrGwcwanT1E1TrapEnaRcvTestCode
		INTEGER
	}

    usrGwcwanT1E1TrapEnaDS1Index OBJECT-TYPE
	SYNTAX INTEGER
	MAX-ACCESS read-only
	STATUS current
	DESCRIPTION
	"The value of ifIndex for the DS1/ES1 port.  By convention
	and if possible, hardware port numbers map directly
	to external connectors.  The value for each port must
	remain constant at least from one re-initialization
	of the network management agent to the next."
	::= { usrGwcwanT1E1TrapEnaEntry 1 }

    usrGwcwanT1E1TrapEnaYellowAlarm OBJECT-TYPE
	SYNTAX INTEGER{
	  enableTrap(1),
	  disableAll(2),
	  enableLog(3),
	  enableAll(4)
	}
	MAX-ACCESS read-write
	STATUS current
	DESCRIPTION
	"Enable the generation of an SNMP trap for Far-End Loss of
	Frame condition (signaled by a received Yellow Alarm) on the
	specified DS1. This corresponds to dsx1RcvFarEndLOF bit in
	dsx1LineStatus variable"
	--CONFIGURABLE
	::= { usrGwcwanT1E1TrapEnaEntry 2 }

    usrGwcwanT1E1TrapEnaSndYellowAlarm OBJECT-TYPE
	SYNTAX INTEGER{
	  enableTrap(1),
	  disableAll(2),
	  enableLog(3),
	  enableAll(4)
	}
	MAX-ACCESS read-write
	STATUS current
	DESCRIPTION
	"Enable the generation of an SNMP trap for Near End Sending
	Yellow Alarm condition on the specified DS1. This corresponds
	to dsx1XmtFarEndLOF bit in dsx1LineStatus variable"
	--CONFIGURABLE
	::= { usrGwcwanT1E1TrapEnaEntry 3 }

    usrGwcwanT1E1TrapEnaAlarmIndSignal OBJECT-TYPE
	SYNTAX INTEGER{
	  enableTrap(1),
	  disableAll(2),
	  enableLog(3),
	  enableAll(4)
	}
	MAX-ACCESS read-write
	STATUS current
	DESCRIPTION
	"Enable the generation of an SNMP trap for Far End Sending
	Alarm Indication Signal condition on the specified DS1. This
	corresponds to dsx1RcvAIS bit in dsx1LineStatus variable"
	--CONFIGURABLE
	::= { usrGwcwanT1E1TrapEnaEntry 4 }

    usrGwcwanT1E1TrapEnaSndAlarmIndSignal OBJECT-TYPE
	SYNTAX INTEGER{
	  enableTrap(1),
	  disableAll(2),
	  enableLog(3),
	  enableAll(4)
	}
	MAX-ACCESS read-write
	STATUS current
	DESCRIPTION
	"Enable the generation of an SNMP trap for Near End Sending
	Alarm Indication Signal condition on the specified DS1.
	This corresponds to dsx1XmtAIS bit in dsx1LineStatus variable"
	--CONFIGURABLE
	::= { usrGwcwanT1E1TrapEnaEntry 5 }

    usrGwcwanT1E1TrapEnaRedAlarm OBJECT-TYPE
	SYNTAX INTEGER{
	  enableTrap(1),
	  disableAll(2),
	  enableLog(3),
	  enableAll(4)
	}
	MAX-ACCESS read-write
	STATUS current
	DESCRIPTION
	"Enable the generation of an SNMP trap for Near End Loss Of
	Frame (in red alarm condition) condition on the specified DS1.
	This corresponds to dsx1LossOfFrame bit in dsx1LineStatus variable"
	--CONFIGURABLE
	::= { usrGwcwanT1E1TrapEnaEntry 6 }

    usrGwcwanT1E1TrapEnaLossOfSignal OBJECT-TYPE
	SYNTAX INTEGER{
	  enableTrap(1),
	  disableAll(2),
	  enableLog(3),
	  enableAll(4)
	}
	MAX-ACCESS read-write
	STATUS current
	DESCRIPTION
	"Enable the generation of an SNMP trap for Near End Loss Of
	Signal condition on the specified DS1. This corresponds to
	dsx1LossOfSignal bit in dsx1LineStatus variable"
	--CONFIGURABLE
	::= { usrGwcwanT1E1TrapEnaEntry 7 }

    usrGwcwanT1E1TrapEnaloopBack OBJECT-TYPE
	SYNTAX INTEGER{
	  enableTrap(1),
	  disableAll(2),
	  enableLog(3),
	  enableAll(4)
	}
	MAX-ACCESS read-write
	STATUS current
	DESCRIPTION
	"Enable the generation of an SNMP trap for Near End loopback
	condition on the specified DS1. This corresponds to
	dsx1LoopbackState bit in dsx1LineStatus variable"
	--CONFIGURABLE
	::= { usrGwcwanT1E1TrapEnaEntry 8 }

    usrGwcwanT1E1TrapEnaRcvTestCode OBJECT-TYPE
	SYNTAX INTEGER{
	  enableTrap(1),
	  disableAll(2),
	  enableLog(3),
	  enableAll(4)
	}
	MAX-ACCESS read-write
	STATUS current
	DESCRIPTION
	"Enable the generation of an SNMP trap for Near End test code
	condition on the specified DS1. This corresponds to
	dsx1RcvTestCode bit in dsx1LineStatus variable"
	--CONFIGURABLE
	::= { usrGwcwanT1E1TrapEnaEntry 9 }



	usrGwcwanT1E1YellowAlarm TRAP-TYPE
	ENTERPRISE usrGwcwan
	VARIABLES {
	  usrGwcwanT1E1TrapEnaDS1Index
	}
	DESCRIPTION
	"This trap is generated for an active Far-End Loss of Frame
	condition (signaled by a received Yellow Alarm) on the
	specified DS1."
	--#TYPE "Alarm"
	::= 1

	usrGwcwanT1E1ClrYellowAlarm TRAP-TYPE
	ENTERPRISE usrGwcwan
	VARIABLES {
	  usrGwcwanT1E1TrapEnaDS1Index
	}
	DESCRIPTION
	"This trap is generated when Far-End Loss of Frame condition
	(signaled by a received Yellow Alarm) clears on the
	specified DS1."
	--#TYPE "Alarm"
	::= 2

	usrGwcwanT1E1SndYellowAlarm TRAP-TYPE
	ENTERPRISE usrGwcwan
	VARIABLES {
	  usrGwcwanT1E1TrapEnaDS1Index
	}
	DESCRIPTION
	"This trap is generated for an active Near End Sending Yellow
	Alarm condition on the specified DS1."
	--#TYPE "Alarm"
	::= 3

	usrGwcwanT1E1ClrSndYellowAlarm TRAP-TYPE
	ENTERPRISE usrGwcwan
	VARIABLES {
	  usrGwcwanT1E1TrapEnaDS1Index
	}
	DESCRIPTION
	"This trap is generated when Near End Sending Yellow
	Alarm condition clears on the specified DS1."
	--#TYPE "Alarm"
	::= 4

	usrGwcwanT1E1AlarmIndSignal TRAP-TYPE
	ENTERPRISE usrGwcwan
	VARIABLES {
	  usrGwcwanT1E1TrapEnaDS1Index
	}
	DESCRIPTION
	"This trap is generated for an active Far End Sending Alarm
	Indication Signal condition on the specified DS1."
	--#TYPE "Alarm"
	::= 5

	usrGwcwanT1E1ClrAlarmIndSignal TRAP-TYPE
	ENTERPRISE usrGwcwan
	VARIABLES {
	  usrGwcwanT1E1TrapEnaDS1Index
	}
	DESCRIPTION
	"This trap is generated when Far End Sending Alarm
	Indication Signal condition clears on the specified DS1."
	--#TYPE "Alarm"
	::= 6

	usrGwcwanT1E1SndAlarmIndSignal TRAP-TYPE
	ENTERPRISE usrGwcwan
	VARIABLES {
	  usrGwcwanT1E1TrapEnaDS1Index
	}
	DESCRIPTION
	"This trap is generated for an active Near End Sending Alarm
	Indication Signal condition on the specified DS1."
	--#TYPE "Alarm"
	::= 7

	usrGwcwanT1E1ClrSndAlarmIndSignal TRAP-TYPE
	ENTERPRISE usrGwcwan
	VARIABLES {
	  usrGwcwanT1E1TrapEnaDS1Index
	}
	DESCRIPTION
	"This trap is generated when Near End Sending Alarm
	Indication Signal condition clears on the specified DS1."
	--#TYPE "Alarm"
	::= 8

	usrGwcwanT1E1RedAlarm TRAP-TYPE
	ENTERPRISE usrGwcwan
	VARIABLES {
	  usrGwcwanT1E1TrapEnaDS1Index
	}
	DESCRIPTION
	"This trap is generated for an active Near End Loss Of Frame
	(in red alarm condition) condition on the specified DS1."
	--#TYPE "Alarm"
	::= 9

	usrGwcwanT1E1ClrRedAlarm TRAP-TYPE
	ENTERPRISE usrGwcwan
	VARIABLES {
	  usrGwcwanT1E1TrapEnaDS1Index
	}
	DESCRIPTION
	"This trap is generated when Near End Loss Of Frame
	(in red alarm condition) condition clears on the specified DS1."
	--#TYPE "Alarm"
	::= 10

	usrGwcwanT1E1LossOfSignal TRAP-TYPE
	ENTERPRISE usrGwcwan
	VARIABLES {
	  usrGwcwanT1E1TrapEnaDS1Index
	}
	DESCRIPTION
	"This trap is generated for an active Near End Loss Of Signal
	condition on the specified DS1."
	--#TYPE "Alarm"
	::= 11

	usrGwcwanT1E1ClrLossOfSignal TRAP-TYPE
	ENTERPRISE usrGwcwan
	VARIABLES {
	  usrGwcwanT1E1TrapEnaDS1Index
	}
	DESCRIPTION
	"This trap is generated when Near End Loss Of Signal condition
	clears on the specified DS1."
	--#TYPE "Alarm"
	::= 12

	usrGwcwanT1E1loopBack TRAP-TYPE
	ENTERPRISE usrGwcwan
	VARIABLES {
	  usrGwcwanT1E1TrapEnaDS1Index
	}
	DESCRIPTION
	"This trap is generated for an active Near End loopback condition
	on the specified DS1."
	--#TYPE "Alarm"
	::= 13

	usrGwcwanT1E1ClrloopBack TRAP-TYPE
	ENTERPRISE usrGwcwan
	VARIABLES {
	  usrGwcwanT1E1TrapEnaDS1Index
	}
	DESCRIPTION
	"This trap is generated when Near End loopback condition clears
	on the specified DS1."
	--#TYPE "Alarm"
	::= 14

	usrGwcwanT1E1RcvTestCode TRAP-TYPE
	ENTERPRISE usrGwcwan
	VARIABLES {
	  usrGwcwanT1E1TrapEnaDS1Index
	}
	DESCRIPTION
	"This trap is generated for an active Near End test code
	condition on the specified DS1."
	--#TYPE "Alarm"
	::= 15

	usrGwcwanT1E1ClrRcvTestCode TRAP-TYPE
	ENTERPRISE usrGwcwan
	VARIABLES {
	  usrGwcwanT1E1TrapEnaDS1Index
	}
	DESCRIPTION
	"This trap is generated when Near End test code condition
	clears on the specified DS1."
	--#TYPE "Alarm"
	::= 16
   END
RADIUS-ACC-CLIENT-MIB DEFINITIONS ::= BEGIN

     IMPORTS
            MODULE-IDENTITY, OBJECT-TYPE,
            OBJECT-IDENTITY, experimental,
            Counter32, Integer32,
            IpAddress, TimeTicks             FROM SNMPv2-SMI
            DisplayString                    FROM SNMPv2-TC
            MODULE-COMPLIANCE, OBJECT-GROUP  FROM SNMPv2-CONF;


     radius OBJECT-IDENTITY
            STATUS  current
            DESCRIPTION
                  "The OID assigned to RADIUS MIB work by the IANA."
            ::= { experimental 79 }

     radiusAccounting  OBJECT IDENTIFIER ::= {radius 2}

     radiusAccClientMIB MODULE-IDENTITY
            LAST-UPDATED "9708211659Z"
            ORGANIZATION "IETF RADIUS Working Group."
            CONTACT-INFO
                   " Bernard Aboba
                     Microsoft
                     One Microsoft Way
                     Redmond, WA  98052
                     US

                     Phone: +1 425 936 6605
                     EMail: bernarda@microsoft.com"
            DESCRIPTION
                  "The MIB module for entities implementing the client side of
                   the Remote Access Dialin User Service (RADIUS) accounting
                   protocol."
            ::= { radiusAccounting 2 }

     radiusAccClientMIBObjects     OBJECT IDENTIFIER ::= { radiusAccClientMIB 1 }

     radiusAccClient  OBJECT IDENTIFIER ::= { radiusAccClientMIBObjects 1 }


     radiusAccClientInvalidServerAddresses OBJECT-TYPE
           SYNTAX Counter32
           MAX-ACCESS read-only
           STATUS current
           DESCRIPTION
                 "The total number of RADIUS Accounting-Response packets
                  received from unknown addresses since client start-up."
           ::= { radiusAccClient 1 }

     radiusAccClientIdentifier OBJECT-TYPE
           SYNTAX DisplayString
           MAX-ACCESS read-only
           STATUS current
           DESCRIPTION
                 "The NAS-Identifier of the RADIUS accounting client."
           ::= { radiusAccClient 2 }

     radiusAccServerTable OBJECT-TYPE
           SYNTAX     SEQUENCE OF RadiusAccServerEntry
           MAX-ACCESS not-accessible
           STATUS     current
           DESCRIPTION
                 "The (conceptual) table listing the RADIUS accounting
                  servers with which the client shares a secret."
           ::= { radiusAccClient 3 }

     radiusAccServerEntry OBJECT-TYPE
           SYNTAX     RadiusAccServerEntry
           MAX-ACCESS not-accessible
           STATUS     current
           DESCRIPTION
                 "An entry (conceptual row) representing a RADIUS
                  accounting server with which the client shares a secret."
           INDEX      { radiusAccServerIndex }
           ::= { radiusAccServerTable 1 }

     RadiusAccServerEntry ::= SEQUENCE {
           radiusAccServerIndex                           Integer32,
           radiusAccServerAddress                         IpAddress,
           radiusAccClientRoundTripTime                   TimeTicks,
           radiusAccClientAccountingRequests              Counter32,
           radiusAccClientAccountingRetransmissions       Counter32,
           radiusAccClientAccountingResponses             Counter32,
           radiusAccClientMalformedAccountingResponses    Counter32,
           radiusAccClientAccountingBadAuthenticators     Counter32,
           radiusAccClientAccountingPendingRequests       Counter32,
           radiusAccClientAccountingTimeouts              Counter32,
           radiusAccClientUnknownType                     Counter32
     }

     radiusAccServerIndex OBJECT-TYPE
           SYNTAX     Integer32
           MAX-ACCESS not-accessible
           STATUS     current
           DESCRIPTION
                 "The RADIUS accounting server with which
                  the client interacts."
           ::= { radiusAccServerEntry 1 }

     radiusAccServerAddress OBJECT-TYPE
           SYNTAX     IpAddress
           MAX-ACCESS read-only
           STATUS     current
           DESCRIPTION
                 "The IP address of the RADIUS accounting server
                 referred to in this table entry."
           ::= { radiusAccServerEntry 2 }

     radiusAccClientRoundTripTime  OBJECT-TYPE
           SYNTAX TimeTicks
           MAX-ACCESS read-only
           STATUS current
           DESCRIPTION
                 "The total roundtrip time of the last packet sent
                 between the accounting client and the RADIUS server
                 referred to in this table entry."
           ::= { radiusAccServerEntry 3 }

     radiusAccClientAccountingRequests OBJECT-TYPE
           SYNTAX Counter32
           MAX-ACCESS read-only
           STATUS current
           DESCRIPTION
                 "The total number of RADIUS Accounting-Request packets
                  sent since client start-up. This does not include
                  retransmissions."
           ::= { radiusAccServerEntry 4 }

     radiusAccClientAccountingRetransmissions OBJECT-TYPE
           SYNTAX Counter32
           MAX-ACCESS read-only
           STATUS current
           DESCRIPTION
                 "The total number of RADIUS Accounting-Request packets
                  retransmitted to the same server since client start-up.
                  Retransmissions include retries where the
                  Identifier and Acct-Delay have been updated."
           ::= { radiusAccServerEntry 5 }

     radiusAccClientAccountingResponses OBJECT-TYPE
           SYNTAX Counter32
           MAX-ACCESS read-only
           STATUS current
           DESCRIPTION
                 "The total number of RADIUS Accounting-Response
                 packets received from this server since client start-up."
           ::= { radiusAccServerEntry 6 }

     radiusAccClientMalformedAccountingResponses OBJECT-TYPE
           SYNTAX Counter32
           MAX-ACCESS read-only
           STATUS current
           DESCRIPTION
                 "The total number of malformed RADIUS Accounting-Response
                 packets received from this server since client start-up.
                 Bad authenticators are not included as malformed access
                 responses."
           ::= { radiusAccServerEntry 7 }

     radiusAccClientAccountingBadAuthenticators OBJECT-TYPE
           SYNTAX Counter32
           MAX-ACCESS read-only
           STATUS current
           DESCRIPTION
                 "The total number of RADIUS Accounting-Response
                  packets which contained invalid authenticators
                  received from this server since client start-up."
           ::= { radiusAccServerEntry 8 }

     radiusAccClientAccountingPendingRequests OBJECT-TYPE
           SYNTAX Counter32
           MAX-ACCESS read-only
           STATUS current
           DESCRIPTION
                 "The total number of RADIUS Accounting-Request packets
                  sent to this server that have not yet timed out or
                  received a response. This variable is incremented when an
                  Accounting-Request is sent and decremented due to a timeout
                  or retransmission."
           ::= { radiusAccServerEntry 9 }

     radiusAccClientAccountingTimeouts OBJECT-TYPE
          SYNTAX Counter32
          MAX-ACCESS read-only
          STATUS current
          DESCRIPTION
                 "The total number of accounting timeouts to this server
                 since client startup. After a timeout the client may
                 retry to the same server, send to a different server, or
                 give up. A retry to the same server is counted as a
                 retransmit as well as a timeout. A send to a different
                 server is counted as an Accounting-Request as well as a timeout."
           ::= { radiusAccServerEntry  10 }

     radiusAccClientUnknownType OBJECT-TYPE
           SYNTAX Counter32
           MAX-ACCESS read-only
           STATUS current
           DESCRIPTION
                 "The total number of RADIUS packets of unknown type which
                  were received from this server on the accounting port
                  since client start-up."
           ::= { radiusAccServerEntry  11 }

     -- conformance information

     radiusAccClientMIBConformance
                  OBJECT IDENTIFIER ::= { radiusAccClientMIB 2 }
     radiusAccClientMIBCompliances
                  OBJECT IDENTIFIER ::= { radiusAccClientMIBConformance 1 }
     radiusAccClientMIBGroups
                  OBJECT IDENTIFIER ::= { radiusAccClientMIBConformance 2 }


     -- compliance statements

     radiusAccClientMIBCompliance MODULE-COMPLIANCE
          STATUS  current
          DESCRIPTION
                "The compliance statement for accounting clients
                 implementing the RADIUS Accounting Client MIB."
          MODULE  -- this module
                 MANDATORY-GROUPS { radiusAccClientMIBGroup }

          ::= { radiusAccClientMIBCompliances 1 }


     -- units of conformance

     radiusAccClientMIBGroup OBJECT-GROUP
          OBJECTS { radiusAccClientInvalidServerAddresses,
                    radiusAccServerAddress,
                    radiusAccClientRoundTripTime,
                    radiusAccClientAccountingRequests,
                    radiusAccClientAccountingRetransmissions,
                    radiusAccClientAccountingResponses,
                    radiusAccClientMalformedAccountingResponses,
                    radiusAccClientAccountingBadAuthenticators,
                    radiusAccClientAccountingPendingRequests,
                    radiusAccClientAccountingTimeouts,
                    radiusAccClientUnknownType
                 }
          STATUS  current
          DESCRIPTION
                "The basic collection of objects providing management of
                 RADIUS Accounting Clients."
          ::= { radiusAccClientMIBGroups 1 }

     END
--
--	usr_ip_policy.mib
--
--
-- Author:         Sharon K. Barrett
--
--
--  | Copyright (c) 1995 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-OSPF-MIB DEFINITIONS ::= BEGIN

	IMPORTS
                MODULE-IDENTITY, OBJECT-TYPE, Integer32, IpAddress
				FROM SNMPv2-SMI
		DisplayString, common, UsrConfigStatus
				FROM USR-DEFINITIONS-MIB
		TEXTUAL-CONVENTION, RowStatus
				FROM SNMPv2-TC;

usrOspf MODULE-IDENTITY
        LAST-UPDATED "9901141020Z"
        ORGANIZATION "3Com Corporation, Carrier Division"
        CONTACT-INFO "Customer Support"
      
    DESCRIPTION
       "The MIB module to describe the USR OSPF Protocol"
    ::= { common 63 }

TOSType ::= TEXTUAL-CONVENTION
    STATUS      current
    DESCRIPTION
       "Type of Service is defined as a mapping to the IP Type of
       Service Flags as defined in the IP Forwarding Table MIB

       +-----+-----+-----+-----+-----+-----+-----+-----+
       |                 |                       |     |
       |   PRECEDENCE    |    TYPE OF SERVICE    |  0  |
       |                 |                       |     |
       +-----+-----+-----+-----+-----+-----+-----+-----+

                IP TOS                IP TOS
           Field     Policy      Field     Policy

           Contents    Code      Contents    Code
           0 0 0 0  ==>   0      0 0 0 1  ==>   2
           0 0 1 0  ==>   4      0 0 1 1  ==>   6
           0 1 0 0  ==>   8      0 1 0 1  ==>  10
           0 1 1 0  ==>  12      0 1 1 1  ==>  14
           1 0 0 0  ==>  16      1 0 0 1  ==>  18
           1 0 1 0  ==>  20      1 0 1 1  ==>  22
           1 1 0 0  ==>  24      1 1 0 1  ==>  26
           1 1 1 0  ==>  28      1 1 1 1  ==>  30

       The remaining values are left for future definition."
    SYNTAX      Integer32 (0..30)


-- Begin IP policy object definitions here...

--
--      The OSPF Export Policy Table
--
--
--  Rip gateway and interface have been removed from the
--  the ospf export policy table. To add them back in
--  modify the table using the commented out
--  items at the bottom of this file.
--

    usrOspfExportPolicyTable OBJECT-TYPE
        SYNTAX   SEQUENCE OF UsrOspfExportPolicyEntry
        MAX-ACCESS   not-accessible
        STATUS   current
        DESCRIPTION
	            "A set of export policies for OSPF."
      ::= { usrOspf 1 }

    usrOspfExportPolicyEntry OBJECT-TYPE
        SYNTAX  UsrOspfExportPolicyEntry
        MAX-ACCESS   not-accessible
        STATUS   current
        DESCRIPTION
           ""
       REFERENCE
          ""
      INDEX { 
	usrOspfExportPolicyNet,
	usrOspfExportPolicyMask,
	usrOspfExportPolicyRouteSource
	}
      ::= { usrOspfExportPolicyTable 1 }

UsrOspfExportPolicyEntry ::= SEQUENCE {
      usrOspfExportPolicyNet			IpAddress,
      usrOspfExportPolicyMask			IpAddress,
      usrOspfExportPolicyRouteSource		INTEGER,
      usrOspfExportPolicyAction			INTEGER,
      usrOspfExportPolicyMetric			Integer32 (0..16777215),
      usrOspfExportPolicyMetricType		INTEGER,
      usrOspfExportPolicyTag			Integer32 (0..2147483647),
      usrOspfExportPolicyStatus                 RowStatus
}

usrOspfExportPolicyNet OBJECT-TYPE
        SYNTAX		IpAddress
        MAX-ACCESS   	read-only
        STATUS   	current
        DESCRIPTION
           "Specifies the network address which will match this policy."
::= { usrOspfExportPolicyEntry 1 }

usrOspfExportPolicyMask OBJECT-TYPE
        SYNTAX		IpAddress
        MAX-ACCESS   	read-only
        STATUS   	current
        DESCRIPTION
           "The network mask to be applied to the network address to
            specify a specific address or range of addresses for this policy."
::= { usrOspfExportPolicyEntry 2 }

usrOspfExportPolicyRouteSource OBJECT-TYPE
        SYNTAX		INTEGER {  
				any(0),
                        	local(1),
                              	static(2),
                 	      	rip(8)
			}
        MAX-ACCESS	read-only
        STATUS		current
        DESCRIPTION
           "Identifies the source of the routing information: local,
            static, or RIP."
	DEFVAL		{ 0 }
::= { usrOspfExportPolicyEntry 3 }
--	As part of NSSA development two new CLI commands are added
--	to delete all OSPF send and receive policies, where the 
--	source will be 'any' and the policy will be 'zero' in 
--	order to distinguish between all policy deletion and one policy.

usrOspfExportPolicyAction OBJECT-TYPE
	SYNTAX		INTEGER {
                        	advertise(1),
                              	doNotAdvertise(2)
			}
        MAX-ACCESS   	read-create
        STATUS   	current
        DESCRIPTION
           "The action to take with this export policy. If the action
            is propagate, the route or routes described by the entry are included
            in the local OSPF updates if they exist in the routing table. If the
            action is ignore, the route or routes described are not advertised in
            the local OSPF updates."
	DEFVAL		{ 1 }
       --CONFIGURABLE
::= { usrOspfExportPolicyEntry 4 }


usrOspfExportPolicyMetric OBJECT-TYPE
        SYNTAX   	Integer32 (0..16777215) 
        MAX-ACCESS   	read-create
        STATUS   	current
        DESCRIPTION
           "The metric to be used when advertising the route(s)
            described by this policy. A metric value of 0 will cause the 
            metric that is inserted into the AS External Links advertisement 
            to be taken from the associated route entry in the routing table.
            For all other valid metric values, the value is directly inserted
            into the AS External Links advertisement."
	DEFVAL		{ 0 }
       --CONFIGURABLE
::= { usrOspfExportPolicyEntry 5 }

usrOspfExportPolicyMetricType OBJECT-TYPE
        SYNTAX   	INTEGER {
                        	comparableCost(1), -- external type I
                              	nonComparable(2)  -- external type II
			}
        MAX-ACCESS   	read-create
        STATUS   	current
        DESCRIPTION
           "This variable describes the external type of metric that the
            export policy will advertise an external route as. Essentially
            this variable determines if the E Bit in an AS External Links
            Advertisement is set or not. A selection of external type II
            will cause the E bit to be set to 1. An external route tagged
            as an external type II indicates that the external cost to
            the route is all that should be associated with it's cost metric.
            A route tagged as external type I indicates that the
            internal cost to the Autonomous System Border Router as well
            as the external cost of the route should be associated with
            the route's cost metric."
	DEFVAL		{ 1 }
       --CONFIGURABLE
::= { usrOspfExportPolicyEntry 6 }

usrOspfExportPolicyTag OBJECT-TYPE
        SYNTAX   	Integer32 (0..2147483647)
        MAX-ACCESS   	read-create
        STATUS   	current
        DESCRIPTION
           "The routing tag to be used when exporting the route(s)
described by this policy entry."
	DEFVAL		{ 0 }
       --CONFIGURABLE
::= { usrOspfExportPolicyEntry 7}

usrOspfExportPolicyStatus OBJECT-TYPE
        SYNTAX   	RowStatus
        MAX-ACCESS   	read-create
        STATUS   	current
        DESCRIPTION
           "The administrative status of the export policy entry."
       --CONFIGURABLE
::= { usrOspfExportPolicyEntry 8}


--
--      The OSPF Import Policy Table
--

usrOspfImportPolicyTable OBJECT-TYPE
        SYNTAX   	SEQUENCE OF UsrOspfImportPolicyEntry
        MAX-ACCESS   	not-accessible
        STATUS   	current
        DESCRIPTION
	"A set of OSPF import policies."
::= { usrOspf 2 }

usrOspfImportPolicyEntry OBJECT-TYPE
        SYNTAX   	UsrOspfImportPolicyEntry
        MAX-ACCESS   	not-accessible
        STATUS   	current
        DESCRIPTION
           "An entry for an OSPF Import Policy"
      INDEX {usrOspfImportPolicyNet }
::= { usrOspfImportPolicyTable 1 }

UsrOspfImportPolicyEntry ::= SEQUENCE {
	usrOspfImportPolicyNet		                IpAddress,
	usrOspfImportPolicyMask		                IpAddress,
	usrOspfImportPolicyAction	                INTEGER,
	usrOspfImportPolicyRoutingPreference	        INTEGER,
        usrOspfImportPolicyStatus                       RowStatus
}

usrOspfImportPolicyNet OBJECT-TYPE
        SYNTAX		IpAddress
        MAX-ACCESS   	read-only
        STATUS   	current
        DESCRIPTION
           "The network address of the destination or set of
destinations for which this import policy is being defined."
::= { usrOspfImportPolicyEntry 1 }

usrOspfImportPolicyMask OBJECT-TYPE
        SYNTAX   	IpAddress
        MAX-ACCESS   	read-only
        STATUS   	current
        DESCRIPTION
           "The network mask for the destination or set of
            destinations for which this import policy is being defined."
::= { usrOspfImportPolicyEntry 2 }

usrOspfImportPolicyAction OBJECT-TYPE
        SYNTAX   	INTEGER {
                        	accept(1),
	                 	ignore(2)
			}
        MAX-ACCESS   	read-create
        STATUS   	current
        DESCRIPTION
           "The action to take with this import policy. If the action
            is accept, the route or routes described by the entry are included 
            in the routing table when received in peer OSPF updates. If the action 
            is ignore, the route or routes described are filtered from received 
            OSPF updates."
       --CONFIGURABLE
::= { usrOspfImportPolicyEntry 3 }

usrOspfImportPolicyRoutingPreference OBJECT-TYPE
        SYNTAX 	INTEGER  {
	            routingPreference0 (1),   -- same routing preference as OSPF 
                                              --    internal routes
                    routingPreference1 (2),   -- same routing preference as OSPF 
                                              --    external type 1 routes
                    routingPreference2 (3),   -- same routing preference as OSPF
                                              --    external type 2 routes
                    routingPreference3 (4)    -- route will never be used for
                                              --    forwarding
                  }
        MAX-ACCESS   	read-create
        STATUS   	current
        DESCRIPTION
           "The routing preference to associate with this route. A routing preference
            of routingPreference0 is more preferred than a preference equal to
            routingPreference1. A routing preference of routingPreference1 is more 
            preferred than a preference equal to routingPreference2. A routing
            preference of routingPreference3 will cause a route to never be used
	    in forwarding. It will be present in the routing table but will never
            make it into the forwarding table."
       --CONFIGURABLE
::= { usrOspfImportPolicyEntry 4 }

usrOspfImportPolicyStatus OBJECT-TYPE
        SYNTAX   	RowStatus
        MAX-ACCESS   	read-create
        STATUS   	current
        DESCRIPTION
           "The administrative status of the import policy entry."
       --CONFIGURABLE
::= { usrOspfImportPolicyEntry 5}


--      The OSPF Area Table

    usrOspfAreaTable OBJECT-TYPE
        SYNTAX   SEQUENCE OF UsrOspfAreaEntry
        MAX-ACCESS   not-accessible
        STATUS   current
        DESCRIPTION
           "NOT IMPLEMENTED!
           Information describing the configured  parame-
           ters  and cumulative statistics of the router's
           attached areas."
       REFERENCE
          "OSPF Version 2, Section 6  The Area Data Struc-
          ture"
       ::= { usrOspf 3 }

    usrOspfAreaEntry OBJECT-TYPE
        SYNTAX  UsrOspfAreaEntry
        MAX-ACCESS   not-accessible
        STATUS   current
        DESCRIPTION
           "Information describing the configured  parame-
           ters  and  cumulative  statistics of one of the
           router's attached areas."
      INDEX { 
	usrOspfAreaId
	}
      ::= { usrOspfAreaTable 1 }

UsrOspfAreaEntry ::= SEQUENCE {
      usrOspfAreaId		IpAddress,
      usrOspfAreaType	        INTEGER
}

    usrOspfAreaId OBJECT-TYPE
        SYNTAX       IpAddress
        MAX-ACCESS   read-only
        STATUS   current
        DESCRIPTION
           "A 32-bit integer uniquely identifying an area.
           Area ID 0.0.0.0 is used for the OSPF backbone."
       REFERENCE
          "OSPF Version 2, Appendix C.2 Area parameters"
      ::= { usrOspfAreaEntry 1 }


    usrOspfAreaType OBJECT-TYPE
        SYNTAX   INTEGER    {
                    transit (1),
                    stub (2)
                  }
        MAX-ACCESS   read-write
        STATUS   current
        DESCRIPTION
           "The area's support for determining if the Type is Stub or Transit."
       REFERENCE
          "OSPF Version 2, Appendix C.2 Area parameters"
      DEFVAL { transit }
      ::= { usrOspfAreaEntry 2 }


usrOspfVersion OBJECT-TYPE
	SYNTAX      DisplayString
	MAX-ACCESS      read-only
	STATUS      current
	DESCRIPTION
		"The current software version of the OSPF Process."
::= { usrOspf 4 }


usrOspfConfigFileName OBJECT-TYPE
	SYNTAX      DisplayString
	MAX-ACCESS      read-only
	STATUS      current
	DESCRIPTION		
		"The name of a ConfigFile to read/write  permanent database records."
::= { usrOspf 5 }

usrOspfCFMStatusFlag  OBJECT-TYPE
	SYNTAX	  UsrConfigStatus
	MAX-ACCESS      read-write
	STATUS      current
	DESCRIPTION
		"Setting the value of this object to `save' causes the values
		 of the OSPF Group to be written out to the current config
		 file. While the new data is being written, the config process
		 will set the value of this flag to `saving''. Any
		 attempts to set the value while it is  not `normal'
		 (i.e. the file is currently being written to the
		 ConfigFile) will result in a badValue error being
		 returned. Setting the value to `normal' will result in no
		 action."
::= { usrOspf 6 }


--      The OSPF Default Area ID

usrOspfDefaultAreaId OBJECT-TYPE
    SYNTAX       IpAddress
    MAX-ACCESS   read-write
    STATUS   current
    DESCRIPTION
           "A 32-bit integer uniquely identifying an area.
           Area ID 0.0.0.0 is used for the OSPF backbone.  This area ID is used 
           to create the default area when the ospf base is created"
    DEFVAL   { '00000000'H }    -- 0.0.0.0
    --CONFIGURABLE
::= { usrOspf 7 }


--      The OSPF Host Table

    usrOspfHostTable OBJECT-TYPE
        SYNTAX   SEQUENCE OF UsrOspfHostEntry
        MAX-ACCESS   not-accessible
        STATUS   current
        DESCRIPTION
           "The list of Hosts, and their metrics, that the
            router will advertise as host routes."
       REFERENCE
          "OSPF Version 2, Section C.6  The Host route parameters"
::= { usrOspf 8 }

    usrOspfHostEntry OBJECT-TYPE
        SYNTAX  UsrOspfHostEntry
        MAX-ACCESS   not-accessible
        STATUS   current
        DESCRIPTION
           "A metric to be advertised, for a given type of service,
            when a given host is reachable."
      INDEX { 
	usrOspfHostIpAddress, usrOspfHostIpTOS
	}
      ::= { usrOspfHostTable 1 }

UsrOspfHostEntry ::= SEQUENCE {
      usrOspfHostIpAddress	IpAddress,
      usrOspfHostIpTOS	        TOSType,
      usrOspfHostIpMask	        IpAddress
}

    usrOspfHostIpAddress OBJECT-TYPE
        SYNTAX       IpAddress
        MAX-ACCESS   read-only
        STATUS   current
        DESCRIPTION
           "The IP Address of the Host."
       REFERENCE
          "OSPF Version 2, Appendix C.6 Host route parameters"
      ::= { usrOspfHostEntry 1 }

    usrOspfHostIpTOS OBJECT-TYPE
        SYNTAX       TOSType
        MAX-ACCESS   read-only
        STATUS   current
        DESCRIPTION
           "The Type of Service of the route being config-
           ured."
        REFERENCE
          "OSPF Version 2, Appendix C.6 Host route parame-
          ters"
	::= { usrOspfHostEntry 2 }

    usrOspfHostIpMask OBJECT-TYPE
        SYNTAX       IpAddress
        MAX-ACCESS   read-only
        STATUS   current
        DESCRIPTION
           "The IP Mask of the Host."
       REFERENCE
          "The IP Mask of the Host entry - Proprietary object"
      ::= { usrOspfHostEntry 3 }


--      The OSPF Cryptographic Key Table

    usrOspfCryptoKeyTable OBJECT-TYPE
        SYNTAX   SEQUENCE OF UsrOspfCryptoKeyEntry
        MAX-ACCESS   not-accessible
        STATUS   current
        DESCRIPTION
           "The list of OSPF Cryptographic Authentication Keys 
            per OSPF Interface that will be used to generating/
            verifying Cryptographic authentication."
       REFERENCE
          "OSPF Version 2, Appendix D. Authentication"
      ::= { usrOspf 9 }

    usrOspfCryptoKeyEntry OBJECT-TYPE
        SYNTAX   UsrOspfCryptoKeyEntry
        MAX-ACCESS   not-accessible
        STATUS   current
        DESCRIPTION
           "The information regarding a single OSPF Cryptographic
            Authentication Key."
       INDEX { usrOspfIfIpAddress, usrOspfAddressLessIf, usrOspfCryptoKeyId }
       ::= { usrOspfCryptoKeyTable 1 }

UsrOspfCryptoKeyEntry ::=
    SEQUENCE {
        usrOspfIfIpAddress
            IpAddress,
        usrOspfAddressLessIf
            Integer32,
        usrOspfCryptoKeyId
            Integer32 (0..'FF'h),
        usrOspfCryptoKey
            OCTET STRING,
        usrOspfCryptoKeyStatus
            RowStatus,
        usrOspfCryptoAlgo
            Integer32,
        usrOspfCryptoKeyStartAccept
            Integer32,
        usrOspfCryptoKeyStartGenerate
            Integer32,
        usrOspfCryptoKeyStopGenerate
            Integer32,
        usrOspfCryptoKeyStopAccept
            Integer32
              }

    usrOspfIfIpAddress OBJECT-TYPE
        SYNTAX   IpAddress
        MAX-ACCESS   read-only
        STATUS   current
        DESCRIPTION
           "The IP address of this OSPF interface."
       ::= { usrOspfCryptoKeyEntry 1 }

    usrOspfAddressLessIf OBJECT-TYPE
        SYNTAX   Integer32
        MAX-ACCESS   read-only
        STATUS   current
        DESCRIPTION
           "For the purpose of easing  the  instancing  of
           addressed   and  addressless  interfaces;  This
           variable takes the value 0 on  interfaces  with
           IP  Addresses,  and  the corresponding value of
           ifIndex for interfaces having no IP Address."
       ::= { usrOspfCryptoKeyEntry 2 }

    usrOspfCryptoKeyId OBJECT-TYPE
        SYNTAX   Integer32 (0..'FF'h)
        MAX-ACCESS   read-only
        STATUS   current
        DESCRIPTION
           "The Key ID of this cryptographic key.    This 
            field identifies the algorithm and secret key 
            used to create the message digest appended to 
            the OSPF packet. Key Identifiers are unique
            per-interface (or equivalently, per-subnet)."
       ::= { usrOspfCryptoKeyEntry 3 }

    usrOspfCryptoKey OBJECT-TYPE
        SYNTAX   OCTET STRING (SIZE (0..256))
        MAX-ACCESS   read-create
        STATUS   current
        DESCRIPTION
           "The Cryptographic Authentication Key.  If the 
            Authentication Type is Cryptographic,  and the 
            key length is shorter than 16 octets, the agent
            will left adjust and zero fill to 16 octets.

            When read, usrOspfCryptoKey always returns an 
            Octet String of length zero."

       --CONFIGURABLE
      ::= { usrOspfCryptoKeyEntry 4 }

    usrOspfCryptoKeyStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."

       --CONFIGURABLE
      ::= { usrOspfCryptoKeyEntry 5 }

    usrOspfCryptoAlgo OBJECT-TYPE
        SYNTAX   Integer32
                    -- md5 (0)
        MAX-ACCESS   read-create
        STATUS   current
        DESCRIPTION
           "This field identifies the algorithm used to create
           message digest."
      DEFVAL { 0 }
       --CONFIGURABLE
      ::= { usrOspfCryptoKeyEntry 6 }

    usrOspfCryptoKeyStartAccept OBJECT-TYPE
        SYNTAX   Integer32
        MAX-ACCESS   read-create
        STATUS   current
        DESCRIPTION
           "The time that the router will start accepting 
           packets that have been created with the given key.
           
           The time is expressed as a number of seconds since
           the Epoch, 00:00:00 GMT, on January 1, 1995"

       --CONFIGURABLE
      ::= { usrOspfCryptoKeyEntry 7 }

    usrOspfCryptoKeyStartGenerate OBJECT-TYPE
        SYNTAX   Integer32
        MAX-ACCESS   read-create
        STATUS   current
        DESCRIPTION
           "The time that the router will start using the 
           key for packet generation.
           
           The time is expressed as a number of seconds since
           the Epoch, 00:00:00 GMT, on January 1, 1995"

       --CONFIGURABLE
      ::= { usrOspfCryptoKeyEntry 8 }

    usrOspfCryptoKeyStopGenerate OBJECT-TYPE
        SYNTAX   Integer32
        MAX-ACCESS   read-create
        STATUS   current
        DESCRIPTION
           "The time that the router will stop using the 
           key for packet generation.
           
           The time is expressed as a number of seconds since
           the Epoch, 00:00:00 GMT, on January 1, 1995.

           The value 0HFFFFFFFF stands for infinity."

       --CONFIGURABLE
      ::= { usrOspfCryptoKeyEntry 9 }

    usrOspfCryptoKeyStopAccept OBJECT-TYPE
        SYNTAX   Integer32
        MAX-ACCESS   read-create
        STATUS   current
        DESCRIPTION
           "The time that the router will stop accepting 
           packets that have been created with the given key.
           
           The time is expressed as a number of seconds since
           the Epoch, 00:00:00 GMT, on January 1, 1995

           The value 0HFFFFFFFF stands for infinity."

       --CONFIGURABLE
      ::= { usrOspfCryptoKeyEntry 10 }

--      OSPF Default Area

usrOspfDefaultAreaStatus OBJECT-TYPE
        SYNTAX   RowStatus
        MAX-ACCESS   read-create
        STATUS   current
        DESCRIPTION
           "This variable is used to delete the ospf default
            area."
::= { usrOspf 10 }

END

-- Commented out items for ospf send policy table. To restore
-- the ospf send policy rip gateway and rip interface cut and
-- and paste these items back into the table. Within the table
-- they followed the export policy action. Adjust usrOspfExportPolicyEntry
-- numbers accordingly for ospf send metric, metric type, and tag
-- after reinserting rip gateway and interface.
--
--      INDEX { 
--	usrOspfExportPolicyRouteSource, 
--	usrOspfExportPolicyNet,
--	usrOspfExportPolicyMask,
--	usrOspfExportPolicyFromRIPGateway,
--	usrOspfExportPolicyReceivedOnRIPInterface 
--	}
--
-- UsrOspfExportPolicyEntry ::= SEQUENCE {
--      usrOspfExportPolicyRouteSource		INTEGER,
--      usrOspfExportPolicyNet			IpAddress,
--      usrOspfExportPolicyMask			IpAddress,
--      usrOspfExportPolicyAction		INTEGER,
--      usrOspfExportPolicyFromRIPGateway		IpAddress,
--      usrOspfExportPolicyReceivedOnRIPInterface	IpAddress,
--      usrOspfExportPolicyMetric			Integer32,
--      usrOspfExportPolicyMetricType		INTEGER,
--      usrOspfExportPolicyTag			Integer32,
--      usrOspfExportPolicyStatus               RowStatus
-- }
--
-- usrOspfExportPolicyFromRIPGateway OBJECT-TYPE
--        SYNTAX   	IpAddress
--        MAX-ACCESS   	read-only
--        STATUS   	current
--        DESCRIPTION
--           "This attribute applies when the route to be exported is a
-- RIP route. If this attribute is defined, then only RIP updates
-- received from the specified RIP gateway are eligible for export. Any
-- RIP gateway can be specified using 0.0.0.0 as the address."
-- ::= { usrOspfExportPolicyEntry 5 }
--
-- usrOspfExportPolicyReceivedOnRIPInterface OBJECT-TYPE
--        SYNTAX   	IpAddress
--        MAX-ACCESS   	read-only
--        STATUS   	current
--        DESCRIPTION
--           "This attribute applies when the route described by this
-- policy is a RIP route. If this attribute is defined, then only RIP
-- updates received on the specified interface are eligible for
-- export. Use 0.0.0.0 to indicate that this policy applies to RIP
-- updates received on any interface."
-- ::= { usrOspfExportPolicyEntry 6 }
--




--
--    usr_fr_ext.mib - The USR Frame Relay Proprietary MIB module
--                     This MIB module when used in conjunction with
--                     rfc2115.mib obsoletes previously used usr_fr.mib 
--
--
-- Author:         <Cezary Wierucki>
--
-- $Id: Exp $
--
--  | Copyright (c) 1995-98 U.S. Robotics Access Corp., Skokie, IL 60076   |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--


USR-FR-EXT-MIB DEFINITIONS ::= BEGIN

     IMPORTS
             DisplayString, UsrConfigStatus, common     FROM USR-DEFINITIONS-MIB
             MODULE-IDENTITY, NOTIFICATION-TYPE,
             Integer32, Counter32, OBJECT-TYPE          FROM SNMPv2-SMI
             RowStatus, TimeStamp, TruthValue           FROM SNMPv2-TC;

     --  Frame Relay DTE MIB Extensions
     --
     --      the range of ifIndex
     --
     Index ::= Integer32       -- 1..ifNumber

     --
     --      the range of a Data Link Connection Identifier
     --
     DLCI ::= INTEGER(16..1023)        -- 0..DLCINumber

     --
     --  The Frame Relay Base Group.
     --


    usrFRExt MODULE-IDENTITY
         LAST-UPDATED "9901141020Z"
         ORGANIZATION "3Com Corporation, Carrier Division"
         CONTACT-INFO "Customer Support"
      
         DESCRIPTION
                 "The USR Frame Relay DTE MIB Extensions"
         ::= { common 64 }


     usrfrExtBaseCfgFileName OBJECT-TYPE
         SYNTAX  DisplayString
         MAX-ACCESS  read-write
         STATUS  current
         DESCRIPTION
                 "The name of a Frame Relay ConfigFile to read/write
                 permanent database records. If the value of this
                 object is an empty string, then the FR process
                 uses the default name '@file://FrFile.cfg'."
         ::= { usrFRExt 1 }

     usrfrExtBaseCFMSaveStatus OBJECT-TYPE
         SYNTAX  UsrConfigStatus
         MAX-ACCESS  read-write
         STATUS  current
         DESCRIPTION
                 "Setting the value of this object to 'save'
                 causes the values of the FR Base Group
                 entries to be written out to the current FR
                 configuration file. While the new configuration file 
                 is being written, the FR process will set the value
                 of this flag set to 'saving'. Any attempts to set
                 the value while it is not 'normal' (i.e. the file
                 is currently being written to the config file)
                 will result in a badValue error being returned.
                 Setting the value to 'normal' will result in no
                 action."
         ::= { usrFRExt 2 }


     --
     --  Frame Relay Conformance Options
     --
  
     usrfrExtBaseConformanceOption OBJECT-TYPE
         SYNTAX INTEGER {
                 sprint  (1),
                 idacom  (2)
         }
         MAX-ACCESS  read-write
         STATUS  current
         DESCRIPTION
                 "This variable indicates the Conformance Option
                 of the Frame Relay Datalink."
         DEFVAL { 2 }
         --CONFIGURABLE
         ::= { usrFRExt 3 }


     --
     --  Data Link Connection Management Interface Extensions
     --
     --  The variables that configure the DLC Management Interface.
     --

     usrfrExtDlcmiTable OBJECT-TYPE
         SYNTAX   SEQUENCE OF UsrFrExtDlcmiEntry
         MAX-ACCESS   not-accessible
         STATUS   current
         DESCRIPTION
            "The Parameters for the Data Link Connection Management
            Interface for the frame relay service on this
            interface."
         REFERENCE
            "Draft American National Standard T1.617-1991, Annex D"
         ::= { usrFRExt 4 }

         usrfrExtDlcmiEntry OBJECT-TYPE
             SYNTAX   UsrFrExtDlcmiEntry
             MAX-ACCESS   not-accessible
             STATUS   current
             DESCRIPTION
                "The Parameters for a particular Data Link Connection
                 Management Interface."
            INDEX { usrfrExtDlcmiIfIndex }
            ::= { usrfrExtDlcmiTable 1 }

         UsrFrExtDlcmiEntry ::=
             SEQUENCE {
                 usrfrExtDlcmiIfIndex
                     Index,
                 usrfrExtDlcmiOperStatus
                     INTEGER,
                 usrfrExtDlcmiMaximumTransferUnit
                     INTEGER,
                 usrfrExtDlcmiAccessRate
                     INTEGER,
                 usrfrExtDlcmiNewPVCLearning
                     INTEGER,
                 usrfrExtDlcmiTrace
                     INTEGER
         }

         usrfrExtDlcmiIfIndex OBJECT-TYPE
             SYNTAX  Index
             MAX-ACCESS  read-only
             STATUS  current
             DESCRIPTION
                 "The ifIndex value of the  corresponding  ifEntry."
             ::= { usrfrExtDlcmiEntry 1 }

         usrfrExtDlcmiOperStatus OBJECT-TYPE
             SYNTAX  INTEGER {
                 ready         (1),
                 waitForDriver (2),
                 recovery      (3),
                 down          (4),
                 disabled      (5)
             }
             MAX-ACCESS  read-only
             STATUS  current
             DESCRIPTION
                 "This variable indicates the operational status of 
                 the Frame Relay link. The Status is determined by a 
                 success or failure of the LMI message exchange with
                 the Frame Relay switch, the WAN Interface state and 
                 Administrator Link State."
             ::= { usrfrExtDlcmiEntry 2 }

         usrfrExtDlcmiMaximumTransferUnit OBJECT-TYPE
             SYNTAX  INTEGER (260..2048)
             MAX-ACCESS  read-write
             STATUS  current
             DESCRIPTION
                 "This is the largest number of bytes the Frame Relay
                 DLL Layer will attempt to transmit through its 
                 physical interface in a single frame."
             DEFVAL { 1600 }
             --CONFIGURABLE
             ::= { usrfrExtDlcmiEntry 3 }

         usrfrExtDlcmiAccessRate OBJECT-TYPE
             SYNTAX  INTEGER (0..8192000)
             MAX-ACCESS  read-write
             STATUS  current
             DESCRIPTION
                 "This is the speed of access channel, a Frame Relay
                 DLL Layer will use for data transfer. This value is
                 expressed in bits per second.
                 If value 0 is selected, then the Access Rate value used
                 by Frame Relay to its calculations will be taken from
                 physical WAN driver."
             REFERENCE
                 "CCITT Recommendation I.370, Section 1.2 access rate"
             DEFVAL { 1544000 }
             --CONFIGURABLE
             ::= { usrfrExtDlcmiEntry 4 }

         usrfrExtDlcmiNewPVCLearning OBJECT-TYPE
             SYNTAX  INTEGER {
                 on  (1),
                 off (2)
             }
             MAX-ACCESS  read-write
             STATUS  current
             DESCRIPTION
                 "This indicates if the Frame Relay interface 
                 can dynamically create a new PVC based on
                 information received in LMI Full Status message."
             DEFVAL { 2 }
             --CONFIGURABLE
             ::= { usrfrExtDlcmiEntry 5 }

         usrfrExtDlcmiTrace OBJECT-TYPE
             SYNTAX  INTEGER {
                 on  (1),
                 off (2)
             }
             MAX-ACCESS  read-write
             STATUS  current
             DESCRIPTION
                 "This indicates if the LMI Protocol frames trace 
                 information will be displayed on the console."
             DEFVAL { 2 }
             --CONFIGURABLE
             ::= { usrfrExtDlcmiEntry 6 }



     -- A Frame Relay service is a multiplexing service.  Data
     -- Link Connection Identifiers enumerate virtual circuits
     -- (permanent or switched) which are layered onto the underlying
     -- interface, represented by ifEntry.  Therefore, each of the entries
     -- in the Standard MIB's Interface Table with an IfType of
     -- Frame Relay represents a Q.922 interface.  Zero or more
     -- virtual circuits are layered onto this interface and provide
     -- interconnection with various remote destinations.
     -- Each such virtual circuit is represented by an entry in the
     -- circuit table.

     --   Circuit Table Extensions  
     -- The table describing the use of the PVCs attached to
     -- each Frame Relay Interface.

     usrfrExtCircuitTable OBJECT-TYPE
         SYNTAX   SEQUENCE OF UsrFrExtCircuitEntry
         MAX-ACCESS   not-accessible
         STATUS   current
         DESCRIPTION
            "A table containing information about 
            specific virtual circuits."
         ::= { usrFRExt 5 }

         usrfrExtCircuitEntry OBJECT-TYPE
             SYNTAX   UsrFrExtCircuitEntry
             MAX-ACCESS   not-accessible
             STATUS   current
             DESCRIPTION
                "The information regarding a single  Data  Link
                Connection Identifier."
             INDEX { usrfrExtCircuitIfIndex, usrfrExtCircuitDlci }
             ::= { usrfrExtCircuitTable 1 }

         UsrFrExtCircuitEntry ::=
             SEQUENCE {
                 usrfrExtCircuitIfIndex
                     Index,
                 usrfrExtCircuitDlci
                     DLCI,
                 usrfrExtCircuitOperStatus
                     INTEGER,
                 usrfrExtCircuitCIR
                     INTEGER,
                 usrfrExtCircuitBcMax
                     INTEGER,
                 usrfrExtCircuitBcMin
                     INTEGER,
                 usrfrExtCircuitCurrentBc
                     INTEGER,
                 usrfrExtCircuitTc
                     INTEGER,
                 usrfrExtCircuitBECNMonitoring
                     INTEGER,
                 usrfrExtCircuitCMP
                     INTEGER,
                 usrfrExtCircuitTxFramesCongested             
                     Counter32,             
                 usrfrExtCircuitTxOctetsCongested
                     Counter32,             
                 usrfrExtCircuitTxFramesDiscarded
                     Counter32,             
                 usrfrExtCircuitTxOctetsDiscarded
                     Counter32,             
                 usrfrExtCircuitTxFramesFromForwarder
                     Counter32,             
                 usrfrExtCircuitTxOctetsFromForwarder    
                     Counter32,             
                 usrfrExtCircuitRxFramesCongested    
                     Counter32,             
                 usrfrExtCircuitRxOctetsCongested    
                     Counter32,             
                 usrfrExtCircuitRxOctetsDiscarded    
                     Counter32,             
                 usrfrExtCircuitRxFramesByForwarder    
                     Counter32,             
                 usrfrExtCircuitRxOctetsByForwarder    
                     Counter32,             
                 usrfrExtCircuitTxIPProtocolFrames    
                     Counter32,             
                 usrfrExtCircuitRxIPProtocolFrames    
                     Counter32,             
                 usrfrExtCircuitTxIPXProtocolFrames    
                     Counter32,             
                 usrfrExtCircuitRxIPXProtocolFrames    
                     Counter32,             
                 usrfrExtCircuitTxATProtocolFrames    
                     Counter32,             
                 usrfrExtCircuitRxATProtocolFrames    
                     Counter32,             
                 usrfrExtCircuitTxBridgedFrames    
                     Counter32,             
                 usrfrExtCircuitRxBridgedFrames    
                     Counter32,
                 usrfrExtCircuitPVCName
                     DisplayString,
                 usrfrExtCircuitTrace
                     INTEGER,
                 usrfrExtCircuitBECNRatio
                     INTEGER,
                 usrfrExtCircuitTxL2TPProtocolFrames
                     Counter32,
                 usrfrExtCircuitRxL2TPProtocolFrames
                     Counter32,
	         usrfrExtCircuitPTMPGroupState
		     TruthValue,
	         usrfrExtCircuitPTMPGroupName
	             DisplayString	
         }

         usrfrExtCircuitIfIndex OBJECT-TYPE
             SYNTAX  Index
             MAX-ACCESS  read-only
             STATUS  current
             DESCRIPTION
                 "The ifIndex value of the ifEntry this  virtual
                 circuit is layered onto."
             ::= { usrfrExtCircuitEntry 1 }

         usrfrExtCircuitDlci OBJECT-TYPE
             SYNTAX  DLCI
             MAX-ACCESS  read-only
             STATUS  current
             DESCRIPTION
                 "The Data Link Connection Identifier  for  this
                 virtual circuit."
             REFERENCE
                 "Draft American National  Standard  T1.618-1991,
                 Section 3.3.6"
             ::= { usrfrExtCircuitEntry 2 }

         usrfrExtCircuitOperStatus OBJECT-TYPE
             SYNTAX  INTEGER {
                 up       (1),  -- ready to pass packets
                 down     (2),
                 disabled (3)
             }
             MAX-ACCESS  read-only
             STATUS  current
             DESCRIPTION
                 "The current operational state of the FR PVC.  The
                 disabled(3) state indicates that no operational packets
                 can be passed through this PVC.  It reflects the fact that 
                 CircuitAdminStatus is disabled. The up(1) describes
                 a state when packets can be sent and received on the PVC.
                 The down(2) indicates that PVC is not able to operate. 
                 The up(1) and down(2) states are set up based
                 on LMI PVCS IE."
             ::= { usrfrExtCircuitEntry 3 }

         usrfrExtCircuitCIR OBJECT-TYPE
             SYNTAX  INTEGER {
                 on  (1),
                 off (2)
             }
             MAX-ACCESS  read-write
             STATUS  current
             DESCRIPTION
                 "Committed Information Rate (CIR) describes how congestion
                 control is handled.  Off indicates that no attempt
                 at transmit control is made.
                 On indicates that Frame Relay is monitoring amount of
                 data transmitted through the physical interface and
                 restricts this according to CIR rules."
             DEFVAL { 1 }
             --CONFIGURABLE
             ::= { usrfrExtCircuitEntry 4 }

         usrfrExtCircuitBcMax OBJECT-TYPE
             SYNTAX  INTEGER (0..8192000)
             MAX-ACCESS  read-write
             STATUS  current
             DESCRIPTION
                 "The Committed Burst Size is the maximum amount of data
                 (in bits) that the user may offer to the network, under
                 normal conditions, during a time interval Tc.
                 The BcMax value defines the upper boundary of current
                 Bc value."
             REFERENCE 
                 "CCITT Recommendation I.370, Section 1.2 Bc"
             DEFVAL { 256000 }
             --CONFIGURABLE
             ::= { usrfrExtCircuitEntry 5 }

         usrfrExtCircuitBcMin OBJECT-TYPE
             SYNTAX  INTEGER (0..8192000)
             MAX-ACCESS  read-write
             STATUS  current
             DESCRIPTION
                 "The Committed Burst Size is the maximum amount of data
                 (in bits) that the user may offer to the network, under
                 normal conditions, during a time interval Tc.
                 The BcMin value defines the lower boundary of current
                 Bc value."
             REFERENCE 
                 "CCITT Recommendation I.370, Section 1.2 Bc"
             DEFVAL { 128000 }
             --CONFIGURABLE
             ::= { usrfrExtCircuitEntry 6 }

         usrfrExtCircuitCurrentBc OBJECT-TYPE
             SYNTAX  INTEGER (0..8192000)
             MAX-ACCESS  read-only
             STATUS  current
             DESCRIPTION
                 "The Committed Burst Size is the maximum amount of data
                 (in bits) that the user may offer to the network, under
                 normal conditions, during a time interval Tc.
                 The CurrentBc value represents currently used Bc value."
             REFERENCE 
                 "CCITT Recommendation I.370, Section 1.2 Bc"
             ::= { usrfrExtCircuitEntry 7 }

         usrfrExtCircuitTc OBJECT-TYPE
             SYNTAX  INTEGER (0..2147483647)
             MAX-ACCESS  read-only
             STATUS  current
             DESCRIPTION
                 "The Committed Rate Measurement Interval is
                 a time interval during which the user is allowed
                 to send only the committed amount of date (Bc) and
                 the excess amount of data (Be). This value is
                 calculated and is expressed in milliseconds."
             REFERENCE 
                 "CCITT Recommendation I.370, Section 1.2 Tc"
             ::= { usrfrExtCircuitEntry 8 }

         usrfrExtCircuitBECNMonitoring OBJECT-TYPE
             SYNTAX  INTEGER {
                 on  (1),
                 off (2)
             }
             MAX-ACCESS  read-write
             STATUS  current
             DESCRIPTION
                 "BECN Monitoring describes if BECN congestion notification
                 control is handled.  Off indicates that no attempt
                 at congestion notification control is made. 
                 On indicates that the BECN bit of the Q.922 header is
                 monitored. When the BECN bit indicates that the Frame
                 Relay switch is experiencing congestion over this DLCI,
                 the transmission rate will be slowed, to value calculated
                 based on usrfrCircuitBcMin. When the bit indicates 
                 alleviation of congestion, the transmission rate will 
                 be incrementally increased back to a value calculated 
                 based on usrfrCircuitBcMax."
             DEFVAL { 2 }
             --CONFIGURABLE
             ::= { usrfrExtCircuitEntry 9 }

         usrfrExtCircuitCMP OBJECT-TYPE
             SYNTAX  INTEGER (1..100)
             MAX-ACCESS  read-write
             STATUS  current
             DESCRIPTION
                 "The Congestion Monitoring Period - is a period
                 expressed in seconds, during which Frame Relay
                 monitors number of received BECN events."    
             DEFVAL { 10 }
             --CONFIGURABLE
             ::= { usrfrExtCircuitEntry 10 }


         --
         -- Circuit Statistics
         --

         usrfrExtCircuitTxFramesCongested OBJECT-TYPE
             SYNTAX  Counter32
             MAX-ACCESS  read-only
             STATUS  current
             DESCRIPTION
                 "Number of frames congested by a physical driver
                  during transmit action taken by this PVC since 
                  it was created."
             ::= { usrfrExtCircuitEntry 11 }

         usrfrExtCircuitTxOctetsCongested OBJECT-TYPE
             SYNTAX  Counter32
             MAX-ACCESS  read-only
             STATUS  current
             DESCRIPTION
                 "Number of bytes congested by a physical driver
                  during transmit action taken by this PVC since 
                  it was created."
             ::= { usrfrExtCircuitEntry 12 }

         usrfrExtCircuitTxFramesDiscarded OBJECT-TYPE
             SYNTAX  Counter32
             MAX-ACCESS  read-only
             STATUS  current
             DESCRIPTION
                 "Number of frames discarded during transmit 
                  action by this PVC since it was created."
             ::= { usrfrExtCircuitEntry 13 }

         usrfrExtCircuitTxOctetsDiscarded OBJECT-TYPE
             SYNTAX  Counter32
             MAX-ACCESS  read-only
             STATUS  current
             DESCRIPTION
                 "Number of bytes discarded during transmit
                  action by this PVC since it was created."
             ::= { usrfrExtCircuitEntry 14 }

         usrfrExtCircuitTxFramesFromForwarder OBJECT-TYPE
             SYNTAX  Counter32
             MAX-ACCESS  read-only
             STATUS  current
             DESCRIPTION
                 "Number of frames handed down from forwarder to
                  this PVC since it was created."
             ::= { usrfrExtCircuitEntry 15 }

         usrfrExtCircuitTxOctetsFromForwarder OBJECT-TYPE
             SYNTAX  Counter32
             MAX-ACCESS  read-only
             STATUS  current
             DESCRIPTION
                 "Number of bytes handed down from forwarder to
                  this PVC since it was created."
             ::= { usrfrExtCircuitEntry 16 }

         usrfrExtCircuitRxFramesCongested OBJECT-TYPE
             SYNTAX  Counter32
             MAX-ACCESS  read-only
             STATUS  current
             DESCRIPTION
                 "Number of frames congested by a forwarder
                  during receive action taken by this PVC since 
                  it was created."
             ::= { usrfrExtCircuitEntry 17 }

         usrfrExtCircuitRxOctetsCongested OBJECT-TYPE
             SYNTAX  Counter32
             MAX-ACCESS  read-only
             STATUS  current
             DESCRIPTION
                 "Number of bytes congested by a forwarder
                  during receive action taken by this PVC since 
                  it was created."
             ::= { usrfrExtCircuitEntry 18 }

         usrfrExtCircuitRxOctetsDiscarded OBJECT-TYPE
             SYNTAX  Counter32
             MAX-ACCESS  read-only
             STATUS  current
             DESCRIPTION
                 "Number of bytes discarded during receive
                  action by this PVC since it was created."
             ::= { usrfrExtCircuitEntry 19 }

         usrfrExtCircuitRxFramesByForwarder OBJECT-TYPE
             SYNTAX  Counter32
             MAX-ACCESS  read-only
             STATUS  current
             DESCRIPTION
                 "Number of frames passed to forwarder by
                  this PVC since it was created."
             ::= { usrfrExtCircuitEntry 20 }

         usrfrExtCircuitRxOctetsByForwarder OBJECT-TYPE
             SYNTAX  Counter32
             MAX-ACCESS  read-only
             STATUS  current
             DESCRIPTION
                 "Number of bytes passed to forwarder by
                  this PVC since it was created."
             ::= { usrfrExtCircuitEntry 21 }

         usrfrExtCircuitTxIPProtocolFrames OBJECT-TYPE
             SYNTAX  Counter32
             MAX-ACCESS  read-only
             STATUS  current
             DESCRIPTION
                 "Number of IP protocol frames sent by
                  this PVC since it was created."
             ::= { usrfrExtCircuitEntry 22 }

         usrfrExtCircuitRxIPProtocolFrames OBJECT-TYPE
             SYNTAX  Counter32
             MAX-ACCESS  read-only
             STATUS  current
             DESCRIPTION
                 "Number of IP protocol frames received by
                  this PVC since it was created."
             ::= { usrfrExtCircuitEntry 23 }

         usrfrExtCircuitTxIPXProtocolFrames OBJECT-TYPE
             SYNTAX  Counter32
             MAX-ACCESS  read-only
             STATUS  current
             DESCRIPTION
                 "Number of IPX protocol frames sent by
                  this PVC since it was created."
             ::= { usrfrExtCircuitEntry 24 }

         usrfrExtCircuitRxIPXProtocolFrames OBJECT-TYPE
             SYNTAX  Counter32
             MAX-ACCESS  read-only
             STATUS  current
             DESCRIPTION
                 "Number of IPX protocol frames received by
                  this PVC since it was created."
             ::= { usrfrExtCircuitEntry 25 }

         usrfrExtCircuitTxATProtocolFrames OBJECT-TYPE
             SYNTAX  Counter32
             MAX-ACCESS  read-only
             STATUS  current
             DESCRIPTION
                 "Number of AppleTalk protocol frames sent by
                  this PVC since it was created."
             ::= { usrfrExtCircuitEntry 26 }

         usrfrExtCircuitRxATProtocolFrames OBJECT-TYPE
             SYNTAX  Counter32
             MAX-ACCESS  read-only
             STATUS  current
             DESCRIPTION
                 "Number of AppleTalk protocol frames received by
                  this PVC since it was created."
             ::= { usrfrExtCircuitEntry 27 }

         usrfrExtCircuitTxBridgedFrames OBJECT-TYPE
             SYNTAX  Counter32
             MAX-ACCESS  read-only
             STATUS  current
             DESCRIPTION
                 "Number of Bridged frames sent by
                  this PVC since it was created."
             ::= { usrfrExtCircuitEntry 28 }

         usrfrExtCircuitRxBridgedFrames OBJECT-TYPE
             SYNTAX  Counter32
             MAX-ACCESS  read-only
             STATUS  current
             DESCRIPTION
                 "Number of Bridged frames received by
                  this PVC since it was created."
             ::= { usrfrExtCircuitEntry 29 }

         usrfrExtCircuitPVCName OBJECT-TYPE
             SYNTAX  DisplayString (SIZE (1..32))
             MAX-ACCESS  read-write
             STATUS  current
             DESCRIPTION
                 "The name of this PVC. This table allows
                 the Pilgrim CLI process to translate PVC
                 name into IfIndex/DLCI pair."
             --CONFIGURABLE
             ::= { usrfrExtCircuitEntry 30 }

         usrfrExtCircuitTrace OBJECT-TYPE
             SYNTAX  INTEGER {
                 on  (1),
                 off (2)
             }
             MAX-ACCESS  read-write
             STATUS  current
             DESCRIPTION
                 "This indicates if the Frame Relay data frames trace 
                 information will be displayed on the console for this
                 PVC."
             DEFVAL { 2 }
             --CONFIGURABLE
             ::= { usrfrExtCircuitEntry 31 }
 
         usrfrExtCircuitBECNRatio OBJECT-TYPE
             SYNTAX  INTEGER (1..99)
             MAX-ACCESS  read-write
             STATUS  current
             DESCRIPTION
                 "BECN/(BECN + NO_BECN) percentage ratio used by 
                 BECN Monitoring mechanism to make a BC adjustment
                 decision for this PVC. It is expressed in percents."
             DEFVAL { 50 }
             --CONFIGURABLE
             ::= { usrfrExtCircuitEntry 32 }

         usrfrExtCircuitTxL2TPProtocolFrames OBJECT-TYPE
             SYNTAX  Counter32
             MAX-ACCESS  read-only
             STATUS  current
             DESCRIPTION
                 "Number of L2TP Protocol frames sent by
                  this PVC since it was created."
             ::= { usrfrExtCircuitEntry 33 }

         usrfrExtCircuitRxL2TPProtocolFrames OBJECT-TYPE
             SYNTAX  Counter32
             MAX-ACCESS  read-only
             STATUS  current
             DESCRIPTION
                 "Number of L2TP Protocol frames received by
                  this PVC since it was created."
             ::= { usrfrExtCircuitEntry 34 }

		 usrfrExtCircuitPTMPGroupState	OBJECT-TYPE
			 SYNTAX  TruthValue
			 MAX-ACCESS	read-only
			 STATUS	 current
			 DESCRIPTION
				"Determines whether this PVC is attached to a PTMP
				 Group or not"
			 ::= { usrfrExtCircuitEntry 35 }

		 usrfrExtCircuitPTMPGroupName	OBJECT-TYPE
			 SYNTAX	DisplayString
			 MAX-ACCESS	read-only
			 STATUS	current
			 DESCRIPTION
				"Name of the Point-to-Multipoint group this PVC is
				 assiciated with"
			 ::= { usrfrExtCircuitEntry 36 }

     --        
     --  Frame Relay DLL Error Table Extensions
     --
     -- The table describing errors encountered on each Frame
     -- Relay Interface.

     usrfrExtErrTable OBJECT-TYPE
         SYNTAX   SEQUENCE OF UsrFrExtErrEntry
         MAX-ACCESS   not-accessible
         STATUS   current
         DESCRIPTION
            "A table containing information about Errors on the 
            Frame Relay interface."
         ::= { usrFRExt 6 }

         usrfrExtErrEntry OBJECT-TYPE
             SYNTAX   UsrFrExtErrEntry
             MAX-ACCESS   not-accessible
             STATUS   current
             DESCRIPTION
                "The error information for a single Frame Relay
                interface."
            INDEX { usrfrExtErrIfIndex }
            ::= { usrfrExtErrTable 1 }

         UsrFrExtErrEntry ::=
             SEQUENCE {
                 usrfrExtErrIfIndex
                     Index,
                 usrfrExtErrUnknownError
                     Counter32,
                 usrfrExtErrReceivedShortFrames
                     Counter32,
                 usrfrExtErrReceivedLongFrames
                     Counter32,
                 usrfrExtErrIllegalDlcis
                     Counter32,
                 usrfrExtErrUnknownDlcis
                     Counter32,
                 usrfrExtErrDlmciProtocolErrs
                     Counter32,
                 usrfrExtStatDLLRxFrames
                     Counter32,
                 usrfrExtStatDLLRxOctets
                     Counter32,
                 usrfrExtStatDLLTxFrames    
                     Counter32,
                 usrfrExtStatDLLTxOctets    
                     Counter32,
                 usrfrExtStatLMIRxFrames    
                     Counter32,
                 usrfrExtStatLMITxFrames    
                     Counter32,
                 usrfrExtStatLMIRxStatusEnquiry    
                     Counter32,
                 usrfrExtStatLMITxStatusEnquiry    
                     Counter32,
                 usrfrExtStatLMIRxStatus    
                     Counter32,
                 usrfrExtStatLMITxStatus    
                     Counter32,
                 usrfrExtStatLMIRxStatusUpdate    
                     Counter32,
                 usrfrExtErrLMINoNetworkResponse    
                     Counter32,
                 usrfrExtErrLMIInvQ922    
                     Counter32,
                 usrfrExtErrLMIInvControlField    
                     Counter32,
                 usrfrExtErrLMIInvProtocolDiscr    
                     Counter32,
                 usrfrExtErrLMIInvCallReference    
                     Counter32,
                 usrfrExtErrLMIInvMessageType    
                     Counter32,
                 usrfrExtErrLMIInvLockingShift    
                     Counter32,
                 usrfrExtErrLMIInvReportType    
                     Counter32,
                 usrfrExtErrLMIInvLIV    
                     Counter32,
                 usrfrExtErrLMIInvSeqNum    
                     Counter32,
                 usrfrExtErrLMIInvPVCStatus    
                     Counter32,
                 usrfrExtErrLMIUnsolicitedMessage    
                     Counter32,
                 usrfrExtErrLMIUnrecognizedIE    
                     Counter32,
                 usrfrExtErrLMIIncompleteMessage    
                     Counter32,
                 usrfrExtErrLMIOutOfOrderIE    
                     Counter32,
                 usrfrExtErrLMIInvSpareBits    
                     Counter32,
                 usrfrExtErrLMIInvExtensionBit    
                     Counter32,
                 usrfrExtErrLMIInvNADBits    
                     Counter32,
                 usrfrExtStatLMIRxAsyncStatus    
                     Counter32
         }

         usrfrExtErrIfIndex OBJECT-TYPE
             SYNTAX   Index
             MAX-ACCESS   read-only
             STATUS   current
             DESCRIPTION
                "The ifIndex Value of the ifEntry this  virtual
                circuit is layered onto."
            ::= { usrfrExtErrEntry 1 }

         usrfrExtErrUnknownError OBJECT-TYPE
             SYNTAX   Counter32
             MAX-ACCESS   read-only
             STATUS   current
             DESCRIPTION
                "An error which is not specified by another counter."
           ::= { usrfrExtErrEntry 2 }

         usrfrExtErrReceivedShortFrames OBJECT-TYPE
             SYNTAX   Counter32
             MAX-ACCESS   read-only
             STATUS   current
             DESCRIPTION
                "Number of frames discarded because they were
                too short."
           ::= { usrfrExtErrEntry 3 }

         usrfrExtErrReceivedLongFrames OBJECT-TYPE
             SYNTAX   Counter32
             MAX-ACCESS   read-only
             STATUS   current
             DESCRIPTION
                "Number of frames discarded because they were
                too long."
           ::= { usrfrExtErrEntry 4 }

         usrfrExtErrIllegalDlcis OBJECT-TYPE
             SYNTAX   Counter32
             MAX-ACCESS   read-only
             STATUS   current
             DESCRIPTION
                "Number of frames discarded because they contained
                illegal DLCIs."
           ::= { usrfrExtErrEntry 5 }

                 
         usrfrExtErrUnknownDlcis OBJECT-TYPE
             SYNTAX   Counter32
             MAX-ACCESS   read-only
             STATUS   current
             DESCRIPTION
                "Number of frames discarded because they contained
                unknown DLCIs."
           ::= { usrfrExtErrEntry 6 }

                 
         usrfrExtErrDlmciProtocolErrs OBJECT-TYPE
             SYNTAX   Counter32
             MAX-ACCESS   read-only
             STATUS   current
             DESCRIPTION
                "Number of Frame Relay protocol errors."
           ::= { usrfrExtErrEntry 7 }
                 

         usrfrExtStatDLLRxFrames OBJECT-TYPE
             SYNTAX   Counter32
             MAX-ACCESS   read-only
             STATUS   current
             DESCRIPTION
                "Number of Frame Relay frames received on this DLL."
           ::= { usrfrExtErrEntry 8 }

         usrfrExtStatDLLRxOctets OBJECT-TYPE
             SYNTAX   Counter32
             MAX-ACCESS   read-only
             STATUS   current
             DESCRIPTION
                "Number of bytes received on this DLL."
           ::= { usrfrExtErrEntry 9 }

         usrfrExtStatDLLTxFrames OBJECT-TYPE
             SYNTAX   Counter32
             MAX-ACCESS   read-only
             STATUS   current
             DESCRIPTION
                "Number of Frame Relay frames transmitted on this DLL."
           ::= { usrfrExtErrEntry 10 }

         usrfrExtStatDLLTxOctets OBJECT-TYPE
             SYNTAX   Counter32
             MAX-ACCESS   read-only
             STATUS   current
             DESCRIPTION
                "Number of octets transmitted on this DLL."
           ::= { usrfrExtErrEntry 11 }

         usrfrExtStatLMIRxFrames OBJECT-TYPE
             SYNTAX   Counter32
             MAX-ACCESS   read-only
             STATUS   current
             DESCRIPTION
                "Number of Frame Relay LMI frames received on this DLL."
           ::= { usrfrExtErrEntry 12 }

         usrfrExtStatLMITxFrames OBJECT-TYPE
             SYNTAX   Counter32
             MAX-ACCESS   read-only
             STATUS   current
             DESCRIPTION
                "Number of Frame Relay LMI frames transmitted on this DLL."
           ::= { usrfrExtErrEntry 13 }

         usrfrExtStatLMIRxStatusEnquiry OBJECT-TYPE
             SYNTAX   Counter32
             MAX-ACCESS   read-only
             STATUS   current
             DESCRIPTION
                "Number of Frame Relay LMI Status Enquiry frames 
                 receiveded on this DLL."
           ::= { usrfrExtErrEntry 14 }

         usrfrExtStatLMITxStatusEnquiry OBJECT-TYPE
             SYNTAX   Counter32
             MAX-ACCESS   read-only
             STATUS   current
             DESCRIPTION
                "Number of Frame Relay LMI Status Enquiry frames 
                 transmitted on this DLL."
           ::= { usrfrExtErrEntry 15 }

         usrfrExtStatLMIRxStatus OBJECT-TYPE
             SYNTAX   Counter32
             MAX-ACCESS   read-only
             STATUS   current
             DESCRIPTION
                "Number of Frame Relay LMI Status frames 
                 received on this DLL."
           ::= { usrfrExtErrEntry 16 }

         usrfrExtStatLMITxStatus OBJECT-TYPE
             SYNTAX   Counter32
             MAX-ACCESS   read-only
             STATUS   current
             DESCRIPTION
                "Number of Frame Relay LMI Status frames 
                 transmitted on this DLL."
           ::= { usrfrExtErrEntry 17 }

         usrfrExtStatLMIRxStatusUpdate OBJECT-TYPE
             SYNTAX   Counter32
             MAX-ACCESS   read-only
             STATUS   current
             DESCRIPTION
                "Number of Frame Relay LMI Status Update frames 
                 received on this DLL."
           ::= { usrfrExtErrEntry 18 }

         usrfrExtErrLMINoNetworkResponse OBJECT-TYPE
             SYNTAX   Counter32
             MAX-ACCESS   read-only
             STATUS   current
             DESCRIPTION
                "Number of lacks of Network responses to LMI 
                 Status Enquiry frames sent on this DLL."
           ::= { usrfrExtErrEntry 19 }

         usrfrExtErrLMIInvQ922 OBJECT-TYPE
             SYNTAX   Counter32
             MAX-ACCESS   read-only
             STATUS   current
             DESCRIPTION
                "Number of LMI frames with invalid Q922 header
                 received on this DLL."
           ::= { usrfrExtErrEntry 20 }

         usrfrExtErrLMIInvControlField OBJECT-TYPE
             SYNTAX   Counter32
             MAX-ACCESS   read-only
             STATUS   current
             DESCRIPTION
                "Number of LMI frames with invalid Control Field
                 received on this DLL."
           ::= { usrfrExtErrEntry 21 }

         usrfrExtErrLMIInvProtocolDiscr OBJECT-TYPE
             SYNTAX   Counter32
             MAX-ACCESS   read-only
             STATUS   current
             DESCRIPTION
                "Number of LMI frames with invalid Protocol 
                 Discriominator field received on this DLL."
           ::= { usrfrExtErrEntry 22 }

         usrfrExtErrLMIInvCallReference OBJECT-TYPE
             SYNTAX   Counter32
             MAX-ACCESS   read-only
             STATUS   current
             DESCRIPTION
                "Number of LMI frames with invalid Call Reference
                 field received on this DLL."
           ::= { usrfrExtErrEntry 23 }

         usrfrExtErrLMIInvMessageType OBJECT-TYPE
             SYNTAX   Counter32
             MAX-ACCESS   read-only
             STATUS   current
             DESCRIPTION
                "Number of LMI frames with invalid Message Type
                 field received on this DLL."
           ::= { usrfrExtErrEntry 24 }

         usrfrExtErrLMIInvLockingShift OBJECT-TYPE
             SYNTAX   Counter32
             MAX-ACCESS   read-only
             STATUS   current
             DESCRIPTION
                "Number of LMI frames with invalid Locking Shift
                 IE received on this DLL."
           ::= { usrfrExtErrEntry 25 }

         usrfrExtErrLMIInvReportType OBJECT-TYPE
             SYNTAX   Counter32
             MAX-ACCESS   read-only
             STATUS   current
             DESCRIPTION
                "Number of LMI frames with invalid Report Type
                 IE received on this DLL."
           ::= { usrfrExtErrEntry 26 }

         usrfrExtErrLMIInvLIV OBJECT-TYPE
             SYNTAX   Counter32
             MAX-ACCESS   read-only
             STATUS   current
             DESCRIPTION
                "Number of LMI frames with invalid Link Integrity
                 Verification IE received on this DLL."
           ::= { usrfrExtErrEntry 27 }

         usrfrExtErrLMIInvSeqNum OBJECT-TYPE
             SYNTAX   Counter32
             MAX-ACCESS   read-only
             STATUS   current
             DESCRIPTION
                "Number of LMI frames with invalid Sequence Number
                 field received on this DLL."
           ::= { usrfrExtErrEntry 28 }

         usrfrExtErrLMIInvPVCStatus OBJECT-TYPE
             SYNTAX   Counter32
             MAX-ACCESS   read-only
             STATUS   current
             DESCRIPTION
                "Number of LMI frames with invalid PVC Status
                 IE received on this DLL."
           ::= { usrfrExtErrEntry 29 }

         usrfrExtErrLMIUnsolicitedMessage OBJECT-TYPE
             SYNTAX   Counter32
             MAX-ACCESS   read-only
             STATUS   current
             DESCRIPTION
                "Number of unsolicited LMI frames received on 
                 this DLL."
           ::= { usrfrExtErrEntry 30 }

         usrfrExtErrLMIUnrecognizedIE OBJECT-TYPE
             SYNTAX   Counter32
             MAX-ACCESS   read-only
             STATUS   current
             DESCRIPTION
                "Number of LMI frames with unrecognized
                 IE received on this DLL."
           ::= { usrfrExtErrEntry 31 }

         usrfrExtErrLMIIncompleteMessage OBJECT-TYPE
             SYNTAX   Counter32
             MAX-ACCESS   read-only
             STATUS   current
             DESCRIPTION
                "Number of LMI frames with incomplete current
                 IE received on this DLL."
           ::= { usrfrExtErrEntry 32 }

         usrfrExtErrLMIOutOfOrderIE OBJECT-TYPE
             SYNTAX   Counter32
             MAX-ACCESS   read-only
             STATUS   current
             DESCRIPTION
                "Number of LMI frames with out_of_order IE 
                 received on this DLL."
           ::= { usrfrExtErrEntry 33 }

         usrfrExtErrLMIInvSpareBits OBJECT-TYPE
             SYNTAX   Counter32
             MAX-ACCESS   read-only
             STATUS   current
             DESCRIPTION
                "Number of LMI frames with invalid Spare Bits
                 values in IE received on this DLL."
           ::= { usrfrExtErrEntry 34 }

         usrfrExtErrLMIInvExtensionBit OBJECT-TYPE
             SYNTAX   Counter32
             MAX-ACCESS   read-only
             STATUS   current
             DESCRIPTION
                "Number of LMI frames with invalid Extension Bit
                 value in IE received on this DLL."
           ::= { usrfrExtErrEntry 35 }

         usrfrExtErrLMIInvNADBits OBJECT-TYPE
             SYNTAX   Counter32
             MAX-ACCESS   read-only
             STATUS   current
             DESCRIPTION
                "Number of LMI frames with invalid New, Active or
                 Delete bits in PVCS IE received on this DLL."
           ::= { usrfrExtErrEntry 36 }

         usrfrExtStatLMIRxAsyncStatus OBJECT-TYPE
             SYNTAX   Counter32
             MAX-ACCESS   read-only
             STATUS   current
             DESCRIPTION
                "Number of LMI Async Status frames received on this DLL."
           ::= { usrfrExtErrEntry 37 }    


     
     -- 
     --  Frame Relay Trap Extensions
     --  

     usrfrExtTraps OBJECT IDENTIFIER ::= { usrFRExt 7}
     

     usrfrExtDLCMIStatusChange NOTIFICATION-TYPE
         OBJECTS  { usrfrExtDlcmiOperStatus }
         STATUS   current

         DESCRIPTION
         " This trap indicates that the indicated Data Link Layer
         has changed state. It has either been created or invalidated,
         or has toggled between the active and inactive states. " 
         
         ::= { usrfrExtTraps 1 }


	--
	--  Frame Relay PTMP PVC Group Definition
	-- The Point-to-Multipoint PVC Group is a logical
      -- interface between Layer 3 protocol forwarders
      -- and a Group of PTP PVCs participating in this
      -- Group.
      --

usrfrExtPTMPGroupTable OBJECT-TYPE
         SYNTAX   SEQUENCE OF UsrFrExtPTMPGroupEntry
         MAX-ACCESS   not-accessible
         STATUS   current
         DESCRIPTION
            "A table containing information about 
            PTMP PVC Group specific"
         ::= { usrFRExt 8 }

         usrfrExtPTMPGroupEntry OBJECT-TYPE
             SYNTAX   UsrFrExtPTMPGroupEntry
             MAX-ACCESS   not-accessible
             STATUS   current
             DESCRIPTION
                "The information regarding a single PTMP PVC
                Group entry."
             INDEX { usrfrExtPTMPGroupName }
             ::= { usrfrExtPTMPGroupTable 1 }

         UsrFrExtPTMPGroupEntry ::=
             SEQUENCE {
                 usrfrExtPTMPGroupName
                     DisplayString,
                 usrfrExtPTMPGroupIndex
                     Index,
                 usrfrExtPTMPGroupOperStatus
                     INTEGER,
                 usrfrExtPTMPNumberOfPVCs
                     Counter32,
                 usrfrExtPTMPTxUcastFrames
                     Counter32,
                 usrfrExtPTMPTxUcastOctets
                     Counter32,
                 usrfrExtPTMPTxMcastFrames
                     Counter32,
                 usrfrExtPTMPTxMcastOctets
                     Counter32,
                 usrfrExtPTMPTxDiscardedFrames
                     Counter32,
                 usrfrExtPTMPTxDiscardedOctets
                     Counter32,
                 usrfrExtPTMPRxFrames
                     Counter32,
                 usrfrExtPTMPRxOctets 
                     Counter32,
                 usrfrExtPTMPRxCongestedFrames
                     Counter32,
                 usrfrExtPTMPRxCongestedOctets
                     Counter32,
                 usrfrExtPTMPRxDiscardedFrames
                     Counter32,
                 usrfrExtPTMPRxDiscardedOctets
                     Counter32,
                 usrfrExtPTMPTxIPProtocolFrames
                     Counter32,    
                 usrfrExtPTMPRxIPProtocolFrames
                     Counter32,    
                 usrfrExtPTMPTxIPXProtocolFrames
                     Counter32,
                 usrfrExtPTMPRxIPXProtocolFrames
                     Counter32,
                 usrfrExtPTMPTxATProtocolFrames
                     Counter32,    
                 usrfrExtPTMPRxATProtocolFrames
                     Counter32,    
                 usrfrExtPTMPTxBridgedFrames
                     Counter32,    
                 usrfrExtPTMPRxBridgedFrames
                     Counter32,    
                 usrfrExtPTMPTxL2TPProtocolFrames
                     Counter32,    
                 usrfrExtPTMPRxL2TPProtocolFrames
                     Counter32,
                 usrfrExtPTMPCreationTime
                     TimeStamp,
                 usrfrExtPTMPLastTimeChange
                     TimeStamp,
                 usrfrExtPTMPRowStatus
                     RowStatus,
                 usrfrExtPTMPTrace
                     INTEGER
 
         }

         usrfrExtPTMPGroupName OBJECT-TYPE
             SYNTAX  DisplayString (SIZE (1..32))
             MAX-ACCESS  read-only
             STATUS  current
             DESCRIPTION
                "The name of the PTMP PVC Group. It is a unique
                 name used as a index to PTMP PVC Group Table."
             ::= { usrfrExtPTMPGroupEntry 1 }

         usrfrExtPTMPGroupIndex OBJECT-TYPE
             SYNTAX  Index
             MAX-ACCESS  read-only
             STATUS  current
             DESCRIPTION
                "Logical Index used by a PVC as a reference to 
                a PTMP PVC Group. This index is a unique number."
             --CONFIGURABLE
             ::= { usrfrExtPTMPGroupEntry 2 }   

         usrfrExtPTMPGroupOperStatus OBJECT-TYPE
             SYNTAX  INTEGER {
                 up       (1),  -- ready to pass packets
                 down     (2),
                 disabled (3)
             }
             MAX-ACCESS  read-only
             STATUS  current
             DESCRIPTION
                 "The current operational state of the PTMP PVC Group. The
                 disabled(3) state indicates that no data packets
                 can be passed through this PTMP PVC Group. It reflects the fact that 
                 RowStatus is set to notInService. The up(1) describes
                 a state when packets can be sent and received on the PTMP PVC Group.
                 The down(2) indicates that PTMP PVC Group is not able to operate. 
                 The up(1) and down(2) states are set up based
                 on status of all PVC participating in this Group. "
             ::= { usrfrExtPTMPGroupEntry 3 }

         usrfrExtPTMPNumberOfPVCs OBJECT-TYPE
             SYNTAX  Counter32
             MAX-ACCESS  read-only
             STATUS  current
             DESCRIPTION
                "Number of PVCs associated with this PTMP PVC
                Group."
             ::= { usrfrExtPTMPGroupEntry 4 }   

         usrfrExtPTMPTxUcastFrames OBJECT-TYPE
             SYNTAX  Counter32
             MAX-ACCESS  read-only
             STATUS  current
             DESCRIPTION
                "Number of unicast frames sent by a forwarder 
                to this PTMP PVC Group, since it was enabled."
             ::= { usrfrExtPTMPGroupEntry 5 }

         usrfrExtPTMPTxUcastOctets OBJECT-TYPE
             SYNTAX  Counter32
             MAX-ACCESS  read-only
             STATUS  current
             DESCRIPTION
                "Number of octets in unicast frames sent by a forwarder
                to this PTMP PVC Group, since it was enabled."
             ::= { usrfrExtPTMPGroupEntry 6 }   

         usrfrExtPTMPTxMcastFrames OBJECT-TYPE
             SYNTAX  Counter32
             MAX-ACCESS  read-only
             STATUS  current
             DESCRIPTION
                "Number of multicast frames sent by a forwarder 
                to this PTMP PVC Group, since it was enabled."
             ::= { usrfrExtPTMPGroupEntry 7 }   

         usrfrExtPTMPTxMcastOctets OBJECT-TYPE
             SYNTAX  Counter32
             MAX-ACCESS  read-only
             STATUS  current
             DESCRIPTION
                "Number of octets in multicast frames sent by a forwarder
                to this PTMP PVC Group, since it was enabled."
             ::= { usrfrExtPTMPGroupEntry 8 }

         usrfrExtPTMPTxDiscardedFrames OBJECT-TYPE
             SYNTAX  Counter32
             MAX-ACCESS  read-only
             STATUS  current
             DESCRIPTION
                "Number of frames discarded, which were sent by forwarder 
                to this PTMP PVC Group, since it was enabled."
             ::= { usrfrExtPTMPGroupEntry 9 }

         usrfrExtPTMPTxDiscardedOctets OBJECT-TYPE
             SYNTAX  Counter32
             MAX-ACCESS  read-only
             STATUS  current
             DESCRIPTION
                "Number of octets in a discarded frames sent by a 
                forwarder to this PTMP PVC Group, since it was enabled."
             ::= { usrfrExtPTMPGroupEntry 10 }

         usrfrExtPTMPRxFrames OBJECT-TYPE
             SYNTAX  Counter32
             MAX-ACCESS  read-only
             STATUS  current
             DESCRIPTION
                "Number of frames received from all associated PVCS
                by this PTMP PVC Group, since it was enabled."
             ::= { usrfrExtPTMPGroupEntry 11 }

         usrfrExtPTMPRxOctets OBJECT-TYPE
             SYNTAX  Counter32
             MAX-ACCESS  read-only
             STATUS  current
             DESCRIPTION
                "Number of octets received from all associated PVCS
                by this PTMP PVC Group, since it was enabled."
             ::= { usrfrExtPTMPGroupEntry 12 }

         usrfrExtPTMPRxCongestedFrames OBJECT-TYPE
             SYNTAX  Counter32
             MAX-ACCESS  read-only
             STATUS  current
             DESCRIPTION
                "Number of frames received from all associated PVCS,
                which were congested by the forwarder on attempt of
                passing them by PTMP PVC Group, since the group was enabled."
             ::= { usrfrExtPTMPGroupEntry 13 }

         usrfrExtPTMPRxCongestedOctets OBJECT-TYPE
             SYNTAX  Counter32
             MAX-ACCESS  read-only
             STATUS  current
             DESCRIPTION
                "Number of octets in frames received from all associated PVCS,
                which were congested by the forwarder on attempt of
                passing them by PTMP PVC Group, since the group was enabled."
             ::= { usrfrExtPTMPGroupEntry 14 }

         usrfrExtPTMPRxDiscardedFrames OBJECT-TYPE
             SYNTAX  Counter32
             MAX-ACCESS  read-only
             STATUS  current
             DESCRIPTION
                "Number of received frames from all associated PVCs which 
                were discarded by this PTMP PVC Group, since it was enabled."
             ::= { usrfrExtPTMPGroupEntry 15 }

         usrfrExtPTMPRxDiscardedOctets OBJECT-TYPE
             SYNTAX  Counter32
             MAX-ACCESS  read-only
             STATUS  current
             DESCRIPTION
                "Number of octets in a received frames from all associated
                PVCs which were discarded by  this PTMP PVC Group, since it 
                was enabled."
             ::= { usrfrExtPTMPGroupEntry 16 }

         usrfrExtPTMPTxIPProtocolFrames OBJECT-TYPE
             SYNTAX  Counter32
             MAX-ACCESS  read-only
             STATUS  current
             DESCRIPTION
                 "Number of IP protocol frames sent by
                  this PTMP PVC Group since it was enabled."
             ::= { usrfrExtPTMPGroupEntry 17 }

         usrfrExtPTMPRxIPProtocolFrames OBJECT-TYPE
             SYNTAX  Counter32
             MAX-ACCESS  read-only
             STATUS  current
             DESCRIPTION
                 "Number of IP protocol frames received by
                  this PTMP PVC Group since it was enabled."
             ::= { usrfrExtPTMPGroupEntry 18 }

         usrfrExtPTMPTxIPXProtocolFrames OBJECT-TYPE
             SYNTAX  Counter32
             MAX-ACCESS  read-only
             STATUS  current
             DESCRIPTION
                 "Number of IPX protocol frames sent by
                  this PTMP PVC Group since it was enabled."
             ::= { usrfrExtPTMPGroupEntry 19 }

         usrfrExtPTMPRxIPXProtocolFrames OBJECT-TYPE
             SYNTAX  Counter32
             MAX-ACCESS  read-only
             STATUS  current
             DESCRIPTION
                 "Number of IPX protocol frames received by
                  this PTMP PVC Group since it was enabled."
             ::= { usrfrExtPTMPGroupEntry 20 }

         usrfrExtPTMPTxATProtocolFrames OBJECT-TYPE
             SYNTAX  Counter32
             MAX-ACCESS  read-only
             STATUS  current
             DESCRIPTION
                 "Number of AppleTalk protocol frames sent by
                  this PTMP PVC Group since it was enabled."
             ::= { usrfrExtPTMPGroupEntry 21 }

         usrfrExtPTMPRxATProtocolFrames OBJECT-TYPE
             SYNTAX  Counter32
             MAX-ACCESS  read-only
             STATUS  current
             DESCRIPTION
                 "Number of AppleTalk protocol frames received by
                  this PTMP PVC Group since it was enabled."
             ::= { usrfrExtPTMPGroupEntry 22 }

         usrfrExtPTMPTxBridgedFrames OBJECT-TYPE
             SYNTAX  Counter32
             MAX-ACCESS  read-only
             STATUS  current
             DESCRIPTION
                 "Number of Bridged frames sent by
                  this PTMP PVC Group since it was enabled."
             ::= { usrfrExtPTMPGroupEntry 23 }

         usrfrExtPTMPRxBridgedFrames OBJECT-TYPE
             SYNTAX  Counter32
             MAX-ACCESS  read-only
             STATUS  current
             DESCRIPTION
                 "Number of Bridged frames received by
                  this PTMP PVC Group since it was enabled."
             ::= { usrfrExtPTMPGroupEntry 24 }

         usrfrExtPTMPTxL2TPProtocolFrames OBJECT-TYPE
             SYNTAX  Counter32
             MAX-ACCESS  read-only
             STATUS  current
             DESCRIPTION
                 "Number of L2TP Protocol frames sent by
                  this PTMP PVC Group since it was enabled."
             ::= { usrfrExtPTMPGroupEntry 25 }

         usrfrExtPTMPRxL2TPProtocolFrames OBJECT-TYPE
             SYNTAX  Counter32
             MAX-ACCESS  read-only
             STATUS  current
             DESCRIPTION
                 "Number of L2TP Protocol frames received by
                  this PTMP PVC Group since it was enabled."
             ::= { usrfrExtPTMPGroupEntry 26 }

         usrfrExtPTMPCreationTime OBJECT-TYPE
             SYNTAX  TimeStamp
             MAX-ACCESS  read-only
             STATUS  current
             DESCRIPTION
                 "The value of sysUpTime when this PTMP PVC Group was created."
             ::= { usrfrExtPTMPGroupEntry 27 }
 
 
         usrfrExtPTMPLastTimeChange OBJECT-TYPE
             SYNTAX  TimeStamp
             MAX-ACCESS  read-only
             STATUS  current
             DESCRIPTION
                 "The value of sysUpTime when last there was a change
                  in this PTMP PVC Group state."
             ::= { usrfrExtPTMPGroupEntry 28 }

         usrfrExtPTMPRowStatus OBJECT-TYPE
             SYNTAX  RowStatus
             MAX-ACCESS  read-write
             STATUS  current
             DESCRIPTION
                "This object is used to create a new row or destroy or modify an
                existing row in a manner described in the definition of the
                RowStatus textual convention."
             --CONFIGURABLE
             ::= { usrfrExtPTMPGroupEntry 29 }

         usrfrExtPTMPTrace OBJECT-TYPE
             SYNTAX  INTEGER {
                 on  (1),
                 off (2)
             }
             MAX-ACCESS  read-write
             STATUS  current
             DESCRIPTION
                 "This indicates if the Frame Relay data frames trace 
                 information will be displayed on the console for this
                 PTMP PVC Group."
             DEFVAL { 2 }
             --CONFIGURABLE
             ::= { usrfrExtPTMPGroupEntry 30 }



     usrfrExtPTMPGroupStatusChange NOTIFICATION-TYPE
         OBJECTS  { usrfrExtPTMPGroupOperStatus }
         STATUS   current

         DESCRIPTION
         " This trap indicates that the indicated PTMP PVC Group
         has changed its state. It has either been created or invalidated,
         or has toggled between the active and inactive states. " 
         
         ::= { usrfrExtTraps 2 }

     END

     FRAME-RELAY-DTE-MIB DEFINITIONS ::= BEGIN

     IMPORTS
                 MODULE-IDENTITY, OBJECT-TYPE, Counter32,
                 Integer32, NOTIFICATION-TYPE             FROM SNMPv2-SMI
                 TEXTUAL-CONVENTION, RowStatus, TimeStamp FROM SNMPv2-TC
                 MODULE-COMPLIANCE, OBJECT-GROUP,
                 NOTIFICATION-GROUP                       FROM SNMPv2-CONF
                 transmission                             FROM RFC1213-MIB
--                InterfaceIndex                           FROM IF-MIB
                 InterfaceIndex                           FROM USR-DEFINITIONS-MIB; 

     --  Frame Relay DTE MIB

     frameRelayDTE MODULE-IDENTITY
         LAST-UPDATED "9705010229Z" -- Thu May  1 02:29:46 PDT 1997
         ORGANIZATION "IETF IPLPDN Working Group"
         CONTACT-INFO
            "       Caralyn Brown
            Postal: Cadia Networks, Inc.
                    1 Corporate Drive
                    Andover, Massachusetts  01810
            Tel:    +1 508 689 2400 x133
            E-Mail: cbrown@cadia.com

                    Fred Baker
            Postal: Cisco Systems
                    519 Lado Drive
                    Santa Barbara, California 93111
            Tel:    +1 408 526 425
            E-Mail: fred@cisco.com"
         DESCRIPTION
            "The MIB module to describe the use of a Frame Relay
            interface by a DTE."
--         REVISION "9705010229Z"
--         DESCRIPTION
--            "Converted from SMIv1 to SMIv2. (Thus, indices are
--            read-only rather than being not-accessible.) Added
--            objects and made clarifications based on implementation
--            experience."
--         REVISION "9204010000Z"
--         DESCRIPTION
--            "Published as RFC 1315, the initial version of this MIB
--            module." 
         ::= { transmission 32 }


     --
     --      the range of a Data Link Connection Identifier
     --
     DLCI ::= TEXTUAL-CONVENTION
         STATUS      current
         DESCRIPTION
            "The range of DLCI values.  Note that this varies by
            interface configuration; normally, interfaces may use
            0..1023, but may be configured to use ranges as large
            as 0..2^23."
         SYNTAX      Integer32(0..8388607)


     --
     --  Data Link Connection Management Interface
     --      The variables that configure the DLC Management Interface.

     frDlcmiTable OBJECT-TYPE
         SYNTAX   SEQUENCE OF FrDlcmiEntry
         MAX-ACCESS   not-accessible
         STATUS   current
         DESCRIPTION
            "The Parameters for the Data Link Connection Management
            Interface for the frame relay service on this
            interface."
         REFERENCE
            "American National Standard T1.617-1991, Annex D"
         ::= { frameRelayDTE 1 }

     frDlcmiEntry OBJECT-TYPE
         SYNTAX   FrDlcmiEntry
         MAX-ACCESS   not-accessible
         STATUS   current
         DESCRIPTION
            "The Parameters for a particular Data Link Connection
            Management Interface."
         INDEX { frDlcmiIfIndex }
         ::= { frDlcmiTable 1 }


     FrDlcmiEntry ::=
         SEQUENCE {
             frDlcmiIfIndex                  InterfaceIndex,
             frDlcmiState                    INTEGER,
             frDlcmiAddress                  INTEGER,
             frDlcmiAddressLen               INTEGER,
             frDlcmiPollingInterval          Integer32,
             frDlcmiFullEnquiryInterval      Integer32,
             frDlcmiErrorThreshold           Integer32,
             frDlcmiMonitoredEvents          Integer32,
             frDlcmiMaxSupportedVCs          DLCI,
             frDlcmiMulticast                INTEGER,
             frDlcmiStatus                   INTEGER,
             frDlcmiRowStatus                RowStatus
     }


     frDlcmiIfIndex OBJECT-TYPE

         SYNTAX   InterfaceIndex
         MAX-ACCESS   read-only
         STATUS   current
         DESCRIPTION
            "The ifIndex value of the corresponding ifEntry."
         ::= { frDlcmiEntry 1 }


     frDlcmiState OBJECT-TYPE
         SYNTAX INTEGER      {
             noLmiConfigured (1),
             lmiRev1         (2),
             ansiT1617D      (3),  -- ANSI T1.617 Annex D
             ansiT1617B      (4),  -- ANSI T1.617 Annex B
             itut933A        (5),  -- CCITT Q933 Annex A
             ansiT1617D1994  (6)   -- ANSI T1.617a-1994 Annex D
         }
         MAX-ACCESS   read-create
         STATUS   current
         DESCRIPTION
            "This variable states which Data Link Connection
            Management scheme is active (and by implication, what
            DLCI it uses) on the Frame Relay interface."
         REFERENCE
            "American National Standard T1.617-1991, American
            National Standard T1.617a-1994, ITU-T Recommendation
            Q.933 (03/93)."
         --CONFIGURABLE
         ::= { frDlcmiEntry 2 }


     frDlcmiAddress OBJECT-TYPE
         SYNTAX      INTEGER {
                     q921           (1),  -- 13 bit DLCI
                     q922March90    (2),  -- 11 bit DLCI
                     q922November90 (3),  -- 10 bit DLCI
                     q922           (4)   -- Final Standard
         }
         MAX-ACCESS  read-create
         STATUS  current
         DESCRIPTION
            "This variable states which address format is in use on
            the Frame Relay interface."
         ::= { frDlcmiEntry 3 }


     frDlcmiAddressLen OBJECT-TYPE
         SYNTAX  INTEGER     {
                 twoOctets (2),
                 threeOctets (3),
                 fourOctets (4)
         }
         MAX-ACCESS  read-create
         STATUS  current
         DESCRIPTION
            "This variable states the address length in octets.  In
            the case of Q922 format, the length indicates the
            entire length of the address including the control
            portion."
         ::= { frDlcmiEntry 4 }


     frDlcmiPollingInterval OBJECT-TYPE
         SYNTAX   Integer32 (5..30)
         UNITS    "seconds"
         MAX-ACCESS   read-create
         STATUS   current
         DESCRIPTION
            "This is the number of seconds between successive
            status enquiry messages."
         REFERENCE
            "American National Standard T1.617-1991, Section D.7
            Timer T391."
         DEFVAL { 10 }
         --CONFIGURABLE
         ::= { frDlcmiEntry 5 }


     frDlcmiFullEnquiryInterval OBJECT-TYPE
         SYNTAX   Integer32 (1..255)
         MAX-ACCESS   read-create
         STATUS   current
         DESCRIPTION
            "Number of status enquiry intervals that pass before
            issuance of a full status enquiry message."
         REFERENCE
            "American National Standard T1.617-1991, Section D.7
            Counter N391."
         DEFVAL { 6 }
         --CONFIGURABLE
         ::= { frDlcmiEntry 6 }


     frDlcmiErrorThreshold OBJECT-TYPE
         SYNTAX   Integer32 (1..10)
         MAX-ACCESS   read-create
         STATUS   current
         DESCRIPTION
            "This is the maximum number of unanswered Status
            Enquiries the equipment shall accept before declaring
            the interface down."
         REFERENCE
            "American National Standard T1.617-1991, Section D.5.1
            Counter N392."
         DEFVAL { 3 }
         --CONFIGURABLE
         ::= { frDlcmiEntry 7 }


     frDlcmiMonitoredEvents OBJECT-TYPE
         SYNTAX   Integer32 (1..10)
         MAX-ACCESS   read-create
         STATUS   current
         DESCRIPTION
            "This is the number of status polling intervals over
            which the error threshold is counted.  For example, if
            within 'MonitoredEvents' number of events the station
            receives 'ErrorThreshold' number of errors, the
            interface is marked as down."
         REFERENCE
            "American National Standard T1.617-1991, Section D.5.2
            Counter N393."
         DEFVAL { 4 }
         --CONFIGURABLE
         ::= { frDlcmiEntry 8 }


     frDlcmiMaxSupportedVCs OBJECT-TYPE
         SYNTAX   DLCI
         MAX-ACCESS   read-create
         STATUS   current
         DESCRIPTION
            "The maximum number of Virtual Circuits allowed for
            this interface.  Usually dictated by the Frame Relay
            network.

            In response to a SET, if a value less than zero or
            higher than the agent's maximal capability is
            configured, the agent should respond badValue"
         --CONFIGURABLE
         ::= { frDlcmiEntry 9 }


     frDlcmiMulticast OBJECT-TYPE
         SYNTAX   INTEGER    {
                     nonBroadcast (1),
                     broadcast (2)
                     }
         MAX-ACCESS   read-create
         STATUS   current
         DESCRIPTION
            "This indicates whether the Frame Relay interface is
            using a multicast service."
         --CONFIGURABLE
         ::= { frDlcmiEntry 10 }



     frDlcmiStatus OBJECT-TYPE
         SYNTAX   INTEGER    {
                     running      (1),    -- init complete, system running
                     fault        (2),    -- error threshold exceeded
                     initializing (3)     -- system start up
                     }
         MAX-ACCESS   read-only
         STATUS   current
         DESCRIPTION
            "This indicates the status of the Frame Relay interface
            as determined by the performance of the dlcmi.  If no
            dlcmi is running, the Frame Relay interface will stay
            in the running state indefinitely."
         ::= { frDlcmiEntry 11 }


     frDlcmiRowStatus OBJECT-TYPE
         SYNTAX   RowStatus
         MAX-ACCESS   read-create
         STATUS   current
         DESCRIPTION
            "SNMP Version 2 Row Status Variable.  Writable objects
            in the table may be written in any RowStatus state."
         --CONFIGURABLE
         ::= { frDlcmiEntry 12 }


     --
     -- A Frame Relay service is a multiplexing service.  Data
     -- Link Connection Identifiers enumerate virtual circuits
     -- (permanent or dynamic) which are layered onto the underlying
     -- circuit, represented by ifEntry.  Therefore, each of the entries
     -- in the Standard MIB's Interface Table with an IfType of
     -- Frame Relay represents a Q.922 interface.  Zero or more
     -- virtual circuits are layered onto this interface and provide
     -- interconnection with various remote destinations.
     -- Each such virtual circuit is represented by an entry in the
     -- circuit table.  The management virtual circuit (i.e. DLCI 0)
     -- is a virtual circuit by this definition and will be represented
     -- with an entry in the circuit table.

     --   Circuit Table

     -- The table describing the use of the DLCIs attached to
     -- each Frame Relay Interface.

     frCircuitTable OBJECT-TYPE
         SYNTAX   SEQUENCE OF FrCircuitEntry
         MAX-ACCESS   not-accessible
         STATUS   current
         DESCRIPTION
            "A table containing information about specific Data
            Link Connections (DLC) or virtual circuits."
         ::= { frameRelayDTE 2 }


     frCircuitEntry OBJECT-TYPE
         SYNTAX   FrCircuitEntry
         MAX-ACCESS   not-accessible
         STATUS   current
         DESCRIPTION
            "The information regarding a single Data Link
            Connection.  Discontinuities in the counters contained
            in this table are indicated by the value in
            frCircuitCreationTime."
         INDEX { frCircuitIfIndex, frCircuitDlci }
         ::= { frCircuitTable 1 }


     FrCircuitEntry ::=
         SEQUENCE {
             frCircuitIfIndex                InterfaceIndex,
             frCircuitDlci                   DLCI,
             frCircuitState                  INTEGER,
             frCircuitReceivedFECNs          Counter32,
             frCircuitReceivedBECNs          Counter32,
             frCircuitSentFrames             Counter32,
             frCircuitSentOctets             Counter32,
             frCircuitReceivedFrames         Counter32,
             frCircuitReceivedOctets         Counter32,
             frCircuitCreationTime           TimeStamp,
             frCircuitLastTimeChange         TimeStamp,
             frCircuitCommittedBurst         Integer32,
             frCircuitExcessBurst            Integer32,
             frCircuitThroughput             Integer32,
             frCircuitMulticast              INTEGER,
             frCircuitType                   INTEGER,
             frCircuitDiscards               Counter32,
             frCircuitReceivedDEs            Counter32,
             frCircuitSentDEs                Counter32,
             frCircuitLogicalIfIndex         InterfaceIndex,
             frCircuitRowStatus              RowStatus
     }


     frCircuitIfIndex OBJECT-TYPE
         SYNTAX   InterfaceIndex
         MAX-ACCESS   read-only
         STATUS   current
         DESCRIPTION
            "The ifIndex Value of the ifEntry this virtual circuit
            is layered onto."
         ::= { frCircuitEntry 1 }


     frCircuitDlci OBJECT-TYPE
         SYNTAX   DLCI
         MAX-ACCESS   read-only
         STATUS   current
         DESCRIPTION
            "The Data Link Connection Identifier for this virtual
            circuit."
         REFERENCE
            "American National Standard T1.618-1991, Section 3.3.6"
         ::= { frCircuitEntry 2 }


     frCircuitState OBJECT-TYPE
         SYNTAX   INTEGER    {

                     invalid (1),
                     active (2),
                     inactive (3)
                  }
         MAX-ACCESS   read-create
         STATUS   current
         DESCRIPTION
            "Indicates whether the particular virtual circuit is
            operational.  In the absence of a Data Link Connection
            Management Interface, virtual circuit entries (rows)
            may be created by setting virtual circuit state to
            'active', or deleted by changing Circuit state to
            'invalid'.

            Whether or not the row actually disappears is left to
            the implementation, so this object may actually read as
            'invalid' for some arbitrary length of time.  It is
            also legal to set the state of a virtual circuit to
            'inactive' to temporarily disable a given circuit.

            The use of 'invalid' is deprecated in this SNMP Version
            2 MIB, in favor of frCircuitRowStatus."
         DEFVAL { active }
         ::= { frCircuitEntry 3 }


     frCircuitReceivedFECNs OBJECT-TYPE
         SYNTAX   Counter32
         MAX-ACCESS   read-only
         STATUS   current
         DESCRIPTION
            "Number of frames received from the network indicating
            forward congestion since the virtual circuit was
            created.  This occurs when the remote DTE sets the FECN
            flag, or when a switch in the network enqueues the
            frame to a trunk whose transmission queue is
            congested."
         REFERENCE
            "American National Standard T1.618-1991, Section 3.3.3"
         ::= { frCircuitEntry 4 }


     frCircuitReceivedBECNs OBJECT-TYPE
         SYNTAX   Counter32
         MAX-ACCESS   read-only


         STATUS   current
         DESCRIPTION
            "Number of frames received from the network indicating
            backward congestion since the virtual circuit was
            created.  This occurs when the remote DTE sets the BECN
            flag, or when a switch in the network receives the
            frame from a trunk whose transmission queue is
            congested."
         REFERENCE
            "American National Standard T1.618-1991, Section 3.3.4"
         ::= { frCircuitEntry 5 }


     frCircuitSentFrames OBJECT-TYPE
         SYNTAX   Counter32
         MAX-ACCESS   read-only
         STATUS   current
         DESCRIPTION
            "The number of frames sent from this virtual circuit
            since it was created."
         ::= { frCircuitEntry 6 }


     frCircuitSentOctets OBJECT-TYPE
         SYNTAX   Counter32
         MAX-ACCESS   read-only
         STATUS   current
         DESCRIPTION
            "The number of octets sent from this virtual circuit
            since it was created.  Octets counted are the full
            frame relay header and the payload, but do not include
            the flag characters or CRC."
         ::= { frCircuitEntry 7 }


     frCircuitReceivedFrames OBJECT-TYPE
         SYNTAX   Counter32
         MAX-ACCESS   read-only
         STATUS   current
         DESCRIPTION
            "Number of frames received over this virtual circuit
            since it was created."
         ::= { frCircuitEntry 8 }


     frCircuitReceivedOctets OBJECT-TYPE
         SYNTAX   Counter32
         MAX-ACCESS   read-only
         STATUS   current
         DESCRIPTION
            "Number of octets received over this virtual circuit
            since it was created.  Octets counted include the full
            frame relay header, but do not include the flag
            characters or the CRC."
         ::= { frCircuitEntry 9 }


     frCircuitCreationTime OBJECT-TYPE
         SYNTAX   TimeStamp
         MAX-ACCESS   read-only
         STATUS   current
         DESCRIPTION
            "The value of sysUpTime when the virtual circuit was
            created, whether by the Data Link Connection Management
            Interface or by a SetRequest."
         ::= { frCircuitEntry 10 }


     frCircuitLastTimeChange OBJECT-TYPE
         SYNTAX   TimeStamp
         MAX-ACCESS   read-only
         STATUS   current
         DESCRIPTION
            "The value of sysUpTime when last there was a change in
            the virtual circuit state"
         ::= { frCircuitEntry 11 }


     frCircuitCommittedBurst OBJECT-TYPE
         SYNTAX   Integer32(0..2147483647)
         MAX-ACCESS   read-create
         STATUS   current
         DESCRIPTION
            "This variable indicates the maximum amount of data, in
            bits, that the network agrees to transfer under normal
            conditions, during the measurement interval."
         REFERENCE
            "American National Standard T1.617-1991, Section
            6.5.19"
         DEFVAL   { 0 }  -- the default indicates no commitment
         ::= { frCircuitEntry 12 }


     frCircuitExcessBurst OBJECT-TYPE
         SYNTAX   Integer32(0..2147483647)
         MAX-ACCESS   read-create
         STATUS   current
         DESCRIPTION
            "This variable indicates the maximum amount of
            uncommitted data bits that the network will attempt to
            deliver over the measurement interval.

            By default, if not configured when creating the entry,
            the Excess Information Burst Size is set to the value
            of ifSpeed."
         REFERENCE
            "American National Standard T1.617-1991, Section
            6.5.19"
         --CONFIGURABLE
         ::= { frCircuitEntry 13 }


     frCircuitThroughput OBJECT-TYPE
         SYNTAX   Integer32(0..2147483647)
         MAX-ACCESS   read-create
         STATUS   current
         DESCRIPTION
            "Throughput is the average number of 'Frame Relay
            Information Field' bits transferred per second across a
            user network interface in one direction, measured over
            the measurement interval.

            If the configured committed burst rate and throughput
            are both non-zero, the measurement interval, T, is
                T=frCircuitCommittedBurst/frCircuitThroughput.

            If the configured committed burst rate and throughput
            are both zero, the measurement interval, T, is
                       T=frCircuitExcessBurst/ifSpeed."
         REFERENCE
            "American National Standard T1.617-1991, Section
            6.5.19"
         DEFVAL {0}  -- the default value of Throughput is
                     -- "no commitment".
         --CONFIGURABLE
         ::= { frCircuitEntry 14 }


     frCircuitMulticast OBJECT-TYPE
         SYNTAX   INTEGER    {
                     unicast   (1),
                     oneWay    (2),
                     twoWay    (3),
                     nWay      (4)
                     }
         MAX-ACCESS   read-create
         STATUS   current
         DESCRIPTION
            "This indicates whether this VC is used as a unicast VC
            (i.e. not multicast) or the type of multicast service
            subscribed to"
         REFERENCE
            "Frame Relay PVC Multicast Service and Protocol
            Description Implementation: FRF.7 Frame Relay Forum
            Technical Committe October 21, 1994"
         DEFVAL {unicast}
            -- the default value of frCircuitMulticast is
            -- "unicast" (not a multicast VC).
         --CONFIGURABLE
         ::= { frCircuitEntry 15 }


     frCircuitType OBJECT-TYPE
         SYNTAX   INTEGER    {
                     static  (1),
                     dynamic (2)
                  }
         MAX-ACCESS   read-only
         STATUS   current
         DESCRIPTION
            "Indication of whether the VC was manually created
            (static), or dynamically created (dynamic) via the data
            link control management interface."
         ::= { frCircuitEntry 16 }


     frCircuitDiscards OBJECT-TYPE
         SYNTAX   Counter32
         MAX-ACCESS   read-only
         STATUS   current
         DESCRIPTION
            "The number of inbound frames dropped because of format
            errors, or because the VC is inactive."
         ::= { frCircuitEntry 17 }


     frCircuitReceivedDEs OBJECT-TYPE
         SYNTAX   Counter32
         MAX-ACCESS   read-only
         STATUS   current
         DESCRIPTION
            "Number of frames received from the network indicating
            that they were eligible for discard since the virtual
            circuit was created.  This occurs when the remote DTE
            sets the DE flag, or when in remote DTE's switch
            detects that the frame was received as Excess Burst
            data."
         REFERENCE
            "American National Standard T1.618-1991, Section 3.3.4"
         ::= { frCircuitEntry 18 }


     frCircuitSentDEs OBJECT-TYPE
         SYNTAX   Counter32
         MAX-ACCESS   read-only
         STATUS   current
         DESCRIPTION
            "Number of frames sent to the network indicating that
            they were eligible for discard since the virtual
            circuit was created.   This occurs when the local DTE
            sets the DE flag, indicating that during Network
            congestion situations those frames should be discarded
            in preference of other frames sent without the DE bit
            set."
         REFERENCE
            "American National  Standard  T1.618-1991, Section
            3.3.4"
        ::= { frCircuitEntry 19 }

     frCircuitLogicalIfIndex OBJECT-TYPE
         SYNTAX  InterfaceIndex
         MAX-ACCESS read-create
         STATUS  current
         DESCRIPTION
            "Normally the same value as frDlcmiIfIndex, but
            different when an implementation associates a virtual
            ifEntry with a DLC or set of DLCs in order to associate
            higher layer objects such as the ipAddrEntry with a
            subset of the virtual circuits on a Frame Relay
            interface. The type of such ifEntries is defined by the
            higher layer object; for example, if PPP/Frame Relay is
            implemented, the ifType of this ifEntry would be PPP.
            If it is not so defined, as would be the case with an
            ipAddrEntry, it should be of type Other."
        --CONFIGURABLE
        ::= { frCircuitEntry 20 }

     frCircuitRowStatus OBJECT-TYPE
         SYNTAX   RowStatus
         MAX-ACCESS   read-create
         STATUS   current
         DESCRIPTION
            "This object is used to create a new row or modify or
            destroy an existing row in the manner described in the
            definition of the RowStatus textual convention.
            Writable objects in the table may be written in any
            RowStatus state."
         --CONFIGURABLE
         ::= { frCircuitEntry 21 }


     --
     --  Error Table

     -- The table describing errors encountered on each Frame
     -- Relay Interface.

     frErrTable OBJECT-TYPE
         SYNTAX   SEQUENCE OF FrErrEntry
         MAX-ACCESS   not-accessible
         STATUS   current
         DESCRIPTION
            "A table containing information about Errors on the
            Frame Relay interface.  Discontinuities in the counters
            contained in this table are the same as apply to the
            ifEntry associated with the Interface."
         ::= { frameRelayDTE 3 }

     frErrEntry OBJECT-TYPE
         SYNTAX   FrErrEntry
         MAX-ACCESS   not-accessible
         STATUS   current
         DESCRIPTION
            "The error information for a single frame relay
            interface."
         INDEX { frErrIfIndex }
         ::= { frErrTable 1 }


     FrErrEntry ::=
         SEQUENCE {
             frErrIfIndex            InterfaceIndex,
             frErrType               INTEGER,
             frErrData               OCTET STRING,
             frErrTime               TimeStamp,
             frErrFaults             Counter32,
             frErrFaultTime          TimeStamp
     }


     frErrIfIndex OBJECT-TYPE
         SYNTAX   InterfaceIndex
         MAX-ACCESS   read-only
         STATUS   current
         DESCRIPTION
            "The ifIndex Value of the corresponding ifEntry."
         ::= { frErrEntry 1 }


         frErrType OBJECT-TYPE
             SYNTAX   INTEGER    {
                         unknownError(1),
                         receiveShort(2),
                         receiveLong(3),
                         illegalAddress(4),
                         unknownAddress(5),
                         dlcmiProtoErr(6),
                         dlcmiUnknownIE(7),
                         dlcmiSequenceErr(8),
                         dlcmiUnknownRpt(9),
                         noErrorSinceReset(10)
                      }
         MAX-ACCESS   read-only
         STATUS   current
         DESCRIPTION
     "The type of error that was last seen  on  this interface:

     receiveShort: frame was not long enough to allow
             demultiplexing - the address field was incomplete,
             or for virtual circuits using Multiprotocol over
             Frame Relay, the protocol identifier was missing
             or incomplete.

     receiveLong: frame exceeded maximum length configured for this
                  interface.

     illegalAddress: address field did not match configured format.

     unknownAddress: frame received on a virtual circuit which was not
                     active or administratively disabled.

     dlcmiProtoErr: unspecified error occurred when attempting to
                    interpret link maintenance frame.

     dlcmiUnknownIE: link maintenance frame contained an Information
                     Element type which is not valid for the
                     configured link maintenance protocol.

     dlcmiSequenceErr: link maintenance frame contained a sequence
                       number other than the expected value.

     dlcmiUnknownRpt: link maintenance frame contained a Report Type
                      Information Element whose value was not valid
                      for the configured link maintenance protocol.

     noErrorSinceReset: no errors have been detected since the last
                        cold start or warm start."
         ::= { frErrEntry 2 }


     frErrData OBJECT-TYPE
         SYNTAX   OCTET STRING (SIZE(1..1600))
         MAX-ACCESS   read-only
         STATUS   current
         DESCRIPTION
            "An octet string containing as much of the error packet
            as possible.  As a minimum, it must contain the Q.922
            Address or as much as was delivered.  It is desirable
            to include all header and demultiplexing information."
         ::= { frErrEntry 3 }


     frErrTime OBJECT-TYPE
         SYNTAX   TimeStamp
         MAX-ACCESS   read-only
         STATUS   current
         DESCRIPTION
            "The value of sysUpTime at which the error was
            detected."
         ::= { frErrEntry 4 }


     frErrFaults OBJECT-TYPE
         SYNTAX   Counter32
         MAX-ACCESS   read-only
         STATUS   current
         DESCRIPTION
            "The number of times the interface has gone down since
            it was initialized."
         ::= { frErrEntry 5 }


     frErrFaultTime OBJECT-TYPE
         SYNTAX   TimeStamp
         MAX-ACCESS   read-only
         STATUS   current
         DESCRIPTION
            "The value of sysUpTime at the time when the interface
            was taken down due to excessive errors.  Excessive
            errors is defined as the time when a DLCMI exceeds the
            frDlcmiErrorThreshold number of errors within
            frDlcmiMonitoredEvents. See FrDlcmiEntry for further
            details."
         ::= { frErrEntry 6 }


     --

     -- Frame Relay Trap Control

     frameRelayTrapControl OBJECT IDENTIFIER ::= { frameRelayDTE 4 }

     -- the following highly unusual OID is as it is for compatibility
     -- with RFC 1315, the SNMP V1 predecessor of this document.
     frameRelayTraps OBJECT IDENTIFIER ::= { frameRelayDTE 0 }

     frTrapState OBJECT-TYPE
         SYNTAX  INTEGER     { enabled(1), disabled(2) }
         MAX-ACCESS   read-write
         STATUS   current
         DESCRIPTION
            "This variable indicates whether the system produces
            the frDLCIStatusChange trap."
         DEFVAL { disabled }
         --CONFIGURABLE
         ::= { frameRelayTrapControl 1 }

     frTrapMaxRate OBJECT-TYPE
         SYNTAX  Integer32 (0..3600000)
         MAX-ACCESS   read-write
         STATUS   current
         DESCRIPTION
            "This variable indicates the number of milliseconds
            that must elapse between trap emissions.  If events
            occur more rapidly, the impementation may simply fail
            to trap, or may queue traps until an appropriate time."
         DEFVAL { 0 }        -- no minimum elapsed period is specified
         --CONFIGURABLE
         ::= { frameRelayTrapControl 2 }



     --  Data Link Connection Management Interface Related Traps

     frDLCIStatusChange NOTIFICATION-TYPE
         OBJECTS  { frCircuitState }
         STATUS      current


         DESCRIPTION
            "This trap indicates that the indicated Virtual Circuit
            has changed state.  It has either been created or
            invalidated, or has toggled between the active and
            inactive states.  If, however, the reason for the state
            change is due to the DLCMI going down, per-DLCI traps
            should not be generated."
     ::= { frameRelayTraps 1 }
     -- conformance information

     frConformance OBJECT IDENTIFIER ::= { frameRelayDTE 6 }

     frGroups      OBJECT IDENTIFIER ::= { frConformance 1 }
     frCompliances OBJECT IDENTIFIER ::= { frConformance 2 }

     -- compliance statements
     frCompliance MODULE-COMPLIANCE
         STATUS  current
         DESCRIPTION
            "The compliance statement "
         MODULE  -- this module
         MANDATORY-GROUPS { frPortGroup, frCircuitGroup }

         GROUP       frErrGroup
         DESCRIPTION
            "This optional group is used for debugging Frame Relay
            Systems."

         GROUP       frTrapGroup
         DESCRIPTION
            "This optional group is used for the management of
            asynchronous notifications by Frame Relay Systems."

         GROUP       frNotificationGroup
         DESCRIPTION
            "This optional group defines the asynchronous
            notifications generated by Frame Relay Systems."

         OBJECT      frDlcmiRowStatus
         MIN-ACCESS  read-only
         DESCRIPTION
            "Row creation is not required for the frDlcmiTable."

         OBJECT      frCircuitRowStatus

         MIN-ACCESS  read-only
         DESCRIPTION
            "Row creation is not required for the frCircuitTable."

         ::= { frCompliances 1 }

     frCompliance0 MODULE-COMPLIANCE
         STATUS  current
         DESCRIPTION
            "The compliance statement for objects and the trap
            defined in RFC 1315."
         MODULE  -- this module
         MANDATORY-GROUPS { frPortGroup0, frCircuitGroup0 }

         GROUP       frErrGroup0
         DESCRIPTION
            "This optional group is used for debugging Frame Relay
            Systems."

         GROUP       frTrapGroup0
         DESCRIPTION
            "This optional group is used for the management of
            asynchronous notifications by Frame Relay Systems."

         GROUP       frNotificationGroup
         DESCRIPTION
            "This optional group defines the asynchronous
            notifications generated by Frame Relay Systems."

         ::= { frCompliances 2 }

     -- units of conformance

     frPortGroup    OBJECT-GROUP
         OBJECTS {
                   frDlcmiIfIndex, frDlcmiState, frDlcmiAddress,
                   frDlcmiAddressLen, frDlcmiPollingInterval,
                   frDlcmiFullEnquiryInterval, frDlcmiErrorThreshold,
                   frDlcmiMonitoredEvents, frDlcmiMaxSupportedVCs,
                   frDlcmiMulticast, frDlcmiStatus, frDlcmiRowStatus
                }
         STATUS  current
         DESCRIPTION
            "The objects necessary to control the Link Management
            Interface for a Frame Relay Interface as well as
            maintain the error statistics on this interface."
         ::= { frGroups 1 }

     frCircuitGroup    OBJECT-GROUP
         OBJECTS {
                   frCircuitIfIndex, frCircuitDlci, frCircuitState,
                   frCircuitReceivedFECNs, frCircuitReceivedBECNs,
                   frCircuitSentFrames, frCircuitSentOctets,
                   frCircuitReceivedFrames, frCircuitReceivedOctets,
                   frCircuitCreationTime, frCircuitLastTimeChange,
                   frCircuitCommittedBurst, frCircuitExcessBurst,
                   frCircuitThroughput, frCircuitMulticast,
                   frCircuitType, frCircuitDiscards,
                   frCircuitReceivedDEs, frCircuitSentDEs,
                   frCircuitLogicalIfIndex, frCircuitRowStatus
                 }
         STATUS  current
         DESCRIPTION
            "The objects necessary to control the Virtual Circuits
            layered onto a Frame Relay Interface."
         ::= { frGroups 2 }


     frTrapGroup    OBJECT-GROUP
         OBJECTS { frTrapState, frTrapMaxRate }
         STATUS  current
         DESCRIPTION
            "The objects necessary to control a Frame Relay
            Interface's notification messages."
         ::= { frGroups 3 }

     frErrGroup    OBJECT-GROUP
         OBJECTS {
                   frErrIfIndex, frErrType, frErrData, frErrTime,
                   frErrFaults, frErrFaultTime
                }
         STATUS  current
         DESCRIPTION
            "Objects designed to assist in debugging Frame Relay
            Interfaces."
         ::= { frGroups 4 }

     frNotificationGroup NOTIFICATION-GROUP
         NOTIFICATIONS { frDLCIStatusChange }
         STATUS  current
         DESCRIPTION
            "Traps which may be used to enhance event driven
            management of the interface."
         ::= { frGroups 5 }

     frPortGroup0    OBJECT-GROUP
         OBJECTS {
                   frDlcmiIfIndex, frDlcmiState, frDlcmiAddress,
                   frDlcmiAddressLen, frDlcmiPollingInterval,
                   frDlcmiFullEnquiryInterval, frDlcmiErrorThreshold,
                   frDlcmiMonitoredEvents, frDlcmiMaxSupportedVCs,
                   frDlcmiMulticast
                }
         STATUS  current
         DESCRIPTION
            "The objects necessary to control the Link Management
            Interface for a Frame Relay Interface as well as
            maintain the error statistics on this interface from
            RFC 1315."
         ::= { frGroups 6 }

     frCircuitGroup0    OBJECT-GROUP
         OBJECTS {
                   frCircuitIfIndex, frCircuitDlci, frCircuitState,
                   frCircuitReceivedFECNs, frCircuitReceivedBECNs,
                   frCircuitSentFrames, frCircuitSentOctets,
                   frCircuitReceivedFrames, frCircuitReceivedOctets,
                   frCircuitCreationTime, frCircuitLastTimeChange,
                   frCircuitCommittedBurst, frCircuitExcessBurst,
                   frCircuitThroughput
                 }
         STATUS  current
         DESCRIPTION
            "The objects necessary to control the Virtual Circuits
            layered onto a Frame Relay Interface from RFC 1315."
         ::= { frGroups 7 }

     frErrGroup0    OBJECT-GROUP
         OBJECTS {
                   frErrIfIndex, frErrType, frErrData, frErrTime
                }
         STATUS  current
         DESCRIPTION
            "Objects designed to assist in debugging Frame Relay
            Interfaces from RFC 1315."
         ::= { frGroups 8 }


     frTrapGroup0    OBJECT-GROUP
         OBJECTS { frTrapState }
         STATUS  current
         DESCRIPTION
            "The objects necessary to control a Frame Relay
            Interface's notification messages from RFC 1315."
         ::= { frGroups 9 }

     END
--	filter.mib - Filter MIB file
--
--
-- Author:         Fritz Reeve
--
-- $Id: usr_filter.mib,v 1.4.2.3 1997/02/03 19:47:03 sef Exp $
--
--  | Copyright (c) 1996 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

Usr-Dhcp-MIB DEFINITIONS ::= BEGIN

        IMPORTS
          RowStatus
                FROM SNMPv2-TC
          Counter, IpAddress
                  FROM RFC1155-SMI
          OBJECT-TYPE
                  FROM RFC-1212
          DisplayString, usrDhcp, UsrConfigStatus
                  FROM USR-DEFINITIONS-MIB;


   -- textual conventions

          -- All representations of MAC addresses in this MIB Module
          -- use, as a textual convention (i.e. this convention does
          -- not affect their encoding), the data type:
    
          MacAddress ::= OCTET STRING (SIZE (6))    -- a 6 octet address
                                                    -- in the
                                                    -- "canonical"
                                                    -- order
          -- defined by IEEE 802.1a, i.e., as if it were transmitted
          -- least significant bit first, even though 802.5 (in
          -- contrast to other n802.x protocols) requires MAC
          -- addresses to be transmitted most significant bit first.


   -- Begin managed object definitions here...


     usrDhcpConfigFileName OBJECT-TYPE
         SYNTAX      DisplayString
         ACCESS      read-write
         STATUS      mandatory
         DESCRIPTION             
            "The name of a ConfigFile to read/write permanent database
             records.  If the value of this object is an empty string, 
             then the Filter Manager process uses the default name 
             `@file://filter.cfg'. "
     ::= { usrDhcp 1 }

     usrDhcpCFMStatusFlag  OBJECT-TYPE
         SYNTAX      UsrConfigStatus
         ACCESS      read-write
         STATUS      mandatory
         DESCRIPTION
            "Setting the value of this object to `save' causes the values
             of the SNMP Group to be written out to the current config
             file, which is stored in the usrFilterConfigFileName object.
             While the new ConfigFile is being written, the SNMP process
             will set the value of this flag to `saving''. Any
             attempts to set the value while it is not `normal'
             (i.e. the file is currently being written to the
             ConfigFile) will result in a badValue error being
             returned. Setting the value to `normal' will result in no
             action."
     ::= { usrDhcp 2 }

     usrDhcpAgent OBJECT-TYPE
         SYNTAX  INTEGER {
             disable(0),
             enable(1)
         }
         ACCESS read-write
         STATUS mandatory
         DESCRIPTION
             "this variable enables/disables the DHCP Relay Agent"
         --CONFIGURABLE
     ::= { usrDhcp 3 }
      
     usrDhcpServer1    OBJECT-TYPE
         SYNTAX  IpAddress
         ACCESS  read-write
         STATUS  mandatory
         DESCRIPTION
             "when usrDhcpAgent is enabled, this variable contains the DHCP
              Server IP Address."
          --CONFIGURABLE
     ::= { usrDhcp 4 }
     
     usrDhcpServer2    OBJECT-TYPE
         SYNTAX  IpAddress
         ACCESS  read-write
         STATUS  mandatory
         DESCRIPTION
             "when usrDhcpAgent is enabled, this variable contains the DHCP
              Server IP Address."
          --CONFIGURABLE
     ::= { usrDhcp 5 }

     usrDhcpClientMessages OBJECT-TYPE
         SYNTAX  Counter
         ACCESS  read-only
         STATUS  mandatory
         DESCRIPTION
                 "The total number of messages received on the LAN
                 interface from the Client."
     ::= { usrDhcp 6 }

     usrDhcpServerMessages OBJECT-TYPE
         SYNTAX  Counter
         ACCESS  read-only
         STATUS  mandatory
         DESCRIPTION
                 "The total number of messages received on the WAN 
                 interfaces from the Servers."
     ::= { usrDhcp 7 }

     usrDhcpClientErrors   OBJECT-TYPE
         SYNTAX  Counter
         ACCESS  read-only
         STATUS  mandatory
         DESCRIPTION
                 "The total number of messages received on the LAN 
                 interfaces from the Client which were discarded 
                 due to validation errors."
     ::= { usrDhcp 8 }

     usrDhcpServerErrors   OBJECT-TYPE
         SYNTAX  Counter
         ACCESS  read-only
         STATUS  mandatory
         DESCRIPTION
                 "The total number of messages received on the WAN 
                 interfaces from the Servers which were discarded 
                 due to validation errors."
     ::= { usrDhcp 9 }

     usrDhcpCmGiAddr   OBJECT-TYPE
         SYNTAX  DisplayString
         ACCESS  read-write
         STATUS  mandatory
         DESCRIPTION
            "The network name for the Cable Modems in the Cable Modem Termination
			System"
          --CONFIGURABLE
     ::= { usrDhcp 10 }

     usrDhcpCpeGiAddr   OBJECT-TYPE
         SYNTAX  DisplayString
         ACCESS  read-write
         STATUS  mandatory
         DESCRIPTION
            "The network name for the Customer Premises Equipment in the 
			Cable Modem Termination System"
          --CONFIGURABLE
     ::= { usrDhcp 11 }


     usrDhcpMode  OBJECT-TYPE
         SYNTAX  INTEGER {
             enabled(1),
             disabled(2)
         }
         ACCESS read-write
         STATUS deprecated
         DESCRIPTION
             "this variable selects the DHCP mode. When set to Server, the 
              router will be a local DHCP server and assign configured addresses 
              and parameters to the clients on the LAN.  When set to Relay, 
              the router will send the Client DHCP/BOOTP requests to the 
              configured remote Server(s).  "
         DEFVAL { 2 } 
         --CONFIGURABLE
     ::= { usrDhcp 12 }
     
    usrDhcpProTable OBJECT-TYPE
	SYNTAX SEQUENCE OF UsrDhcpProEntry
	ACCESS not-accessible
	STATUS deprecated
	DESCRIPTION "Table of Client configuration profiles"
	::= {usrDhcp 13 }

    usrDhcpProEntry OBJECT-TYPE
	SYNTAX UsrDhcpProEntry
	ACCESS not-accessible
	STATUS deprecated
	DESCRIPTION "Client configuration profile"
	INDEX {usrDhcpProIndex}
	::= {usrDhcpProTable 1}

    UsrDhcpProEntry ::=
	SEQUENCE {
           usrDhcpProIndex 	INTEGER,
           usrDhcpProLease 	INTEGER,
           usrDhcpProRtr   	IpAddress,
           usrDhcpProDNS1  	IpAddress,
           usrDhcpProDNS2  	IpAddress,
           usrDhcpProWINS1 	IpAddress,
           usrDhcpProWINS2 	IpAddress,
           usrDhcpProHost	DisplayString,
           usrDhcpProDomain	DisplayString,
	   usrDhcpProStatus	RowStatus
  	   }

    usrDhcpProIndex OBJECT-TYPE
	SYNTAX INTEGER
	ACCESS not-accessible
	STATUS mandatory
	DESCRIPTION "Profile index"
	::= {usrDhcpProEntry 1}

    usrDhcpProLease OBJECT-TYPE
	SYNTAX INTEGER
	ACCESS read-write
	STATUS deprecated
	DESCRIPTION "Address lease lifetime. Default of -1 indicates infinite lease"
	--CONFIGURABLE
	::= {usrDhcpProEntry 2}

    usrDhcpProRtr OBJECT-TYPE
	SYNTAX IpAddress
	ACCESS read-write
	STATUS deprecated
	DESCRIPTION "IP Address of default router for client"
	--CONFIGURABLE
	::= {usrDhcpProEntry 3}

    usrDhcpProDNS1 OBJECT-TYPE
	SYNTAX IpAddress
	ACCESS read-write
	STATUS deprecated
	DESCRIPTION "IP address of DNS server for client"
	--CONFIGURABLE
	::= {usrDhcpProEntry 4}

    usrDhcpProDNS2 OBJECT-TYPE
	SYNTAX IpAddress
	ACCESS read-write
	STATUS deprecated
	DESCRIPTION "IP address of secondary DNS server"
	--CONFIGURABLE
	::= {usrDhcpProEntry 5}

    usrDhcpProWINS1 OBJECT-TYPE
	SYNTAX IpAddress
	ACCESS read-write
	STATUS deprecated
	DESCRIPTION "IP address of primary WINS server"
	--CONFIGURABLE
	::= {usrDhcpProEntry 6}

    usrDhcpProWINS2 OBJECT-TYPE
	SYNTAX IpAddress
	ACCESS read-write
	STATUS deprecated
	DESCRIPTION "IP address of secondary WINS Server"
	--CONFIGURABLE
	::= {usrDhcpProEntry 7}

    usrDhcpProHost OBJECT-TYPE
	SYNTAX DisplayString (SIZE (0..32))
	ACCESS read-write
	STATUS deprecated
	DESCRIPTION "Base host name. Each host name allocated will a a numeric suffix added"
	--CONFIGURABLE
	::= {usrDhcpProEntry 8}

    usrDhcpProDomain OBJECT-TYPE
	SYNTAX DisplayString (SIZE (0..64))
	ACCESS read-write
	STATUS deprecated
	DESCRIPTION "Domain name"
	--CONFIGURABLE
	::= {usrDhcpProEntry 9}

    usrDhcpProStatus OBJECT-TYPE
	SYNTAX RowStatus
	ACCESS read-write
	STATUS mandatory
	DESCRIPTION "Status of the Profile Table row"
	::= {usrDhcpProEntry 10}


    ---
    ---  Automatic Address allocation table
    ---
    usrDhcpAutoTable OBJECT-TYPE
	SYNTAX SEQUENCE OF UsrDhcpAutoEntry
	ACCESS not-accessible
	STATUS mandatory
	DESCRIPTION "Table of IP address allocation entries"
	::= {usrDhcp 14 }

    usrDhcpAutoEntry OBJECT-TYPE
	SYNTAX UsrDhcpAutoEntry
	ACCESS not-accessible
	STATUS deprecated
	DESCRIPTION "Automatic IP address allocation entry"
	INDEX {usrDhcpAutoIndex}
	::={ usrDhcpAutoTable 1}

    UsrDhcpAutoEntry ::=
	SEQUENCE {
		usrDhcpAutoIndex	INTEGER,
		usrDhcpAutoSeed		IpAddress,
		usrDhcpAutoMask		IpAddress,
		usrDhcpAutoRange	IpAddress,
		usrDhcpAutoPro		INTEGER,
		usrDhcpAutoStatus	RowStatus
	  }

    usrDhcpAutoIndex OBJECT-TYPE
	SYNTAX INTEGER
	ACCESS not-accessible
	STATUS deprecated
	DESCRIPTION "Auto range index"
	::={ usrDhcpAutoEntry 1}

    usrDhcpAutoSeed OBJECT-TYPE
	SYNTAX IpAddress
	ACCESS read-write
	STATUS deprecated
	DESCRIPTION "Initial seed address. Default 10.0.0.1"
	--CONFIGURABLE
	::= {usrDhcpAutoEntry 2}

    usrDhcpAutoMask OBJECT-TYPE	
	SYNTAX IpAddress
	ACCESS read-write
	STATUS deprecated
	DESCRIPTION "Subnet mask. Default 255.0.0.0"
	--CONFIGURABLE
	::= {usrDhcpAutoEntry 3}

    usrDhcpAutoRange OBJECT-TYPE
	SYNTAX IpAddress
	ACCESS read-write
	STATUS deprecated
	DESCRIPTION "Highest IP address. Default of 255.255.255.255 indicates up to limit of seed mask"
	--CONFIGURABLE
	::= {usrDhcpAutoEntry 4}

    usrDhcpAutoPro OBJECT-TYPE
	SYNTAX INTEGER
	ACCESS read-write
	STATUS deprecated
	DESCRIPTION "Index of client configuration profile"
	::= {usrDhcpAutoEntry 5}

    usrDhcpAutoStatus OBJECT-TYPE
	SYNTAX RowStatus
	ACCESS read-write
	STATUS mandatory
	DESCRIPTION "Status of the range table row"
	::= {usrDhcpAutoEntry 6}

    ---
    ---   Lease Status table
    ---   Displays details of allocated IP addresses and clients
    ---   to which they have been allocated
    ---
    usrDhcpLeaseTable OBJECT-TYPE
	SYNTAX SEQUENCE OF UsrDhcpLeaseEntry
	ACCESS not-accessible
	STATUS deprecated
	DESCRIPTION "A table of automatically allocated IP addresses"
	::= {usrDhcp 15 }

    usrDhcpLeaseEntry OBJECT-TYPE
	SYNTAX UsrDhcpLeaseEntry
	ACCESS not-accessible
	STATUS mandatory
	DESCRIPTION "A description of an automatically-allocated address"
	INDEX { usrDhcpLeaseIpAddr }
	::= {usrDhcpLeaseTable 1}

    UsrDhcpLeaseEntry ::=
	SEQUENCE {
           usrDhcpLeaseIpAddr  	IpAddress,
           usrDhcpLeaseIfIndex 	INTEGER,
           usrDhcpLeaseHwAddr  	MacAddress,
           usrDhcpLeaseCID     	OCTET STRING,
           usrDhcpLeaseValue	INTEGER,
           usrDhcpLeaseLife	INTEGER,
	   usrDhcpLeaseType	INTEGER,
	   usrDhcpLeaseStatus	RowStatus
         }

    usrDhcpLeaseIpAddr OBJECT-TYPE
	SYNTAX IpAddress
	ACCESS not-accessible
	STATUS mandatory
	DESCRIPTION "Automatically allocated IP address"
	::= {usrDhcpLeaseEntry 1}

    usrDhcpLeaseIfIndex OBJECT-TYPE
	SYNTAX INTEGER
	ACCESS read-write
	STATUS mandatory
	DESCRIPTION "Interface over which IP address was allocated"
	::= {usrDhcpLeaseEntry 2}

    usrDhcpLeaseHwAddr OBJECT-TYPE
	SYNTAX MacAddress
	ACCESS read-write
	STATUS mandatory
	DESCRIPTION "Hardware address of client to which IP address was allocated"
	::= {usrDhcpLeaseEntry 3}

    usrDhcpLeaseCID OBJECT-TYPE
	SYNTAX OCTET STRING
	ACCESS read-write
	STATUS mandatory
	DESCRIPTION "Identifier of client to which IP address was allocated"
	::= {usrDhcpLeaseEntry 4}

    usrDhcpLeaseValue OBJECT-TYPE
	SYNTAX INTEGER
	ACCESS read-write
	STATUS mandatory
	DESCRIPTION "Lifetime of lease. -1 if permanently allocated"
	::= {usrDhcpLeaseEntry 5}

    usrDhcpLeaseLife OBJECT-TYPE
	SYNTAX INTEGER
	ACCESS read-write
	STATUS mandatory
	DESCRIPTION "Remaining lifetime of lease. -1 if permanently allocated"
	::= {usrDhcpLeaseEntry 6}

    usrDhcpLeaseType OBJECT-TYPE
	SYNTAX INTEGER {dynamic(1),manual(2)}
	ACCESS read-write
	STATUS mandatory
	DESCRIPTION "Type of lease"
	::= {usrDhcpLeaseEntry 7}

    usrDhcpLeaseStatus OBJECT-TYPE
	SYNTAX RowStatus
	ACCESS read-write
	STATUS mandatory
	DESCRIPTION "Status of the Lease Table row"
	::= {usrDhcpLeaseEntry 8}

---
--- Server counters
---
   usrDhcpLeaseReqRx OBJECT-TYPE
	SYNTAX Counter
	ACCESS read-only
	STATUS mandatory
	DESCRIPTION ""
	::= {usrDhcp 16 }

   usrDhcpRenewalReqRx OBJECT-TYPE
	SYNTAX Counter
	ACCESS read-only
	STATUS mandatory
	DESCRIPTION ""
	::= {usrDhcp 17 }

   usrDhcpAcceptReqRx OBJECT-TYPE
	SYNTAX Counter
	ACCESS read-only
	STATUS mandatory
	DESCRIPTION ""
	::= {usrDhcp 18 }
      
   usrDhcpDeclineRx OBJECT-TYPE
	SYNTAX Counter
	ACCESS read-only
	STATUS mandatory
	DESCRIPTION ""
	::= {usrDhcp 19 }

   usrDhcpReleaseRx OBJECT-TYPE
	SYNTAX Counter
	ACCESS read-only
	STATUS mandatory
	DESCRIPTION ""
	::= {usrDhcp 20}

   usrDhcpInvalidRx OBJECT-TYPE
	SYNTAX Counter
	ACCESS read-only
	STATUS mandatory
	DESCRIPTION ""
	::= {usrDhcp 21}

   usrDhcpOfferTx OBJECT-TYPE
	SYNTAX Counter
	ACCESS read-only
	STATUS mandatory
	DESCRIPTION ""
	::= {usrDhcp 22}

    usrDhcpConfirmTx OBJECT-TYPE
	SYNTAX Counter
	ACCESS read-only
	STATUS mandatory
	DESCRIPTION ""
	::= {usrDhcp 23}

   usrDhcpDenialTx OBJECT-TYPE
	SYNTAX Counter
	ACCESS read-only
	STATUS mandatory
	DESCRIPTION ""
	::= {usrDhcp 24}

   usrDhcpReqAddrOutOfRange OBJECT-TYPE
	SYNTAX Counter
	ACCESS read-only
	STATUS mandatory
	DESCRIPTION ""
	::= {usrDhcp 25}

   usrDhcpReqAddrInUse OBJECT-TYPE
	SYNTAX Counter
	ACCESS read-only
	STATUS mandatory
	DESCRIPTION ""
	::= {usrDhcp 26}

   usrDhcpNoFreeAddr OBJECT-TYPE
	SYNTAX Counter
	ACCESS read-only
	STATUS mandatory
	DESCRIPTION ""
	::= {usrDhcp 27}

   usrDhcpReqLeaseTooLong OBJECT-TYPE
	SYNTAX Counter
	ACCESS read-only
	STATUS mandatory
	DESCRIPTION ""
	::= {usrDhcp 28}

   usrDhcpProxyEnabled  OBJECT-TYPE
         SYNTAX  INTEGER {
             enabled(1),
             disabled(2)
         } 
         ACCESS read-write
         STATUS mandatory
         DESCRIPTION
             "this variable sets the DHCP proxy to enabled/disabled "
         --CONFIGURABLE
     ::= { usrDhcp 29 }

   usrDhcpProxyDiscIfLeaseExp  OBJECT-TYPE
         SYNTAX  INTEGER {
             yes(1),
             no(2)
         } 
         ACCESS read-write
         STATUS mandatory
         DESCRIPTION
             "this sets the behavior if IP address lease expires "
         --CONFIGURABLE
     ::= { usrDhcp 30 }

    ---
    ---   ProxyClient Lease Status table
    ---   Displays details of allocated IP addresses and clients
    ---   to which they have been allocated
    ---
    usrDhcpProxyLeaseTable OBJECT-TYPE
	SYNTAX SEQUENCE OF UsrDhcpProxyLeaseEntry
	ACCESS not-accessible
	STATUS mandatory
	DESCRIPTION "A table of automatically allocated IP addresses"
	::= {usrDhcp 31}

    usrDhcpProxyLeaseEntry OBJECT-TYPE
	SYNTAX UsrDhcpProxyLeaseEntry
	ACCESS not-accessible
	STATUS mandatory
	DESCRIPTION "A description of an automatically-allocated address"
	INDEX { usrDhcpProxyLeaseIndex }
	::= {usrDhcpProxyLeaseTable 1}

    UsrDhcpProxyLeaseEntry ::=
	SEQUENCE {
           usrDhcpProxyLeaseIndex   	INTEGER,
           usrDhcpProxyLeaseCID     	DisplayString,
           usrDhcpProxyLeaseIpAddr  	IpAddress,
           usrDhcpProxyLeaseIfIndex 	INTEGER,
           usrDhcpProxyLeaseHwAddr  	MacAddress,
           usrDhcpProxyLeaseValue	    INTEGER,
           usrDhcpProxyLeaseLife	    INTEGER
         }

    usrDhcpProxyLeaseIndex OBJECT-TYPE
    SYNTAX INTEGER
    ACCESS not-accessible
    STATUS mandatory
    DESCRIPTION "Index to the table which makes each entry unique"
    ::= {usrDhcpProxyLeaseEntry 1}

    usrDhcpProxyLeaseCID OBJECT-TYPE
	SYNTAX DisplayString
	ACCESS read-only
	STATUS mandatory
	DESCRIPTION "Identifier of client to which IP address was allocated"
	::= {usrDhcpProxyLeaseEntry 2}

    usrDhcpProxyLeaseIpAddr OBJECT-TYPE
	SYNTAX IpAddress
	ACCESS read-only
	STATUS mandatory
	DESCRIPTION "Automatically allocated IP address"
	::= {usrDhcpProxyLeaseEntry 3}

    usrDhcpProxyLeaseIfIndex OBJECT-TYPE
	SYNTAX INTEGER
	ACCESS read-only
	STATUS mandatory
	DESCRIPTION "Interface over which IP address was allocated"
	::= {usrDhcpProxyLeaseEntry 4}

    usrDhcpProxyLeaseHwAddr OBJECT-TYPE
	SYNTAX MacAddress
	ACCESS read-only
	STATUS mandatory
	DESCRIPTION "Hardware address of client to which IP address was allocated"
	::= {usrDhcpProxyLeaseEntry 5}

    usrDhcpProxyLeaseValue OBJECT-TYPE
	SYNTAX INTEGER
	ACCESS read-only
	STATUS mandatory
	DESCRIPTION "Lifetime of lease. -1 if permanently allocated"
	::= {usrDhcpProxyLeaseEntry 6}

    usrDhcpProxyLeaseLife OBJECT-TYPE
	SYNTAX INTEGER
	ACCESS read-only
	STATUS mandatory
	DESCRIPTION "Remaining lifetime of lease. -1 if permanently allocated"
	::= {usrDhcpProxyLeaseEntry 7}

    usrDhcpProxyLeaseStatus OBJECT-TYPE
    SYNTAX RowStatus
    ACCESS read-only
    STATUS mandatory
    DESCRIPTION "Status of the Lease Table row"
    ::= {usrDhcpProxyLeaseEntry 8}

---
---  Proxy Client counters
---

     usrDhcpProxyDiscoveries OBJECT-TYPE
     SYNTAX Counter
     ACCESS read-only
	 STATUS mandatory
	 DESCRIPTION ""
	 ::= {usrDhcp 32 }

     usrDhcpProxyOffers OBJECT-TYPE
     SYNTAX Counter
     ACCESS read-only
	 STATUS mandatory
	 DESCRIPTION ""
	 ::= {usrDhcp 33 }

     usrDhcpProxyAddressesAcquired OBJECT-TYPE
     SYNTAX Counter
     ACCESS read-only
	 STATUS mandatory
	 DESCRIPTION ""
	 ::= {usrDhcp 34 }


     usrDhcpProxyAddressesReleased OBJECT-TYPE
     SYNTAX Counter
     ACCESS read-only
	 STATUS mandatory
	 DESCRIPTION ""
	 ::= {usrDhcp 35 }

     usrDhcpProxyClientsActive OBJECT-TYPE
     SYNTAX Counter
     ACCESS read-only
	 STATUS mandatory
	 DESCRIPTION ""
	 ::= {usrDhcp 36 }

     usrDhcpProxyT1renewals OBJECT-TYPE
     SYNTAX Counter
     ACCESS read-only
	 STATUS mandatory
	 DESCRIPTION ""
	 ::= {usrDhcp 37 }

     usrDhcpProxyT2renewals  OBJECT-TYPE
     SYNTAX Counter
     ACCESS read-only
	 STATUS mandatory
	 DESCRIPTION ""
	 ::= {usrDhcp 38 }

     usrDhcpProxyMaxRetry  OBJECT-TYPE
     SYNTAX INTEGER (2..5)
     ACCESS read-write
	 STATUS mandatory
	 DESCRIPTION "PRoxy Client retry count value"
	 DEFVAL { 2 }
	 --CONFIGURABLE
	 ::= {usrDhcp 39 }


    usrDhcpServerResetCounters	OBJECT-TYPE
    SYNTAX	INTEGER
    ACCESS	write-only
    STATUS	mandatory
    DESCRIPTION
    	"An user action to reset all the server counter contains to value zero"
    --CONFIGURABLE
    ::= { usrDhcp 40 }

    usrDhcpProxyClientResetCounters	OBJECT-TYPE
    SYNTAX	INTEGER
    ACCESS	write-only
    STATUS	mandatory
    DESCRIPTION
    	"An user action to reset all the ProxyClient counter contains to value zero"
    --CONFIGURABLE
    ::= { usrDhcp 41 }

    usrDhcpServerResetSettings	OBJECT-TYPE
    SYNTAX	INTEGER
    ACCESS	write-only
    STATUS	mandatory
    DESCRIPTION
    	"An user action to reset all the server Addresses to value zero"
    --CONFIGURABLE
    ::= { usrDhcp 42 }

END         -- End DHCP MIB definitions

--
-- For the revision history to work correctly, after a new MIB file has been
-- added to the CVS repository the first time the CVS Admin person needs to
-- set the correct comment string delimter for the file.
--
-- Revision 1.1  1996/03/18 21:01:40  freeve
-- First cut at filter MIB
--
--
--
USR-RSHD-MIB DEFINITIONS ::= BEGIN

    IMPORTS
        IpAddress
            FROM RFC1155-SMI
		Counter32 
			FROM  SNMPv2-SMI
        OBJECT-TYPE
            FROM RFC-1212
        usrRsh, UsrUserName
            FROM USR-DEFINITIONS-MIB;

	usrRshHostsTable OBJECT-TYPE
    SYNTAX  SEQUENCE OF USRRshHostsTableEntry
    ACCESS  not-accessible
    STATUS  mandatory
    DESCRIPTION
        "Table of ip address and user name for connection authentication."
    ::= { usrRsh 1 }

    usrRshHostsTableEntry    OBJECT-TYPE
    SYNTAX  USRRshHostsTableEntry
    ACCESS  not-accessible
    STATUS  mandatory
    DESCRIPTION
        "An entry of an ip address and user name for connection authentication."
    INDEX   { usrRshHostsTableIpAddress, usrRshHostsTableUserName}
    ::= { usrRshHostsTable 1 }

    USRRshHostsTableEntry ::= SEQUENCE {
         usrRshHostsTableUserName        UsrUserName,
         usrRshHostsTableIpAddress    IpAddress,
         usrRshHostsTableStatus      INTEGER
         }

    usrRshHostsTableUserName OBJECT-TYPE
    SYNTAX  UsrUserName
    ACCESS  not-accessible
    STATUS  mandatory
    DESCRIPTION
        "The users name"
    ::= { usrRshHostsTableEntry 1 }

    usrRshHostsTableIpAddress OBJECT-TYPE
    SYNTAX  IpAddress
    ACCESS  not-accessible
    STATUS  mandatory
    DESCRIPTION
        "The ip address of the remote hosts"
    ::= { usrRshHostsTableEntry 2 }

    usrRshHostsTableStatus   OBJECT-TYPE
    SYNTAX  INTEGER {
        delete(1),
        add(2)
        }
	ACCESS  read-write
    STATUS  mandatory
    DESCRIPTION
        "If set to 2 user name and the ip address is added to this pool. If
                 set to delet(1) this table is  deleted"
        --CONFIGURABLE
    ::= { usrRshHostsTableEntry 3 }

	usrRshTotalConnections OBJECT-TYPE
        SYNTAX Counter32
        ACCESS read-only
        STATUS mandatory
        DESCRIPTION
                "The total number of connections made"
        ::= { usrRsh 2 }

	 usrRshTotalRSHConnections OBJECT-TYPE
        SYNTAX Counter32
        ACCESS read-only
        STATUS mandatory
        DESCRIPTION
              "The total number of rsh requests"
        ::= { usrRsh 3 }

	 usrRshTotalRcpConnections OBJECT-TYPE
        SYNTAX Counter32
        ACCESS read-only
        STATUS mandatory
        DESCRIPTION
              "The total number of rcp requests"
        ::= { usrRsh 4 }

	 usrRshTotalAuthFailed OBJECT-TYPE
        SYNTAX Counter32
        ACCESS read-only
        STATUS mandatory
        DESCRIPTION
              "The total number of auth failed"
        ::= { usrRsh 5 }

	 usrRshTotalNASDropped OBJECT-TYPE
        SYNTAX Counter32
        ACCESS read-only
        STATUS mandatory
        DESCRIPTION
              "The total number of NAS dropped connections"
        ::= { usrRsh 6 }


END

   USR-VTP-MIB DEFINITIONS ::= BEGIN

   IMPORTS
           	Integer32, 
			Counter32, 
			OBJECT-TYPE 			FROM SNMPv2-SMI
           	IpAddress 				FROM RFC1155-SMI
			RowStatus,TimeStamp 	FROM SNMPv2-TC
			TRAP-TYPE				FROM RFC-1215

           	DisplayString,usrVTP,usrGre FROM USR-DEFINITIONS-MIB;

	-- Textual Conventions       
 
        IpxNetwork ::= OCTET STRING (SIZE(4))

	usrVtpControl		OBJECT IDENTIFIER ::= { usrVTP 1 }
	usrVtpStatistics	OBJECT IDENTIFIER ::= { usrVTP 2 }
	usrVtpCca			OBJECT IDENTIFIER ::= { usrVTP 3 }
	usrVtpCcaTunnel		OBJECT IDENTIFIER ::= { usrVtpCca 1 }
	usrVtpCcaSession	OBJECT IDENTIFIER ::= { usrVtpCca 2 }
	usrVtpTraps         OBJECT IDENTIFIER ::= { usrVTP 6 }

	 usrGreControl           OBJECT IDENTIFIER       ::= { usrGre 1 }
     usrGreStatistics        OBJECT IDENTIFIER       ::= { usrGre 2 }

	--
    --  VTP (Process & Protocol) Control Group
    --


	usrVtpTimecheck	OBJECT-TYPE
		SYNTAX		INTEGER { enabled(1),disabled(2) }
		MAX-ACCESS	read-write
		STATUS		current
		DESCRIPTION	
			"This variable allows enabling/disabling of the timestamp 
			 check performed by VTP on received messages. If there are 
			 problems with the NTP server and/or clock synchronization,
			 it should be set to disabled."
		--CONFIGURABLE
	::= { usrVtpControl 1 }

--
--	VTP Statistics Group
--

	usrVtpRegistrationRequestsIn   OBJECT-TYPE
       SYNTAX   Counter32
       MAX-ACCESS   read-only
       STATUS   current
       DESCRIPTION
        "A table containing all the counters."
       ::= { usrVtpStatistics 1 }
     
     usrVtpRegistrationRequestsOut  OBJECT-TYPE
      SYNTAX    Counter32
      MAX-ACCESS    read-only
      STATUS    current
      DESCRIPTION
        "Registration requests sent counter"
      ::= { usrVtpStatistics 2 }
     
     usrVtpRegistrationResponsesIn  OBJECT-TYPE
      SYNTAX    Counter32
      MAX-ACCESS    read-only
      STATUS    current
      DESCRIPTION
        "Registration responses recvd"
      ::= { usrVtpStatistics 3 }
     
     usrVtpRegistrationResponsesOut OBJECT-TYPE
      SYNTAX    Counter32
      MAX-ACCESS    read-only
      STATUS    current
      DESCRIPTION
        "Registration responses sent"
      ::= { usrVtpStatistics 4 }
     
     usrVtpRefreshRequestsIn    OBJECT-TYPE
      SYNTAX    Counter32
      MAX-ACCESS    read-only
      STATUS    current
      DESCRIPTION
        "Refresh requests received."
      ::= { usrVtpStatistics 5 }

     usrVtpRefreshRequestsOut   OBJECT-TYPE
      SYNTAX    Counter32
      MAX-ACCESS    read-only
      STATUS    current
      DESCRIPTION
        "Refresh requests sent"
      ::= { usrVtpStatistics 6 }
 
     usrVtpRefreshResponsesIn   OBJECT-TYPE
      SYNTAX    Counter32
      MAX-ACCESS    read-only
      STATUS    current
      DESCRIPTION
        "Refresh responses received."
      ::= { usrVtpStatistics 7 }
 
     usrVtpRefreshResponsesOut  OBJECT-TYPE
      SYNTAX    Counter32
      MAX-ACCESS    read-only
      STATUS    current
      DESCRIPTION
        "Refresh responses sent"
      ::= { usrVtpStatistics 8 }
 
     usrVtpDeregistrationRequestsIn OBJECT-TYPE
      SYNTAX    Counter32
      MAX-ACCESS    read-only
      STATUS    current
      DESCRIPTION
        "De registration requests received"
      ::= { usrVtpStatistics 9 }

     usrVtpDeregistrationRequestsOut OBJECT-TYPE
      SYNTAX    Counter32
      MAX-ACCESS    read-only
      STATUS    current
      DESCRIPTION
        "De registration requests received"
      ::= { usrVtpStatistics 10 }

	usrVtpDeregistrationResponsesIn   OBJECT-TYPE
          SYNTAX        Counter32
          MAX-ACCESS    read-only
          STATUS        current
          DESCRIPTION
                "De registration responses sent"
          ::= { usrVtpStatistics 11 }

	usrVtpDeregistrationResponsesOut   OBJECT-TYPE
          SYNTAX        Counter32
          MAX-ACCESS    read-only
          STATUS        current
          DESCRIPTION
                "De registration responses sent"
          ::= { usrVtpStatistics 12 }
 
     usrVtpPDUAuthenticationFailures    OBJECT-TYPE
          SYNTAX        Counter32
          MAX-ACCESS    read-only
          STATUS        current
          DESCRIPTION
                "PDU authentication failures"
          ::= { usrVtpStatistics 13 }
 
     usrVtpVPNValidationFailures    OBJECT-TYPE
          SYNTAX        Counter32
          MAX-ACCESS    read-only
          STATUS        current
          DESCRIPTION
                "VPN validation failures"
          ::= { usrVtpStatistics 14 }

	 usrVtpTimeCheckFailures OBJECT-TYPE
        SYNTAX      Counter32
        MAX-ACCESS  read-only
        STATUS      current
        DESCRIPTION
            "The number of VTP messages which failed the
            timestamp check."
          ::= { usrVtpStatistics 15 }

--	
--	VTP CCA  Tunnel Group
--

	usrCcaTunnelTable OBJECT-TYPE
		SYNTAX		SEQUENCE OF UsrCcaTunnelEntry
		MAX-ACCESS	not-accessible
		STATUS		current
		DESCRIPTION
			"A table of CCA VTP tunnels"
	::= { usrVtpCcaTunnel 1 }

	usrCcaTunnelEntry 	OBJECT-TYPE
		SYNTAX		UsrCcaTunnelEntry
		MAX-ACCESS	not-accessible
		STATUS		current
		DESCRIPTION
			"An entry in the CCA VTP Tunnel table"
		INDEX { usrCcaTunnelTunnelIdx }
	::= { usrCcaTunnelTable 1 }

	UsrCcaTunnelEntry ::= SEQUENCE {
		usrCcaTunnelTunnelIdx			Integer32,
		usrCcaTunnelVPNName				DisplayString,
		usrCcaTunnelInterfaceName		DisplayString,
		usrCcaTunnelEstabTime			TimeStamp,
		usrCcaTunnelVPNId				Integer32,
		usrCcaTunnelGatewayAddr			IpAddress,
		usrCcaTunnelNasAddr				IpAddress,
		usrCcaTunnelSessionCount		Integer32,
		usrCcaTunnelStatus				RowStatus
	}

	usrCcaTunnelTunnelIdx	OBJECT-TYPE
		SYNTAX      Integer32
        MAX-ACCESS  read-only
        STATUS      current
        DESCRIPTION
            ""
    ::= { usrCcaTunnelEntry 1 }

	usrCcaTunnelVPNName OBJECT-TYPE
		SYNTAX		DisplayString
		MAX-ACCESS	read-only
		STATUS		current
		DESCRIPTION
			""
	::= { usrCcaTunnelEntry 2 }

	usrCcaTunnelInterfaceName 	OBJECT-TYPE
		SYNTAX		DisplayString
		MAX-ACCESS  read-only
		STATUS      current
        DESCRIPTION
            ""
    ::= { usrCcaTunnelEntry 3 }

	usrCcaTunnelEstabTime	OBJECT-TYPE
		SYNTAX      TimeStamp
        MAX-ACCESS  read-only
        STATUS      current
        DESCRIPTION
            ""
    ::= { usrCcaTunnelEntry 4 }

	usrCcaTunnelVPNId	OBJECT-TYPE
		SYNTAX      Integer32      
        MAX-ACCESS  read-only
        STATUS      current
        DESCRIPTION
            ""
    ::= { usrCcaTunnelEntry 5 }

	usrCcaTunnelGatewayAddr	OBJECT-TYPE
		SYNTAX      IpAddress      
        MAX-ACCESS  read-only
        STATUS      current
        DESCRIPTION
            ""
    ::= { usrCcaTunnelEntry 6 }

	usrCcaTunnelNasAddr	OBJECT-TYPE
		SYNTAX      IpAddress
        MAX-ACCESS  read-only
        STATUS      current
        DESCRIPTION
            ""
    ::= { usrCcaTunnelEntry 7 }

	usrCcaTunnelSessionCount	OBJECT-TYPE
		SYNTAX      Integer32
        MAX-ACCESS  read-only
        STATUS      current
        DESCRIPTION
            ""
    ::= { usrCcaTunnelEntry 8 }

	usrCcaTunnelStatus	OBJECT-TYPE
		SYNTAX      RowStatus
        MAX-ACCESS  read-write
        STATUS      current
        DESCRIPTION
            ""
    ::= { usrCcaTunnelEntry 9 }

	--
    --  VTP CCA Session Group
    --
    
    usrCcaSessionTable OBJECT-TYPE
        SYNTAX SEQUENCE OF UsrCcaSessionEntry
        MAX-ACCESS  not-accessible
        STATUS      current
        DESCRIPTION
            "A table of client sessions within a tunnel."
        ::= { usrVtpCcaSession 1 }
 
    usrCcaSessionEntry OBJECT-TYPE
        SYNTAX  UsrCcaSessionEntry
        MAX-ACCESS  not-accessible
        STATUS  current
        DESCRIPTION
            "An entry in the tunnel client session table."
        INDEX {usrCcaSessionTunnelId, usrCcaSessionSPI }
        ::= {usrCcaSessionTable 1 }
 
	UsrCcaSessionEntry ::= SEQUENCE {
        usrCcaSessionTunnelId       Integer32,
        usrCcaSessionSPI        Integer32,
        usrCcaSessionVPNId      Integer32,
        usrCcaSessionUserName       DisplayString,
        usrCcaSessionIPregistration INTEGER,
        usrCcaSessionIProuting      INTEGER,
        usrCcaSessionIProutingProto INTEGER,
        usrCcaSessionIPlocalAddress IpAddress,
        usrCcaSessionIPlocalMask    IpAddress,
        usrCcaSessionIPclientAddress    IpAddress,
        usrCcaSessionIPclientMask   IpAddress,
        usrCcaSessionIPXregistration    INTEGER,
        usrCcaSessionIPXrouting     INTEGER,
        usrCcaSessionIPXroutingProto    INTEGER,
        usrCcaSessionIPXlocalNetwork    IpxNetwork,
        usrCcaSessionIPXlocalNode   OCTET STRING,
        usrCcaSessionIPXclientNetwork   IpxNetwork,
        usrCcaSessionIPXclientNode  OCTET STRING,
        usrCcaSessionStatus     RowStatus
    }
    
    usrCcaSessionTunnelId OBJECT-TYPE
            SYNTAX      Integer32
            MAX-ACCESS      read-only
            STATUS          current
            DESCRIPTION
                        "The value used by VTP to uniquely identify this
                        tunnel by both the VPN Gateway and the NAS. This value
                        is also used in the GRE encapsulated packets to
                        identify which tunnel a given packet is on "
                ::= { usrCcaSessionEntry 1 }

	usrCcaSessionSPI OBJECT-TYPE
        SYNTAX      Integer32
        MAX-ACCESS  read-only
        STATUS      current
        DESCRIPTION
            "The session's Security Parameter Index. Used to
            identify a given session."
        ::= { usrCcaSessionEntry 2 }
 
    usrCcaSessionVPNId OBJECT-TYPE
        SYNTAX      Integer32
        MAX-ACCESS  read-only
        STATUS      current
        DESCRIPTION
            "The VPN Identifier for the VPN that this session's
            tunnel is a member of "
        ::= { usrCcaSessionEntry 3 }
 
    usrCcaSessionUserName OBJECT-TYPE
        SYNTAX      DisplayString (SIZE(1..80))
        MAX-ACCESS  read-only
        STATUS      current
        DESCRIPTION
            "The user login string as authenticated by the
            originating NAS."
        ::= { usrCcaSessionEntry 4 }
 
    usrCcaSessionIPregistration OBJECT-TYPE
        SYNTAX  INTEGER {
            enabled(1),
            disabled(2)
        }
        MAX-ACCESS  read-only
        STATUS      current
        DESCRIPTION
            "Indicates if IP is or is not registered for this
            session."
        ::= { usrCcaSessionEntry 5 }
 
	usrCcaSessionIProuting OBJECT-TYPE
        SYNTAX  INTEGER {
            none(0),
            broadcast(1),
            listen(2),
            broadcast-listen(3)
        }
        MAX-ACCESS  read-only
        STATUS      current
        DESCRIPTION
            "Indicates state of IP routing for this session."
        ::= { usrCcaSessionEntry 6 }
 
    usrCcaSessionIProutingProto OBJECT-TYPE
        SYNTAX  INTEGER {
            rip-I(1),
            rip-II(2),
            ospf(3)
        }
        MAX-ACCESS  read-only
        STATUS      current
        DESCRIPTION
            "If IP routing is enabled, indicates which routing
            protocol is used for this session."
        ::= { usrCcaSessionEntry 7 }
 
    usrCcaSessionIPlocalAddress OBJECT-TYPE
        SYNTAX      IpAddress
        MAX-ACCESS  read-only
        STATUS      current
        DESCRIPTION
            "The IP address the VPN Gateway's virtual router is
            using for this link."
        ::= { usrCcaSessionEntry 8 }
 
	usrCcaSessionIPlocalMask OBJECT-TYPE
        SYNTAX      IpAddress
        MAX-ACCESS  read-only
        STATUS      current
        DESCRIPTION
            "The IP subnet mask the VPN Gateway's virtual router
            is using for this link."
        ::= { usrCcaSessionEntry 9 }
 
    usrCcaSessionIPclientAddress OBJECT-TYPE
        SYNTAX      IpAddress
        MAX-ACCESS  read-only
        STATUS      current
        DESCRIPTION
            "The IP address of the NAS's dial-in client, which is
            the remote end of this link."
        ::= { usrCcaSessionEntry 10 }
 
    usrCcaSessionIPclientMask OBJECT-TYPE
        SYNTAX      IpAddress
        MAX-ACCESS  read-only
        STATUS      current
        DESCRIPTION
            "The IP subnet mask of the NAS's dial-in client, which
            is the remote end of this link."
        ::= { usrCcaSessionEntry 11 }
 
    usrCcaSessionIPXregistration OBJECT-TYPE
        SYNTAX  INTEGER {
            enabled(1),
            disabled(2)
        }
        MAX-ACCESS  read-only
        STATUS      current
        DESCRIPTION
            "Indicates if IPX is or is not registered for this
            session "
        ::= { usrCcaSessionEntry 12 }
 
	usrCcaSessionIPXrouting OBJECT-TYPE
        SYNTAX  INTEGER {
            none(0),
            send(1),
            listen(2),
            respond(3),
            all(4)
        }
        MAX-ACCESS  read-only
        STATUS      current
        DESCRIPTION
            "Indicates state of IPX routing for this session "
        ::= { usrCcaSessionEntry 13}
 
    usrCcaSessionIPXroutingProto OBJECT-TYPE
        SYNTAX  INTEGER {
            rip(1),
            nlsp(2)
        }
        MAX-ACCESS  read-only
        STATUS      current
        DESCRIPTION
            "If IPX routing is enabled, indicates which routing
            protocol is used for this session "
        ::= { usrCcaSessionEntry 14 }
 
    usrCcaSessionIPXlocalNetwork OBJECT-TYPE
        SYNTAX      IpxNetwork
        MAX-ACCESS  read-only
        STATUS      current
        DESCRIPTION
            "The IPX Network number the VPN Gateway's virtual
            router is using for this link."
        ::= { usrCcaSessionEntry 15 }
 
	usrCcaSessionIPXlocalNode OBJECT-TYPE
        SYNTAX      OCTET STRING (SIZE(6))
        MAX-ACCESS  read-only
        STATUS      current
        DESCRIPTION
            "The IPX Node address the VPN Gateway's virtual router
            is using for this link."
        ::= { usrCcaSessionEntry 16 }
 
    usrCcaSessionIPXclientNetwork OBJECT-TYPE
        SYNTAX      IpxNetwork
        MAX-ACCESS  read-only
        STATUS      current
        DESCRIPTION
            "The IPX Network number of the NAS's dial-in client,
            which is the remote end of this link "
        ::= { usrCcaSessionEntry 17 }
 
    usrCcaSessionIPXclientNode OBJECT-TYPE
        SYNTAX      OCTET STRING (SIZE(6))
        MAX-ACCESS  read-only
        STATUS      current
        DESCRIPTION
            "The IPX Node address of the NAS's dial-in client,
            which is the remote end of this link "
        ::= { usrCcaSessionEntry 18 }
 
    usrCcaSessionStatus OBJECT-TYPE
        SYNTAX      RowStatus
        MAX-ACCESS  read-write
        STATUS      current
        DESCRIPTION
            "The status of this entry."
        ::= { usrCcaSessionEntry 19 }
 
	        --
        --      GRE Control Group
        --
    
        usrGreState OBJECT-TYPE
                SYNTAX  INTEGER {
                        enabled(1),
                        disabled(2)
                }
                MAX-ACCESS      read-only
                STATUS          current
                DESCRIPTION
                        "Indicates if GRE is enabled or disabled. If the VTP
                        process is running, the state will always be enabled."
                ::= { usrGreControl 1 }
    
        --
        --      GRE Statistics Group
        --
    
        usrGreNetPktsIn OBJECT-TYPE
                SYNTAX          Counter32
                MAX-ACCESS      read-only
                STATUS          current
                DESCRIPTION
                        "Count of GRE encapsulated packets received from IP."
                ::= { usrGreStatistics 1 }
    
        usrGreNetPktsInDelivered OBJECT-TYPE
                SYNTAX          Counter32
                MAX-ACCESS      read-only
                STATUS          current
                DESCRIPTION
                        "Count of de-encapsulated GRE payloads delivered to
                        GRE clients."
                ::= { usrGreStatistics 2 }
    
		usrGreNetPktsInDiscarded OBJECT-TYPE
                SYNTAX          Counter32
                MAX-ACCESS      read-only
                STATUS          current
                DESCRIPTION
                        "Total count of de-encapsulated GRE payloads
                        discarded."
                ::= { usrGreStatistics 3 }
    
        usrGreNetPktsInHdrErrs OBJECT-TYPE
                SYNTAX          Counter32
                MAX-ACCESS      read-only
                STATUS          current
                DESCRIPTION
                        "Count of GRE packets discarded due to malformed
                        headers."
                ::= { usrGreStatistics 4 }
    
        usrGreNetPktsInNoClients OBJECT-TYPE
                SYNTAX          Counter32
                MAX-ACCESS      read-only
                STATUS          current
                DESCRIPTION
                        "Count of de-encapsulated GRE payloads discarded due
                        to no client."
                ::= { usrGreStatistics 5 }
    
        usrGreClientPktsIn OBJECT-TYPE
                SYNTAX          Counter32
                MAX-ACCESS      read-only
                STATUS          current
                DESCRIPTION
                        "Count of packets handed to GRE for encapsulation and
                        subsequent transmission."
                ::= { usrGreStatistics 6 }
    
		usrGreClientPktsEncapsulated OBJECT-TYPE
                SYNTAX          Counter32
                MAX-ACCESS      read-only
                STATUS          current
                DESCRIPTION
                        "Count of packets handed to GRE for encapsulation
                        which were actually encapsulated."
                ::= { usrGreStatistics 7 }
    
        usrGreClientPktsDiscarded OBJECT-TYPE
                SYNTAX          Counter32
                MAX-ACCESS      read-only
                STATUS          current
                DESCRIPTION
                        "Count of packets handed to GRE for encapsulation
                        which were discarded for some reason."
                ::= { usrGreStatistics 8 }
    
        usrGreClientPktToIP OBJECT-TYPE
                SYNTAX          Counter32
                MAX-ACCESS      read-only
                STATUS          current
                DESCRIPTION
                        "Count of GRE encapsulated payloads which were passed
                        to IP for transmission."
                ::= { usrGreStatistics 9 }
    
	usrVtpTunnelEstablishmentFailure TRAP-TYPE
        ENTERPRISE  usrVtpTraps
        VARIABLES   {
            usrCcaTunnelVPNId,
            usrCcaTunnelGatewayAddr
        }
        DESCRIPTION     "This trap is generated for tunnel
                        establishment failure."
    --#TYPE "Alarm" 
    ::= 1

	END
IPSEC-MIB DEFINITIONS ::= BEGIN

	IMPORTS
		Counter, IpAddress
			FROM RFC1155-SMI
		OBJECT-TYPE
			FROM RFC-1212
		TruthValue				FROM SNMPv2-TC
		usrIpSec, DisplayString
			FROM USR-DEFINITIONS-MIB;

	usrIpSecSAObjects	OBJECT IDENTIFIER ::= { usrIpSec  1}


-- User managers table definition

	usrSATable	OBJECT-TYPE
	SYNTAX SEQUENCE OF SaEntry
	ACCESS	not-accessible
	STATUS	mandatory
	DESCRIPTION
		""
	::= { usrIpSecSAObjects 1 }
 
	saEntry	OBJECT-TYPE
	SYNTAX	SaEntry
	ACCESS	not-accessible
	STATUS	mandatory
	DESCRIPTION
		""
	INDEX	{ usrSAIndex }
	::= { usrSATable 1 }

	SaEntry ::=
	SEQUENCE {
		usrSAIndex
			INTEGER,
		usrSASourceAddr
			IpAddress,
		usrSADestAddr
			IpAddress,
		usrSAStatus
			INTEGER
	}

	    usrSAIndex      OBJECT-TYPE
	    SYNTAX  INTEGER (0..2147483647)
	    ACCESS  read-only
	    STATUS  mandatory
	    DESCRIPTION
	           ""
	    ::= { saEntry 1 }

	    usrSASourceAddr      OBJECT-TYPE
	    SYNTAX  IpAddress
	    ACCESS  read-only
	    STATUS  mandatory
	    DESCRIPTION
	           ""
	    ::= { saEntry 2 }

	    usrSADestAddr      OBJECT-TYPE
	    SYNTAX  IpAddress
	    ACCESS  read-only
	    STATUS  mandatory
	    DESCRIPTION
	           ""
	    ::= { saEntry 3 }

	    usrSAStatus      OBJECT-TYPE
	    SYNTAX  INTEGER
	    ACCESS  read-only
	    STATUS  mandatory
	    DESCRIPTION
	           ""
	    ::= { saEntry 4 }
END
USR-SS7-MIB DEFINITIONS ::= BEGIN

    IMPORTS
        IpAddress
            FROM RFC1155-SMI
		Counter32 
			FROM  SNMPv2-SMI
        OBJECT-TYPE
            FROM RFC-1212
		DisplayString
			FROM SNMPv2-TC
		TRAP-TYPE
            FROM RFC-1215
        usrSS7
            FROM USR-DEFINITIONS-MIB;


usrSS7Protocol OBJECT-TYPE
    SYNTAX  INTEGER {
        slapv2(1),
        ipdc(2)
        }
   	  ACCESS      read-write
   	  STATUS      mandatory
	  DESCRIPTION " protocol being serviced:- HSS7I_SLAP_V2 or HSS7I_IPDC."
        --CONFIGURABLE
      ::= {usrSS7 1}

usrSS7LANStartMethod OBJECT-TYPE
   	  SYNTAX      INTEGER {
	  	auto(1),
		manual(2)
	   }
   	  ACCESS      read-write
   	  STATUS      mandatory
	  DESCRIPTION "method to bring up TCP/IP connection to SS7GWP - HSS7I_LS_AUTO or HSS7I_LS_MANUAL."
        --CONFIGURABLE
      ::= {usrSS7 2}

usrSS7SLAPgatewayIPAddress OBJECT-TYPE
   	  SYNTAX      IpAddress
   	  ACCESS      read-write
   	  STATUS      mandatory
	  DESCRIPTION "The IP address of the SLAP SS7 gateway."
        --CONFIGURABLE
      ::= {usrSS7 3}

usrSS7SLAPgatewayPort OBJECT-TYPE
   	  SYNTAX      INTEGER
   	  ACCESS      read-write
   	  STATUS      mandatory
	  DESCRIPTION "The TCP port# of the SLAP SS7 gateway."
        --CONFIGURABLE
      ::= {usrSS7 4}

usrSS7SLAPHeartbeatTimerNearEnd OBJECT-TYPE
   	  SYNTAX      INTEGER
   	  ACCESS      read-write
   	  STATUS      mandatory
	  DESCRIPTION "The heartbeat timer settings."
        --CONFIGURABLE
      ::= {usrSS7 5}

usrSS7SLAPChassisID OBJECT-TYPE
   	  SYNTAX      INTEGER
   	  ACCESS      read-write
   	  STATUS      mandatory
	  DESCRIPTION "uniquely identify the TCH in a WAN. This is an unsigned Integer32" 
        --CONFIGURABLE
      ::= {usrSS7 6}

usrSS7SLAPNumberOfConnectionRetries OBJECT-TYPE
   	  SYNTAX      INTEGER
   	  ACCESS      read-write
   	  STATUS      mandatory
	  DESCRIPTION "number of socket connection retries after lost it"
        --CONFIGURABLE
      ::= {usrSS7 7}

usrSS7SLAPConnectionRetryInterval OBJECT-TYPE
   	  SYNTAX      INTEGER
   	  ACCESS      read-write
   	  STATUS      mandatory
	  DESCRIPTION "socket connection retry interval after it is lost"
        --CONFIGURABLE
      ::= {usrSS7 8}

usrSS7SLAPAllowedMissedHeartBeats OBJECT-TYPE
   	  SYNTAX      INTEGER
   	  ACCESS      read-write
   	  STATUS      mandatory
	  DESCRIPTION "number of heartbeat missed from gw before action taken."
        --CONFIGURABLE
      ::= {usrSS7 9}

--  The following are the IPDC mibs which are not supported now..
--  remove the comments when they are supported..
-- 
-- usrSS7IPDCPrimaryIpAddress OBJECT-TYPE
--   	  SYNTAX      IpAddress
--   	  ACCESS      read-write
--   	  STATUS      mandatory
--	  DESCRIPTION " primary IP address to Soft Switch."
--        CONFIGURABLE
--      ::= {usrSS7 10}
--
-- usrSS7IPDCPrimaryPort OBJECT-TYPE
--   	  SYNTAX      INTEGER
--   	  ACCESS      read-write
--   	  STATUS      mandatory
--	  DESCRIPTION " primary port to Soft Switch."
--       CONFIGURABLE
--      ::= {usrSS7 11}
--
-- usrSS7IPDCSecondaryIpAddress OBJECT-TYPE
--    	  SYNTAX      IpAddress
--    	  ACCESS      read-write
--    	  STATUS      mandatory
-- 	  DESCRIPTION " Secondary IP address to Soft Switch."
--         CONFIGURABLE
--       ::= {usrSS7 12}
--
-- usrSS7IPDCSecondaryPort OBJECT-TYPE
--    	  SYNTAX      INTEGER
--    	  ACCESS      read-write
--    	  STATUS      mandatory
-- 	  DESCRIPTION " Secondary port to Soft Switch."
--         CONFIGURABLE
--       ::= {usrSS7 13}
--
-- usrSS7IPDCBayNumber OBJECT-TYPE
--    	  SYNTAX      INTEGER
--    	  ACCESS      read-write
--    	  STATUS      mandatory
-- 	  DESCRIPTION " Bay Number is an 8 bytes alphanumeric quantity which identifies the rack"
--       CONFIGURABLE
--      ::= {usrSS7 14}
--
-- usrSS7IPDCSystemType OBJECT-TYPE
-- 	  SYNTAX      INTEGER
-- 	  ACCESS      read-write
--  	  STATUS      mandatory
--	  DESCRIPTION "type of system by L3."
--       CONFIGURABLE
--      ::= {usrSS7 15}

usrSS7StatSBUSXmitPacketsOKCount OBJECT-TYPE
   	  SYNTAX      INTEGER
   	  ACCESS      read-only
   	  STATUS      mandatory
	  DESCRIPTION "the number of successful packets transmitted over the pBus connection."
      ::= {usrSS7 16}

usrSS7StatSBUSXmitPacketsFailCount OBJECT-TYPE
   	  SYNTAX      INTEGER
   	  ACCESS      read-only
   	  STATUS      mandatory
	  DESCRIPTION "the number of packets failed to transmit over the pBus connection."
      ::= {usrSS7 17}

usrSS7StatSBUSRcvdPacketsOKCount OBJECT-TYPE
   	  SYNTAX      INTEGER
   	  ACCESS      read-only
   	  STATUS      mandatory
	  DESCRIPTION "the number of successful packets received over the pBus connection."
      ::= {usrSS7 18}

usrSS7StatSBUSRcvdmitPacketsFailCount OBJECT-TYPE
   	  SYNTAX      INTEGER
   	  ACCESS      read-only
   	  STATUS      mandatory
	  DESCRIPTION "the number of packets rejected by the pBus/Sbus client application."
      ::= {usrSS7 19}

usrSS7StatGWXmitByetsCount OBJECT-TYPE
   	  SYNTAX      INTEGER
   	  ACCESS      read-only
   	  STATUS      mandatory
	  DESCRIPTION "the number of successful bytes transmitted over the SS7 GW connection."
      ::= {usrSS7 20}

usrSS7StatGWXmitPacketsCount OBJECT-TYPE
   	  SYNTAX      INTEGER
   	  ACCESS      read-only
   	  STATUS      mandatory
	  DESCRIPTION "the number of packets transmited to the SS7 GW connection."
      ::= {usrSS7 21}

usrSS7StatGWRcvdBytesCount OBJECT-TYPE
   	  SYNTAX      INTEGER
   	  ACCESS      read-only
   	  STATUS      mandatory
	  DESCRIPTION "the number of Bytes received over the SS7 GW connection."
      ::= {usrSS7 22}

usrSS7StatGWRcvdPacketsCount OBJECT-TYPE
   	  SYNTAX      INTEGER
   	  ACCESS      read-only
   	  STATUS      mandatory
	  DESCRIPTION "the number of packets from SS7 GW."
      ::= {usrSS7 23}

usrSS7GWConnectionState OBJECT-TYPE
   	  SYNTAX      INTEGER
   	  ACCESS      read-only
   	  STATUS      mandatory
	  DESCRIPTION "the state of the SS7 GW connection UP/DOWN"
      ::= {usrSS7 24}

usrSS7SLAPSecondaryGatewayIPAddress OBJECT-TYPE
   	  SYNTAX      IpAddress
   	  ACCESS      read-write
   	  STATUS      mandatory
	  DESCRIPTION "The IP address of the SLAP SS7 gateway."
        --CONFIGURABLE
      ::= {usrSS7 25}

usrSS7SLAPSecondaryGatewayPort OBJECT-TYPE
   	  SYNTAX      INTEGER
   	  ACCESS      read-write
   	  STATUS      mandatory
	  DESCRIPTION "The TCP port# of the SLAP SS7 gateway."
        --CONFIGURABLE
      ::= {usrSS7 26}

usrSS7SLAPHeartbeatTimerFarEnd OBJECT-TYPE
   	  SYNTAX      INTEGER
   	  ACCESS      read-write
   	  STATUS      mandatory
	  DESCRIPTION "The heartbeat timer settings."
        --CONFIGURABLE
      ::= {usrSS7 27}

usrSS7SlotTable OBJECT-TYPE
        SYNTAX SEQUENCE OF UsrSS7SlotEntry
        ACCESS not-accessible
        STATUS mandatory
        DESCRIPTION
                  "A table containing one row per slot in the chassis.  Each
           row describes the characteristics of the slot"
    ::= { usrSS7 28 }

    usrSS7SlotEntry OBJECT-TYPE
         SYNTAX  UsrSS7SlotEntry
         ACCESS  not-accessible
         STATUS  mandatory
         DESCRIPTION
            "slot access table"
         INDEX   { usrSS7Slot }

    ::= { usrSS7SlotTable 1 }

    UsrSS7SlotEntry ::=
         SEQUENCE {
         usrSS7Slot
            INTEGER,
         usrSS7SlotOwner
            INTEGER,
         usrSS7SlotType
            INTEGER,
		 usrSS7SlotConnectionStatus
			INTEGER,
		 usrSS7SlotTrace
			INTEGER,
		 usrSS7SlotConnectToSlot
			INTEGER,
		 usrSS7SlotDisconnectToSlot
			INTEGER,
		 usrSS7ENFASLinkDownCause
			INTEGER
         }

	usrSS7Slot OBJECT-TYPE
         SYNTAX  INTEGER
	 ACCESS  not-accessible
         STATUS  mandatory
         DESCRIPTION
            "The slot number of this row."
	::= { usrSS7SlotEntry 1 }

	usrSS7SlotOwner OBJECT-TYPE
		SYNTAX   INTEGER {
			no(1),
			yes(2)
			}
         ACCESS   read-write
         STATUS   mandatory
         DESCRIPTION
            "An indication if this slot's card has this Gateway card assigned
             as the owning gateway"
        --CONFIGURABLE
    ::= { usrSS7SlotEntry 2 }

	usrSS7SlotType OBJECT-TYPE
		SYNTAX   INTEGER {
			static(1),
			dynamic(2)
			}
         ACCESS   read-write
         STATUS   mandatory
         DESCRIPTION
            "An indicator that tells if this slot's (row's) data was
             created statically by configuration, or dynamically by
             the receipt of chassis awareness information from the
             NMC.  Only static entries are saved to the configuration
             file.  Dynamic entries are saved as static entries with 
             an empty card type. If dynamic information is learned
             it replaces the information in a static entry.  A dynamic
             entry cannot be changed through the CLI or an SNMP set."
        --CONFIGURABLE
         ::= { usrSS7SlotEntry 3 }

	usrSS7SlotConnectionStatus OBJECT-TYPE
		 SYNTAX  INTEGER
         ACCESS  read-only
         STATUS  mandatory
         DESCRIPTION
            "The status of the sbus connection to HDM at this slot."
    ::= { usrSS7SlotEntry 4 }

   usrSS7SlotTrace    OBJECT-TYPE
			SYNTAX   INTEGER {
				enable(1),
				disable(0)
				}
			ACCESS  read-write
            STATUS  mandatory
            DESCRIPTION
                "SBUS Side SS7 Trace.  enable(1) disable(2) "
   ::= { usrSS7SlotEntry 5 }

   usrSS7SlotConnectToSlot    OBJECT-TYPE
			SYNTAX   INTEGER 
			ACCESS  read-write
            STATUS  mandatory
            DESCRIPTION
                "The Command to connect Hiper Arc to a SS7 channel in the given slot"
   ::= { usrSS7SlotEntry 6 }

   usrSS7SlotDisconnectToSlot    OBJECT-TYPE
			SYNTAX   INTEGER 
			ACCESS  read-write
            STATUS  mandatory
            DESCRIPTION
                "The Command to connect Hiper Arc to a SS7 channel in the given slot"
   ::= { usrSS7SlotEntry 7 }

	usrSS7ENFASLinkDownCause OBJECT-TYPE
			SYNTAX   INTEGER {
				none(0),
				missingHDM(1),
				lostGWConnection(2),
				pBusError(3),
				manualDisconnect(4)
				}
			ACCESS  read-only
		  STATUS      mandatory
		  DESCRIPTION "The status of the SLAP Connection to the Secondary SS7 gateway."
		  ::= {usrSS7SlotEntry 8 }

	usrSS7SlotStatSBUSXmitPacketsOKCount OBJECT-TYPE
		  SYNTAX      INTEGER
		  ACCESS      read-only
		  STATUS      mandatory
		  DESCRIPTION "the number of successful packets transmitted over the pBus connection."
		  ::= {usrSS7SlotEntry 9}

	usrSS7SlotStatSBUSXmitPacketsFailCount OBJECT-TYPE
		  SYNTAX      INTEGER
		  ACCESS      read-only
		  STATUS      mandatory
		  DESCRIPTION "the number of packets failed to transmit over the pBus connection."
		  ::= {usrSS7SlotEntry 10}

	usrSS7SlotStatSBUSRcvdPacketsOKCount OBJECT-TYPE
		  SYNTAX      INTEGER
		  ACCESS      read-only
		  STATUS      mandatory
		  DESCRIPTION "the number of successful packets received over the pBus connection."
		  ::= {usrSS7SlotEntry 11}

	usrSS7SlotStatSBUSRcvdmitPacketsFailCount OBJECT-TYPE
		  SYNTAX      INTEGER
		  ACCESS      read-only
		  STATUS      mandatory
		  DESCRIPTION "the number of packets rejected by the pBus/Sbus client application."
		  ::= {usrSS7SlotEntry 12}

    usrSS7CountersResetTime    OBJECT-TYPE
            SYNTAX  OCTET STRING (SIZE (0..12))
            ACCESS  read-write
            STATUS  mandatory
            DESCRIPTION
                "set: ignores the string and reset the sbus statistics counters.
								 get: returns the last counter reset time"
   ::= { usrSS7 29 }

   usrSS7GWCountersResetTime    OBJECT-TYPE
            SYNTAX  OCTET STRING (SIZE (12))
            ACCESS  read-write
            STATUS      deprecated
            DESCRIPTION
                "Daily time we reset all the SS7 GW connection  statistics counters.
								This mib is not used right now."
   ::= { usrSS7 30 }

   usrSS7ConnectToGW    OBJECT-TYPE
            SYNTAX  OCTET STRING (SIZE (0..12))
            ACCESS  write-only
            STATUS  mandatory
            DESCRIPTION
                "Command to connect to the  SS7 GW manual mode"
   ::= { usrSS7 31 }

   usrSS7SlapTrace    OBJECT-TYPE
			SYNTAX   INTEGER {
				enable(1),
				disable(0)
				}
			ACCESS  read-write
            STATUS  mandatory
            DESCRIPTION
                "SLAP Side SS7 Trace.  enable(1) disable(2) "
        --CONFIGURABLE
   ::= { usrSS7 32 }

   usrSS7TraceOutput    OBJECT-TYPE
			SYNTAX   INTEGER {
				screen(1),
				syslog(2)
				}
			ACCESS  read-write
            STATUS  mandatory
            DESCRIPTION
                "The place where SS7 Trace output is send to. either to the console or syslog "
        --CONFIGURABLE
   ::= { usrSS7 33 }

   usrSS7DisconnectToGW    OBJECT-TYPE
            SYNTAX  OCTET STRING (SIZE (0..12))
            ACCESS  write-only
            STATUS  mandatory
            DESCRIPTION
                "Command to disconnect the the existing conection to SS7 GW.
				this will tear down all the sbus connections to HDMs "
   ::= { usrSS7 34 }

   usrSS7SendHeartBeat    OBJECT-TYPE
            SYNTAX  OCTET STRING (SIZE (0..12))
            ACCESS  write-only
            STATUS  mandatory
            DESCRIPTION
                "Command to send a heartbeat to the existing conection to SS7 GW."
   ::= { usrSS7 35 }

   usrSS7MissedHeartBeatsCounter    OBJECT-TYPE
            SYNTAX  INTEGER
            ACCESS  read-only
            STATUS  mandatory
            DESCRIPTION
                "Command to send a heartbeat to the existing conection to SS7 GW."
   ::= { usrSS7 36 }

	usrSS7SLAPPrimaryGatewayConnectionStatus OBJECT-TYPE
			SYNTAX   INTEGER {
				up(1),
				down(2),
				connecting(3)
				}
			ACCESS  read-only
		  STATUS      mandatory
		  DESCRIPTION "The status of the SLAP Connection to the Primary SS7 gateway."
		  ::= {usrSS7 37 }

	usrSS7SLAPSecondaryGatewayConnectionStatus OBJECT-TYPE
			SYNTAX   INTEGER {
				up(1),
				down(2),
				connecting(3)
				}
			ACCESS  read-only
		  STATUS      mandatory
		  DESCRIPTION "The status of the SLAP Connection to the Secondary SS7 gateway."
		  ::= {usrSS7 38 }

	usrSS7SLAPPrimaryLinkDownCause OBJECT-TYPE
			SYNTAX   INTEGER {
				none(0),
				heartbeatExpired(1),
				socketError(2),
				physicalLinkCut(3),
				manualDisconect(4)
				}
			ACCESS  read-only
		  STATUS      mandatory
		  DESCRIPTION "The status of the SLAP Connection to the Secondary SS7 gateway."
		  ::= {usrSS7 39 }
	
	usrSS7SLAPSecondaryLinkDownCause OBJECT-TYPE
			SYNTAX   INTEGER {
				none(0),
				heartbeatExpired(1),
				socketError(2),
				physicalLinkCut(3),
				manualDisconect(4)
				}
			ACCESS  read-only
		  STATUS      mandatory
		  DESCRIPTION "The status of the SLAP Connection to the Secondary SS7 gateway."
		  ::= {usrSS7 40 }

	usrSS7SLAPUpTrap OBJECT-TYPE
			SYNTAX   INTEGER {
				enable(1),
				disable(0)
				}
			ACCESS  read-write
		  STATUS      mandatory
		  DESCRIPTION "if enabled sends TRAP each time the SLAP connection
                       to the gateway goes UP."
        --CONFIGURABLE
		  ::= {usrSS7 41 }

	usrSS7SLAPDownTrap OBJECT-TYPE
			SYNTAX   INTEGER {
				enable(1),
				disable(0)
				}
			ACCESS  read-write
		  STATUS      mandatory
		  DESCRIPTION "if enabled sends TRAP each time the SLAP connection 
                       to the gateway goes Down."
        --CONFIGURABLE
		  ::= {usrSS7 42 }

	usrSS7ENFASUpTrap OBJECT-TYPE
			SYNTAX   INTEGER {
				enable(1),
				disable(0)
				}
			ACCESS  read-write
		  STATUS      mandatory
		  DESCRIPTION "if enabled sends TRAP each time the ENFAS connection to the
                       HDM goes Up."
        --CONFIGURABLE
		  ::= {usrSS7 43 }

	usrSS7ENFASDownTrap OBJECT-TYPE
			SYNTAX   INTEGER {
				enable(1),
				disable(0)
				}
			ACCESS  read-write
		  STATUS      mandatory
		  DESCRIPTION "if enabled sends TRAP each time the ENFAS connection to the
                       HDM goes Down."
        --CONFIGURABLE
		  ::= {usrSS7 44 }

	usrSS7DropCallFlag OBJECT-TYPE
			SYNTAX   INTEGER {
				enable(1),
				disable(2)
				}
			ACCESS  read-write
		  STATUS      mandatory
		  DESCRIPTION "if enabled, drops all the calls, if the connection the GW is gone.
                       after the timer expires ."
        --CONFIGURABLE
		  ::= {usrSS7 45 }

	usrSS7DropCallTimer OBJECT-TYPE
			SYNTAX   INTEGER 
			ACCESS  read-write
		  STATUS      mandatory
		  DESCRIPTION "When timer expires drops all the calls, when looses GW connection"
        --CONFIGURABLE
		  ::= {usrSS7 46 }

	usrSS7SLAPGatewayDownTrap TRAP-TYPE
        ENTERPRISE  usrSS7
        VARIABLES   {    
                usrSS7SLAPChassisID,
                usrSS7SLAPgatewayIPAddress,
                usrSS7SLAPgatewayPort,
				usrSS7SLAPPrimaryLinkDownCause
        }
        DESCRIPTION     "This trap is generated when 
			SLAP connection to the SS7 Gateway goes down."
        --#TYPE "Alarm"
        ::= 1

	usrSS7SLAPGatewayUPTrap TRAP-TYPE
        ENTERPRISE  usrSS7
        VARIABLES   {    
                usrSS7SLAPChassisID,
                usrSS7SLAPgatewayIPAddress,
                usrSS7SLAPgatewayPort
        }
        DESCRIPTION     "This trap is generated when 
			SLAP connection to the SS7 Gateway is restored."
        --#TYPE "Alarm"
        ::= 2

	usrSS7ENFASConnectionDownTrap TRAP-TYPE
        ENTERPRISE  usrSS7
        VARIABLES   {    
                usrSS7SLAPChassisID,
                usrSS7Slot,
				usrSS7ENFASLinkDownCause
        }
        DESCRIPTION     "This trap is generated when 
			ENFAS  connection to the HiperDSP slot is Down."
        --#TYPE "Alarm"
        ::= 3

	usrSS7ENFASConnectionUPTrap TRAP-TYPE
        ENTERPRISE  usrSS7
        VARIABLES   {    
                usrSS7SLAPChassisID,
                usrSS7Slot
        }
        DESCRIPTION     "This trap is generated when 
			ENFAS  connection to the HiperDSP slot is restored."
        --#TYPE "Alarm"
        ::= 4

END         -- End USR-SS7-MIB definitions
--
--     usr_betasite.mib -  A template MIB file for Pilgrim MIB modules
--		
--
--	Description:	This module contains MIB definitions for the 
--      		Beta Site specific mibs. 
--
--	Author:	Sachin Natu
--
--  ----------------------------------------------------------------------
-- | Copyright (c) 1999 3Com Corp., Mount Prospect, IL 60056              |
-- |                                                                      |
-- | The information in this software is subject to change without notice |
-- | and should not be construed as a commitment by 3Com Corp.            |
-- |                                                                      |
-- | 3Com Corp. assumes no responsibility for the use or reliability of   |
-- | its software on equipment which is not supplied by 3Com Corp.        |
-- |                                                                      |
-- | This software is furnished under a license and may be copied only    |
-- | with the inclusion of the above copyright notice. This software, or  |
-- | any other copies thereof, may not be provided or otherwise made      |
-- | available to any other person except to one who agrees to these      |
-- | license terms. Title to and ownership of the software shall at all   |
-- | times remain in 3Com Corp.                                           |
--  ----------------------------------------------------------------------

BETASITE-MIB DEFINITIONS ::= BEGIN

	IMPORTS
	  Counter32
		FROM  SNMPv2-SMI
          OBJECT-TYPE
               	FROM RFC-1212
	  TRAP-TYPE
		FROM RFC-1215
          usrBetaSite FROM USR-DEFINITIONS-MIB;

   -- textual conventions
   -- 
   -- textual conventions are like pre-processor macro in 'C'
   --        (i.e. #define statements)
   -- Use them to define your own 'datatypes'

   -- Begin managed object definitions here...

    usrBetaObjs  OBJECT IDENTIFIER ::= { usrBetaSite 1 }
    usrBetaTraps OBJECT IDENTIFIER ::= { usrBetaSite 2 }

    usrChassisActiveCalls  OBJECT-TYPE
         SYNTAX  Counter32
         ACCESS  read-only
         STATUS  mandatory
         DESCRIPTION
             "The number of active calls on the chassis at that moment."
         ::= { usrBetaObjs 1 }

    usrChassisTotalPorts  OBJECT-TYPE
         SYNTAX  Counter32
         ACCESS  read-only
         STATUS  mandatory
         DESCRIPTION
             "The number of ports in the chassis."
         ::= { usrBetaObjs 2 }

    usrChassisPortUtilization  OBJECT-TYPE
         SYNTAX  Counter32
         ACCESS  read-only
         STATUS  mandatory
         DESCRIPTION
             "The percent utilization of the modem ports in the chassis."
         ::= { usrBetaObjs 3 }

    usrChassisCallsInLast24Hrs  OBJECT-TYPE
         SYNTAX  Counter32
         ACCESS  read-only
         STATUS  mandatory
         DESCRIPTION
             "The number of calls answered by the Hiper in last 24 hours."
         ::= { usrBetaObjs 4 }

    usrRouterMemoryUtilization  OBJECT-TYPE
         SYNTAX  Counter32
         ACCESS  read-only
         STATUS  mandatory
         DESCRIPTION
             "The memory utilization of the system."
         ::= { usrBetaObjs 5 }

    usrRouterUptime  OBJECT-TYPE
         SYNTAX  OCTET STRING (SIZE(0..400)) 
         ACCESS  read-only
         STATUS  mandatory
         DESCRIPTION
             "The router uptime."
         ::= { usrBetaObjs 6 }

    usrRouterCodeVersion  OBJECT-TYPE
         SYNTAX  OCTET STRING (SIZE(0..400)) 
         ACCESS  read-only
         STATUS  mandatory
         DESCRIPTION
             "The code version of Hiper Access Router Card."
         ::= { usrBetaObjs 7 }

    usrRouterEthInterfaceIngressPkts  OBJECT-TYPE
         SYNTAX  Counter32
         ACCESS  read-only
         STATUS  mandatory
         DESCRIPTION
             "The aggregate number of incoming packets on all ethernet interfaces."
         ::= { usrBetaObjs 8 }

    usrRouterEthInterfaceEgressPkts  OBJECT-TYPE
         SYNTAX  Counter32
         ACCESS  read-only
         STATUS  mandatory
         DESCRIPTION
             "The aggregate number of outgoing packets on all ethernet interfaces."
         ::= { usrBetaObjs 9 }

    usrBetaInfoTrap TRAP-TYPE
        ENTERPRISE  usrBetaTraps
        VARIABLES   {
    		usrChassisActiveCalls, 
    		usrChassisTotalPorts, 
    		usrChassisPortUtilization, 
    		usrChassisCallsInLast24Hrs,
    		usrRouterMemoryUtilization, 
    		usrRouterUptime,
    		usrRouterCodeVersion,
    		usrRouterEthInterfaceIngressPkts,
    		usrRouterEthInterfaceEgressPkts
        }
        DESCRIPTION     "This trap is generated periodically from the Beta sites and passed on to the 3Com Trap server so that performance of beta code can be monitored closely."
        --#TYPE "Alarm"
        ::= 1

    usrHealthTrapState  OBJECT-TYPE
         SYNTAX  INTEGER {
		enabled(1), 
		disabled(2) 
		}
         ACCESS  read-write
         STATUS  mandatory
         DESCRIPTION
             "Whether the Health Trap is enabled or disabled."
	 DEFVAL { disabled }
	 --CONFIGURABLE
         ::= { usrBetaObjs 10 }

    usrHealthTrapInterval  OBJECT-TYPE
         SYNTAX  INTEGER (1..1440)
         ACCESS  read-write
         STATUS  mandatory
         DESCRIPTION
             "The frequency in minutes the Health Trap is sent out."
	 DEFVAL { 60 }
	 --CONFIGURABLE
         ::= { usrBetaObjs 11 }

END         -- End USRBETA-MIB definitions
--
--	usr_chassis.mib - A MIB file for the Netserver gateway card
--                    Chassis MIB
--
--
-- Author:         Mike Redden
--
--
--  | Copyright (c) 1997 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-CHASSIS-MIB DEFINITIONS ::= BEGIN

	IMPORTS
	  Counter
                  FROM RFC1155-SMI
          OBJECT-TYPE
                  FROM RFC-1212
          DisplayString, usrChassis, UsrConfigStatus
                  FROM USR-DEFINITIONS-MIB;

	usrChassisConfigFileName OBJECT-TYPE
		SYNTAX      DisplayString
		ACCESS      read-write
		STATUS      mandatory
		DESCRIPTION		
		  "The name of a ConfigFile to read/write permanent
		   database records. If the value of this object is an
                   empty string, then the NMBA process uses the
                   default name `@file://Chassis.cfg'. "
	::= { usrChassis 1 }

	usrChassisCFMStatusFlag  OBJECT-TYPE
	 	SYNTAX	  UsrConfigStatus
		ACCESS      read-write
		STATUS      mandatory
		DESCRIPTION
		  "Setting the value of this object to `save' causes the values
		   of the ChassisSlotTable to be written out to the
                   current config file, which is stored in the 
                   usrChassisConfigFileName object. While the new
                   ConfigFile is being written, the NMBA process
		   will set the value of this flag to `saving''. Any
		   attempts to set the value while it is not `normal'
		   (i.e. the file is currently being written to the
		   ConfigFile) while result in a badValue error being
		   returned. Setting the value to `normal' will result in no
		   action."
	::= { usrChassis 2 }

	usrChassisChassisAwareness  OBJECT-TYPE
		SYNTAX   INTEGER {
			enabled(1),
			disabled(2)
			}
		ACCESS      read-write
		STATUS      mandatory
		DESCRIPTION
		  "The value of this object determines if
		   chassis awareness messages from the NMC are to be
                   handled or not.  If this object is set to
                   `enabled' then when a chassis awareness message
                   is received, the information contained within the
                   message is used to update the chassis
                   configuration. If this object is set to `disabled'
                   any chassis awareness messages received from the 
                   NMC are ignored, and the configuration of the 
                   chassis must be set statically through SNMP sets,
                   or CLI commands."
	        --CONFIGURABLE
	::= { usrChassis 3 }

	usrChassisSlotTable	OBJECT-TYPE
		SYNTAX SEQUENCE OF UsrChassisSlotEntry
		ACCESS not-accessible
		STATUS mandatory
		DESCRIPTION
                  "A table containing one row per slot in the chassis.  Each
		   row describes the characteristics of the slot"
	::= { usrChassis 4 }

	usrChassisSlotEntry OBJECT-TYPE
         SYNTAX  UsrChassisSlotEntry
         ACCESS  not-accessible
         STATUS  mandatory
         DESCRIPTION
            ""
         INDEX   { usrChassisSlot}

	::= { usrChassisSlotTable 1 }

	UsrChassisSlotEntry ::=
         SEQUENCE {
         usrChassisSlot
            INTEGER,
         usrChassisOwner
            INTEGER,
         usrChassisCardType
            INTEGER,
         usrChassisNumPorts
            INTEGER,
         usrChassisDescription
            DisplayString,
	     usrChassisType
  	        INTEGER,
         usrChassisConsole
            INTEGER
         }

	usrChassisSlot OBJECT-TYPE
         SYNTAX  INTEGER
	 ACCESS  not-accessible
         STATUS  mandatory
         DESCRIPTION
            "The slot number of this row."
	::= { usrChassisSlotEntry 1 }

	usrChassisOwner OBJECT-TYPE
		SYNTAX   INTEGER {
			no(1),
			yes(2),
			assigned(3)
			}
         ACCESS   read-write
         STATUS   mandatory
         DESCRIPTION
            "An indication if this slot's card has this Gateway card assigned
             as the owning gateway"
         --CONFIGURABLE
         ::= { usrChassisSlotEntry 2 }

	usrChassisCardType OBJECT-TYPE
		SYNTAX   INTEGER {
			empty(1),
			unknown(2),
			quadV32Modem(3),
			dualT1E1(4),
			genericQuadIModem(5),
			hdmsimulator(6),
			trGatewayNAC(7),
			x25GatewayNAC(8),
			dualV34ModemNAC(9),
			quadV32DigitalTerboModemNAC(10),
			quadV32AnalogTerboModemNAC(11),
			quadV32DigAnlTerboModemNAC(12),
			quadV34DigModemNAC(13),
			quadV34AnlModemNAC(14),
			quadV34DigAnlModemNAC(15),
			singleT1NAC(16),
			ethernetGatewayNAC(17),
			accessServer(18),
			i486TrGatewayNAC(19),
			i486EthernetGatewayNAC(20),
			genericQuadModem(21),
			dualRS232NAC(22),
			i486X25GatewayNAC(23),
			i486DXAPINAC(24),
			applicationServerNAC(25),
			iSDNGatewayNAC(26),
			iSDNpriT1NAC(27),
			clkedNetMgtCard(28),
			modemPoolManagementNAC(29),
			modemPoolNetserverNAC(30),
			modemPoolV34ModemNAC(31),
			modemPoolISDNNAC(32),
			nTServerNAC(33),
			quadV34DigitalG2NAC(34),
			quadV34AnalogG2NAC(35),
			quadV34DigAnlgG2NAC(36),
			nETServerFrameRelayNAC(37),
			nETServerTokenRingNAC(38),
			x2524ChannelNAC(39),
			highDensityModem(41),
			wirelessGatewayNAC(42),
			ciscoAS51NAC(43),
			enhancedAccessServer(44),
			enhancedISDNGatewayNAC(45),
			hdm24ChannelNAC(46),
			hdm30ChannelNAC(47),
			riscNetserverNAC(48)
			}
         ACCESS   read-write
         STATUS   mandatory
         DESCRIPTION
            "The ID of the card that is resident in this slot of
             the chassis."
         --CONFIGURABLE
         ::= { usrChassisSlotEntry 3 }

	usrChassisNumPorts OBJECT-TYPE
         SYNTAX  INTEGER
         ACCESS  read-write
         STATUS  mandatory
         DESCRIPTION
            "The number ports that are enabled on the card in this 
             chassis slot. This value will be determined when the the
	     card type for this slot is set, or when a chassis
             awareness message arrives updating this slot.  If the
             card type is empty, the number of ports is set to zero."
         --CONFIGURABLE
	::= { usrChassisSlotEntry 4 }

	usrChassisDescription OBJECT-TYPE
         SYNTAX  DisplayString (SIZE(0..32))
         ACCESS  read-only
         STATUS  mandatory
         DESCRIPTION
            "A string that decsribes the type of card in this chassis 
    		   slot."
	::= { usrChassisSlotEntry 5 }


	usrChassisType OBJECT-TYPE
		SYNTAX   INTEGER {
			static(1),
			dynamic(2)
			}
         ACCESS   read-write
         STATUS   mandatory
         DESCRIPTION
            "An indicator that tells if this slot's (row's) data was
             created statically by configuration, or dynamically by
             the receipt of chassis awareness information from the
             NMC.  Only static entries are saved to the configuration
             file.  Dynamic entries are saved as static entries with 
             an empty card type. If dynamic information is learned
             it replaces the information in a static entry.  A dynamic
             entry cannot be changed through the CLI or an SNMP set."
         ::= { usrChassisSlotEntry 6 }

    usrChassisConsole OBJECT-TYPE
        SYNTAX   INTEGER {
            no(1),
            yes(2)
            }
         ACCESS   read-write
         STATUS   mandatory
         DESCRIPTION
            "An indicator that tells if this slot supports a packet
         bus based console."
    DEFVAL { no }
         --CONFIGURABLE
         ::= { usrChassisSlotEntry 7 }

	usrChassisDSA  OBJECT-TYPE
		SYNTAX   INTEGER {
			enabled(1),
			disabled(2)
			}
		ACCESS      read-write
		STATUS      mandatory
		DESCRIPTION
		  "The value of this object determines if
		   the card is participating in the
		   dynamic slot assigment algorithm.
		   The default is disabled."
	        --CONFIGURABLE
	::= { usrChassis 5 }

	usrChassisDSAQueryReq  OBJECT-TYPE
		SYNTAX      Counter
		ACCESS      read-only
		STATUS      mandatory
		DESCRIPTION
		  "The number of DSA query requests from NMC seen by this card"
	::= { usrChassis 6 }

	usrChassisDSAQueryRsp  OBJECT-TYPE
		SYNTAX      Counter
		ACCESS      read-only
		STATUS      mandatory
		DESCRIPTION
		  "The number of DSA query responses sent by this card to NMC"
	::= { usrChassis 7 }

	usrChassisDSAServiceReq  OBJECT-TYPE
		SYNTAX      Counter
		ACCESS      read-only
		STATUS      mandatory
		DESCRIPTION
		  "The number of DSA service requests issued to this card"
	::= { usrChassis 8 }

	usrChassisDSAServiceAssignments  OBJECT-TYPE
		SYNTAX      Counter
		ACCESS      read-only
		STATUS      mandatory
		DESCRIPTION
		  "The number of DSA assignments performed by this card"
	::= { usrChassis 9 }

	usrChassisDSATraps  OBJECT-TYPE
		SYNTAX      Counter
		ACCESS      read-only
		STATUS      mandatory
		DESCRIPTION
		  "The number of DSA traps issued"
	::= { usrChassis 10 }

	usrChassisDSAInvalidRX  OBJECT-TYPE
		SYNTAX      Counter
		ACCESS      read-only
		STATUS      mandatory
		DESCRIPTION
		  "The number invalid DSA packets received"
	::= { usrChassis 11 }

    usrChassisWhenLastNMCQuery    OBJECT-TYPE
		SYNTAX		OCTET STRING (SIZE (12))
		ACCESS      read-only
		STATUS		mandatory
		DESCRIPTION
			"Time when the last NMC query packet was received"
	::= { usrChassis 12 }


	usrChassisDSARebalancing  OBJECT-TYPE
		SYNTAX   INTEGER {
			enabled(1),
			disabled(2)
			}
		ACCESS      read-write
		STATUS      mandatory
		DESCRIPTION
		  "The value of this object determines if
		   the card allows slot rebalancing when
		   participating in the dynamic slot assigment algorithm.
		   The default is enabled."
	        --CONFIGURABLE
	::= { usrChassis 13 }

	usrNMCSnmpForwarding  OBJECT-TYPE
		SYNTAX   INTEGER {
			enabled(1),
			disabled(2)
			}
		ACCESS      read-write
		STATUS      mandatory
		DESCRIPTION
		  "The value of this object determines if Hiper will
		   accept SNMP forwarded messages from the NMC over NM bus.
                   or CLI commands."
	        --CONFIGURABLE
	::= { usrChassis 14 }

	usrChassisModemNaming  OBJECT-TYPE
		SYNTAX   INTEGER {
			contiguous(1),
			noncontiguous(2)
			}
		ACCESS      read-write
		STATUS      mandatory
		DESCRIPTION
		  "The value of this object determines is having
		   is having contiguous modem naming or not"
	        --CONFIGURABLE
	::= { usrChassis 15 }

END         -- End usrChassis MIB definitions
-- MIB File Generated on 20-Mar-1997 at 16:01:21

PB-MIB DEFINITIONS ::= BEGIN

IMPORTS
   enterprises,
   Counter
      FROM RFC1155-SMI
   OBJECT-TYPE
      FROM RFC-1212;


usRobotics OBJECT IDENTIFIER ::= { enterprises 429 }

nas OBJECT IDENTIFIER ::= { usRobotics 1 }

pb OBJECT IDENTIFIER ::= { nas 12 }

pbCfg OBJECT IDENTIFIER ::= { pb 1 }

pbCfgTable OBJECT-TYPE
SYNTAX SEQUENCE OF PbCfgEntry
ACCESS not-accessible
STATUS mandatory
DESCRIPTION
"A table containing an configuration information for each 
Gateway NAC in the NAS chassis."
::= { pbCfg 1 }

pbCfgEntry OBJECT-TYPE
SYNTAX PbCfgEntry
ACCESS not-accessible
STATUS mandatory
DESCRIPTION
"There is one Configuration row for each Gateway Card in the 
NAS chassis."
INDEX { pbCfgIndex }
::= { pbCfgTable 1 }

PbCfgEntry ::=
SEQUENCE {
pbCfgIndex
    INTEGER,
pbCfgMaxSessions
    INTEGER
}

pbCfgIndex OBJECT-TYPE
SYNTAX INTEGER
ACCESS read-only
STATUS mandatory
DESCRIPTION
"A unique value for each Gateway Card in the chassis. The 
value of this object matches the value of the index of the 
corresponding Gateway Card's entry in the entity table of 
the chassis MIB."
::= { pbCfgEntry 1 }

pbCfgMaxSessions OBJECT-TYPE
SYNTAX INTEGER
ACCESS read-only
STATUS mandatory
DESCRIPTION
"This read-only object defines the maximum number of packet 
bus sessions supported by this entity. This value is used 
to determine the number of rows present in the 
pbSessionTable for this entity."
::= { pbCfgEntry 2 }

pbSession OBJECT IDENTIFIER ::= { pb 2 }

pbSessionTable OBJECT-TYPE
SYNTAX SEQUENCE OF PbSessionEntry
ACCESS not-accessible
STATUS mandatory
DESCRIPTION
"The Packet Bus Session table contains an entry for each 
manageable Gateway NAC in the chassis.  It provides a means 
to configure packet bus connections and determine the 
status of the defined connections.  This table resides in 
the NAC and can be impemented as either a dense or sparse 
table."
::= { pbSession 1 }

pbSessionEntry OBJECT-TYPE
SYNTAX PbSessionEntry
ACCESS not-accessible
STATUS mandatory
DESCRIPTION
"There is an row for each Packet Bus connection."
INDEX { pbSessionEntityIndex, pbSessionIndex }
::= { pbSessionTable 1 }

PbSessionEntry ::=
SEQUENCE {
pbSessionEntityIndex
    INTEGER,
pbSessionIndex
    INTEGER,
pbSessionDestSlot
    INTEGER,
pbSessionDestChan
    INTEGER,
pbSessionDestSess
    INTEGER,
pbSessionRowState
    INTEGER,
pbSessionStatus
    INTEGER,
pbSessionReqStatus
    INTEGER,
pbSessionLastRequest
    INTEGER,
pbSessionPktSents
    Counter,
pbSessionPktRcvds
    Counter,
pbSessionPktSize
    INTEGER,
pbSessionBusTimeOuts
    Counter,
pbSessionErrorStatus
    INTEGER
}

pbSessionEntityIndex OBJECT-TYPE
SYNTAX INTEGER
ACCESS read-only
STATUS mandatory
DESCRIPTION
"A unique value for each entity in the chassis.  The value 
of this object matches the value of the index of the 
corresponding entry in the entity table of the chassis MIB."
::= { pbSessionEntry 1 }

pbSessionIndex OBJECT-TYPE
SYNTAX INTEGER
ACCESS read-only
STATUS mandatory
DESCRIPTION
"An index that uniquely identifies the packet bus session 
for this entity."
::= { pbSessionEntry 2 }

pbSessionDestSlot OBJECT-TYPE
SYNTAX INTEGER (1..64)
ACCESS read-write
STATUS mandatory
DESCRIPTION
"A number that identifies the slot of the entity in the 
chassis to which a packet bus session has been assigned."
::= { pbSessionEntry 3 }

pbSessionDestChan OBJECT-TYPE
SYNTAX INTEGER (1..255)
ACCESS read-write
STATUS mandatory
DESCRIPTION
"A number that identifies a particular entity in a slot."
::= { pbSessionEntry 4 }

pbSessionDestSess OBJECT-TYPE
SYNTAX INTEGER (0..16320)
ACCESS read-only
STATUS mandatory
DESCRIPTION
"A number that identifies the particular session from the 
other  communicating Gateway."
::= { pbSessionEntry 5 }

pbSessionRowState OBJECT-TYPE
SYNTAX INTEGER{
  free(1),
  used(2)
}
ACCESS read-write
STATUS mandatory
DESCRIPTION
"Set availability for this row of packet bus session. 
Default=free(1)."
::= { pbSessionEntry 6 }

pbSessionStatus OBJECT-TYPE
SYNTAX INTEGER{
  unassigned(1),
  assigned(2),
  connected(3)
}
ACCESS read-only
STATUS mandatory
DESCRIPTION
"Displays the current status of the packet bus session.  A 
status of Unassigned coupled with a state of used indicates 
that a packet bus failure has occured."
::= { pbSessionEntry 7 }

pbSessionReqStatus OBJECT-TYPE
SYNTAX INTEGER{
  disconnected(1),
  connected(2)
}
ACCESS read-write
STATUS mandatory
DESCRIPTION
"Used to assign or delete a session between the entities 
specified by the table indecies. A request connect is a 
issue of packet bus session link start, and a request 
disconnect is a issue of packet bus session link terminate. 
Default=disconnected(1)."
::= { pbSessionEntry 8 }

pbSessionLastRequest OBJECT-TYPE
SYNTAX INTEGER{
  unknown(1),
  open(2),
  close(3),
  listen(4),
  dial(5),
  disconnect(6),
  transmit(7),
  receive(8),
  setMode(9),
  query(10),
  flush(11),
  kill(12),
  reserve(13),
  answer(14),
  attach(15)
}
ACCESS read-only
STATUS optional
DESCRIPTION
"Indicates the type of communications contained in the last 
packet sent to the destination entity."
::= { pbSessionEntry 9 }

pbSessionPktSents OBJECT-TYPE
SYNTAX Counter
ACCESS read-only
STATUS mandatory
DESCRIPTION
"A counter that indicates number of packets that have been 
sent."
::= { pbSessionEntry 10 }

pbSessionPktRcvds OBJECT-TYPE
SYNTAX Counter
ACCESS read-only
STATUS mandatory
DESCRIPTION
"A counter that indicates number of packets that have been 
received."
::= { pbSessionEntry 11 }

pbSessionPktSize OBJECT-TYPE
SYNTAX INTEGER
ACCESS read-only
STATUS mandatory
DESCRIPTION
"A number that indicates the packet size of the current or 
last established session."
::= { pbSessionEntry 12 }

pbSessionBusTimeOuts OBJECT-TYPE
SYNTAX Counter
ACCESS read-only
STATUS mandatory
DESCRIPTION
"A counter that indicates number of packet bus timeout that 
have occurred."
::= { pbSessionEntry 13 }

pbSessionErrorStatus OBJECT-TYPE
SYNTAX INTEGER{
  noError(1),
  invalidParm(2),
  socketNotOpened(3),
  noMoreSocket(4),
  connectionExist(5),
  connectionFailed(6),
  noMoreConnObj(7),
  noActiveConn(8),
  ackWaitTimeout(9),
  hwNakRcvd(10),
  otherBusError(11),
  linkStartRcvd(12),
  outOfSeqFrame(13),
  noMemory(14),
  nullPointer(15),
  invalidBlock(16),
  notInitialized(17),
  failedToRecv(18),
  invalidMsgType(19),
  exceedMaxSends(20),
  connectionReset(21),
  socketClosed(22),
  uiReqPending(23),
  heartbeatTimeout(24),
  remoteBusy(25),
  localBusy(26),
  noResponse(27),
  linkdownNoTx(28),
  noDataToTx(29),
  txPreAck(30),
  txTardyAck(31),
  txBusTimeOut(32),
  rxBusTimeOut(33),
  txTAL(34),
  rxTAL(35),
  txMasterTimeOut(36),
  clkVanished(37),
  clkReturned(38),
  shutdown(39),
  frameError(40),
  xIDTimeOut(41),
  recvLSinInfoTransferState(42),
  recvIFrameWithWrongSeq(43),
  rxMsgBufferOverflow(44),
  linkDown(45),
  listenFailed(46),
  listenRcvFailed(47),
  dtrDrop(48),
  answerFailed(49),
  openFailed(50),
  closeFailed(51),
  readFailed(52),
  writeFailed(53),
  autoParityFailed(54),
  setmodeFailed(55),
  badDataBase(56),
  padStreamsError(57),
  padError(58)
}
ACCESS read-only
STATUS mandatory
DESCRIPTION
"Error return status from last packet command."
::= { pbSessionEntry 14 }

pbTrapEna OBJECT IDENTIFIER ::= { pb 3 }

pbTrapEnaTable OBJECT-TYPE
SYNTAX SEQUENCE OF PbTrapEnaEntry
ACCESS not-accessible
STATUS mandatory
DESCRIPTION
"A table containing an enable for each trap that a 
manageable Gateway entity is capable of generating."
::= { pbTrapEna 1 }

pbTrapEnaEntry OBJECT-TYPE
SYNTAX PbTrapEnaEntry
ACCESS not-accessible
STATUS mandatory
DESCRIPTION
"There is one Gateway trap enable row for each Gateway card 
in the NAS chassis."
INDEX { pbTrapEnaIndex, pbTrapSessionIndex }
::= { pbTrapEnaTable 1 }

PbTrapEnaEntry ::=
SEQUENCE {
pbTrapEnaIndex
    INTEGER,
pbTrapSessionIndex
    INTEGER,
pbTrapEnaSessActive
    INTEGER,
pbTrapEnaPktBusCongest
    INTEGER,
pbTrapEnaPktBusSessLost
    INTEGER,
pbTrapEnaSessionInactive
    INTEGER,
pbTrapEnaSessionError
    INTEGER
}

pbTrapEnaIndex OBJECT-TYPE
SYNTAX INTEGER
ACCESS read-only
STATUS mandatory
DESCRIPTION
"A unique value for each Gateway Card in the chassis. The 
value of this object matches the value of the index of the 
corresponding Gateway Card's entry in the entity table of 
the chassis MIB."
::= { pbTrapEnaEntry 1 }

pbTrapSessionIndex OBJECT-TYPE
SYNTAX INTEGER
ACCESS read-only
STATUS mandatory
DESCRIPTION
"A value that identifies the packet bus session for trap 
enable/disable."
::= { pbTrapEnaEntry 2 }

pbTrapEnaSessActive OBJECT-TYPE
SYNTAX INTEGER{
  enableTrap(1),
  disableAll(2),
  enableLog(3),
  enableAll(4)
}
ACCESS read-write
STATUS mandatory
DESCRIPTION
"An object which enables or disables the Active Session 
trap."
::= { pbTrapEnaEntry 3 }

pbTrapEnaPktBusCongest OBJECT-TYPE
SYNTAX INTEGER{
  enableTrap(1),
  disableAll(2),
  enableLog(3),
  enableAll(4)
}
ACCESS read-write
STATUS mandatory
DESCRIPTION
"An object to enable or disable the Packet Bus Congestion 
trap. The Packet Bus Congestion trap is generated when a 
valid packet bus session is in progress but either the 
Modem or the Gateway packet bus driver is experiencing 
congestion problem."
::= { pbTrapEnaEntry 4 }

pbTrapEnaPktBusSessLost OBJECT-TYPE
SYNTAX INTEGER{
  enableTrap(1),
  disableAll(2),
  enableLog(3),
  enableAll(4)
}
ACCESS read-write
STATUS mandatory
DESCRIPTION
"An object to enable or disable the trap that is generated 
when a valid Packet Bus session has been lost."
::= { pbTrapEnaEntry 5 }

pbTrapEnaSessionInactive OBJECT-TYPE
SYNTAX INTEGER{
  enableTrap(1),
  disableAll(2),
  enableLog(3),
  enableAll(4)
}
ACCESS read-write
STATUS mandatory
DESCRIPTION
"An object to enable or disable a trap which is generated 
when a request is made to change a packet bus session from 
the active to inactive state."
::= { pbTrapEnaEntry 6 }

pbTrapEnaSessionError OBJECT-TYPE
SYNTAX INTEGER{
  enableTrap(1),
  disableAll(2),
  enableLog(3),
  enableAll(4)
}
ACCESS read-write
STATUS mandatory
DESCRIPTION
"An object which enables or disables the packet bus session 
error trap."
::= { pbTrapEnaEntry 7 }

END
-- MIB File Generated on 15-Aug-1996 at 10:17:46

PBDG-MIB DEFINITIONS ::= BEGIN

IMPORTS
   enterprises,
   Counter
      FROM RFC1155-SMI
   OBJECT-TYPE
      FROM RFC-1212;


usRobotics OBJECT IDENTIFIER ::= { enterprises 429 }

nas OBJECT IDENTIFIER ::= { usRobotics 1 }

pbdg OBJECT IDENTIFIER ::= { nas 14 }

pbdgDatagram OBJECT IDENTIFIER ::= { pbdg 1 }

pbdgDatagramTable OBJECT-TYPE
SYNTAX SEQUENCE OF PbdgDatagramEntry
ACCESS not-accessible
STATUS mandatory
DESCRIPTION
"A table containing configuration information for each NAC 
in the NAS chassis that supports packet bus datagrams."
::= { pbdgDatagram 1 }

pbdgDatagramEntry OBJECT-TYPE
SYNTAX PbdgDatagramEntry
ACCESS not-accessible
STATUS mandatory
DESCRIPTION
"There is one Configuration row for each Card in the NAS 
chassis that supports packet bus datagrams."
INDEX { pbdgDatagramIndex }
::= { pbdgDatagramTable 1 }

PbdgDatagramEntry ::=
SEQUENCE {
pbdgDatagramIndex
    INTEGER,
pbdgDatagramSentPkts
    Counter,
pbdgDatagramRcvdPkts
    Counter,
pbdgDatagramBusTimeOuts
    Counter,
pbdgDatagramErrorStatus
    INTEGER,
pbdgDatagramClockStatus
    INTEGER
}

pbdgDatagramIndex OBJECT-TYPE
SYNTAX INTEGER
ACCESS read-only
STATUS mandatory
DESCRIPTION
"A unique value for each card in the chassis. The value of 
this object matches the value of the index of the 
corresponding card's entry in the entity table of the 
chassis MIB."
::= { pbdgDatagramEntry 1 }

pbdgDatagramSentPkts OBJECT-TYPE
SYNTAX Counter
ACCESS read-only
STATUS mandatory
DESCRIPTION
"This object contains the number of packet bus datagrams 
sent by this entity."
::= { pbdgDatagramEntry 2 }

pbdgDatagramRcvdPkts OBJECT-TYPE
SYNTAX Counter
ACCESS read-only
STATUS mandatory
DESCRIPTION
"This object contains the number of packet bus datagrams 
received by this entity."
::= { pbdgDatagramEntry 3 }

pbdgDatagramBusTimeOuts OBJECT-TYPE
SYNTAX Counter
ACCESS read-only
STATUS mandatory
DESCRIPTION
"This object contains the number of packet bus timeouts 
experienced by this entity."
::= { pbdgDatagramEntry 4 }

pbdgDatagramErrorStatus OBJECT-TYPE
SYNTAX INTEGER{
  noError(1),
  invalidParm(2),
  socketNotOpened(3),
  noMoreSocket(4),
  ackWaitTimeout(9),
  hwNakRcvd(10),
  otherBusError(11),
  noMemory(14),
  nullPointer(15),
  notInitialized(17),
  failedToRecv(18),
  invalidMsgType(19),
  socketClosed(22),
  noResponse(27),
  noDataToTx(29),
  txPreAck(30),
  txTardyAck(31),
  txBusTimeOut(32),
  rxBusTimeOut(33),
  txTAL(34),
  rxTAL(35),
  txMasterTimeOut(36),
  clkVanished(37),
  clkReturned(38),
  shutdown(39),
  frameError(40),
  xIDTimeOut(41),
  invalidAckMeRtnMarker(45),
  invalidFragmentOffset(46),
  maxRxMsgLengthExceeded(47)
}
ACCESS read-only
STATUS mandatory
DESCRIPTION
"This object reflects the current error status of this 
entity."
::= { pbdgDatagramEntry 5 }

pbdgDatagramClockStatus OBJECT-TYPE
SYNTAX INTEGER{
  notSupported(1),
  clockMaster(2),
  clockSlave(3),
  noClockPresent(4)
}
ACCESS read-only
STATUS mandatory
DESCRIPTION
"This object defines the current status of the packet bus 
clock."
::= { pbdgDatagramEntry 6 }

pbdgCfg OBJECT IDENTIFIER ::= { pbdg 2 }

pbdgCfgTable OBJECT-TYPE
SYNTAX SEQUENCE OF PbdgCfgEntry
ACCESS not-accessible
STATUS mandatory
DESCRIPTION
"A table containing configuration information for each NAC 
in the NAS chassis that supports packet bus datagrams."
::= { pbdgCfg 1 }

pbdgCfgEntry OBJECT-TYPE
SYNTAX PbdgCfgEntry
ACCESS not-accessible
STATUS mandatory
DESCRIPTION
"There is one Configuration row for each Card in the NAS 
chassis that supports packet bus datagrams."
INDEX { pbdgCfgIndex }
::= { pbdgCfgTable 1 }

PbdgCfgEntry ::=
SEQUENCE {
pbdgCfgIndex
    INTEGER,
pbdgCfgMasterClock
    INTEGER,
pbdgCfgClockLossEvent
    INTEGER,
pbdgCfgClockRestoreEvent
    INTEGER
}

pbdgCfgIndex OBJECT-TYPE
SYNTAX INTEGER
ACCESS read-only
STATUS mandatory
DESCRIPTION
"A unique value for each card in the chassis.  The value of 
this object matches the value of the index of the 
corresponding card's entry in the entity table of the 
chassis"
::= { pbdgCfgEntry 1 }

pbdgCfgMasterClock OBJECT-TYPE
SYNTAX INTEGER{
  notSupported(1),
  enable(2),
  disable(3)
}
ACCESS read-write
STATUS mandatory
DESCRIPTION
"This object is used to disable the ability for a NAC to act 
as packet bus clock master.Default =enable(2)."
::= { pbdgCfgEntry 2 }

pbdgCfgClockLossEvent OBJECT-TYPE
SYNTAX INTEGER{
  enableTrap(1),
  disableAll(2),
  enableLog(3),
  enableAll(4)
}
ACCESS read-write
STATUS mandatory
DESCRIPTION
"This object is used to disable the ability for a NAC to 
report when the packet bus clock has been lost.  Default = 
disableAll(2)."
::= { pbdgCfgEntry 3 }

pbdgCfgClockRestoreEvent OBJECT-TYPE
SYNTAX INTEGER{
  enableTrap(1),
  disableAll(2),
  enableLog(3),
  enableAll(4)
}
ACCESS read-write
STATUS mandatory
DESCRIPTION
"This object is used to disable the ability for a NAC to 
report when the packet bus clock has been restored.  
Default = disableAll(2)."
::= { pbdgCfgEntry 4 }

END


--
--    usr_gwc_bsp.mib - The USR GWC BSP mib
--
--
-- Author:         <Sanil Puthiyandyil>
--
--
--  | Copyright (c) 1995 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-GWCBSP-MIB DEFINITIONS ::= BEGIN

          IMPORTS
               IpAddress
                    FROM RFC1155-SMI
               OBJECT-TYPE
                    FROM RFC-1212
                usrGWCBSP, UsrConfigStatus 
                    FROM USR-DEFINITIONS-MIB;


			usrGWCBSPProductCode OBJECT-TYPE
				SYNTAX      OCTET STRING (SIZE(3))
				ACCESS      read-only
				STATUS      mandatory
				DESCRIPTION
						"The Code number assigned for the product"
			::= { usrGWCBSP 1}

			usrGWCBSPHWVersion OBJECT-TYPE
				SYNTAX      OCTET STRING (SIZE(2))
				ACCESS      read-only
				STATUS      mandatory
				DESCRIPTION
						"Hardware version number"
			::= { usrGWCBSP 2}


			usrGWCBSPSerialNumber OBJECT-TYPE
				SYNTAX      OCTET STRING (SIZE(8))
				ACCESS      read-only
				STATUS      mandatory
				DESCRIPTION
						"Serial number of the product"
			::= { usrGWCBSP 3}


			usrGWCBSPCardID OBJECT-TYPE
				SYNTAX      INTEGER
				ACCESS      read-only
				STATUS      mandatory
				DESCRIPTION
						"Assigned card ID"
			::= { usrGWCBSP 4}


			usrGWCBSPFeatureKey OBJECT-TYPE
				SYNTAX      OCTET STRING (SIZE(4))
				ACCESS      read-only
				STATUS      mandatory
				DESCRIPTION
						"Bitmap of the features supported in the product"
			::= { usrGWCBSP 5}


			usrGWCBSPNICID OBJECT-TYPE
				SYNTAX      INTEGER
				ACCESS      read-only
				STATUS      mandatory
				DESCRIPTION
						"NIC card Identifier"
			::= { usrGWCBSP 6}


			usrGWCBSPNICName OBJECT-TYPE
				SYNTAX      OCTET STRING (SIZE(0..128))
				ACCESS      read-only
				STATUS      mandatory
				DESCRIPTION
						"NIC card name"
			::= { usrGWCBSP 7}

			usrGWCBSPNACID OBJECT-TYPE
				SYNTAX      INTEGER
				ACCESS      read-only
				STATUS      mandatory
				DESCRIPTION
						"NAC card Identifier"
			::= { usrGWCBSP 8}


			usrGWCBSPNACName OBJECT-TYPE
				SYNTAX      OCTET STRING (SIZE(0..128))
				ACCESS      read-only
				STATUS      mandatory
				DESCRIPTION
						"NAC Card Name "
			::= { usrGWCBSP 9}



			usrGWCBSPCPUType OBJECT-TYPE
				SYNTAX      OCTET STRING (SIZE(0..64))
				ACCESS      read-only
				STATUS      mandatory
				DESCRIPTION
						"CPU of the product"
			::= { usrGWCBSP 10}



			usrGWCBSPCPUSpeed OBJECT-TYPE
				SYNTAX      INTEGER
				ACCESS      read-only
				STATUS      mandatory
				DESCRIPTION
						"The speed in Mhz in which the CPU runs "
			::= { usrGWCBSP 11}

			


			usrGWCBSPBootMode OBJECT-TYPE
				SYNTAX      INTEGER {
										flash(0),
										network(1)
									}

				ACCESS      read-write
				STATUS      mandatory
				DESCRIPTION
						"This variable decides the booting type. The
						 possible booting types are FLASH ( the boot image
						 is taken from the flash memory) or NETWORK (the 
						 boot image is downloaded from the network"
				--CONFIGURABLE
			::= { usrGWCBSP 12}


			usrGWCBSPIPConfigSource OBJECT-TYPE
				SYNTAX      INTEGER  {
										static(0),
										bootp(1)
									 }
				ACCESS      read-write
				STATUS      mandatory
				DESCRIPTION
						"The IP configuration source"
				--CONFIGURABLE
			::= { usrGWCBSP 13}


			usrGWCBSPIPTable OBJECT-TYPE
				SYNTAX SEQUENCE OF UsrGWCBSPIPEntry
				ACCESS  not-accessible
				STATUS  mandatory
				DESCRIPTION
					" IP Intarface Table"
				::= { usrGWCBSP 14 }
 
			usrGWCBSPIPEntry OBJECT-TYPE
				SYNTAX  UsrGWCBSPIPEntry
				ACCESS  not-accessible
				STATUS  mandatory
				DESCRIPTION
					"IP interface Table"
				INDEX   { usrGWCBSPInterfaceIndex   }
				::= { usrGWCBSPIPTable 1 }
	 
			UsrGWCBSPIPEntry  ::=
			   SEQUENCE	{
				usrGWCBSPInterfaceIndex
					OCTET STRING (SIZE(0..16)),
				usrGWCBSPTFTPServer
					IpAddress, 
				usrGWCBSPIPAddress 
					IpAddress,
				usrGWCBSPIPGateway 
					IpAddress,
				usrGWCBSPNetMask 
					IpAddress,
				usrGWCBSPCrashDumpFile 
					OCTET STRING (SIZE(0..128)),
				usrGWCBSPNetworkFile 
					OCTET STRING (SIZE(0..128)),
				usrGWCBSPTFTPStatus
					INTEGER
			   }



			usrGWCBSPInterfaceIndex OBJECT-TYPE
				SYNTAX      OCTET STRING (SIZE(0..16))
				ACCESS      not-accessible
				STATUS      mandatory
				DESCRIPTION
						"The boot interface of the product. The possible
						values are eth:1 or eth:2"
			::= { usrGWCBSPIPEntry 1}


			usrGWCBSPTFTPServer OBJECT-TYPE
				SYNTAX      IpAddress 
				ACCESS      read-write
				STATUS      mandatory
				DESCRIPTION
						"TFTP server used to down load the application 
						image or upload crashdump file"
				--CONFIGURABLE
			::= { usrGWCBSPIPEntry 2}



			usrGWCBSPIPAddress OBJECT-TYPE
				SYNTAX      IpAddress
				ACCESS      read-write
				STATUS      mandatory
				DESCRIPTION
						"IP address of the selected interface"
				--CONFIGURABLE
			::= { usrGWCBSPIPEntry 3}


			usrGWCBSPIPGateway OBJECT-TYPE
				SYNTAX      IpAddress
				ACCESS      read-write
				STATUS      mandatory
				DESCRIPTION
						"IP gateway for the selected interface"
				--CONFIGURABLE
			::= { usrGWCBSPIPEntry 4}



			usrGWCBSPNetMask OBJECT-TYPE
				SYNTAX      IpAddress
				ACCESS      read-write
				STATUS      mandatory
				DESCRIPTION
						"IP netmask of the selected interface"
				--CONFIGURABLE
			::= { usrGWCBSPIPEntry 5}

			usrGWCBSPCrashDumpFile OBJECT-TYPE
				SYNTAX      OCTET STRING (SIZE(0..128))
				ACCESS      read-write
				STATUS      mandatory
				DESCRIPTION
						"File name to which the crashdump will be uploaded"
				--CONFIGURABLE
			::= { usrGWCBSPIPEntry 6}


			usrGWCBSPNetworkFile OBJECT-TYPE
				SYNTAX      OCTET STRING (SIZE(0..128))
				ACCESS      read-write
				STATUS      mandatory
				DESCRIPTION
						"The download application image file name"
				--CONFIGURABLE
			::= { usrGWCBSPIPEntry 7}

            usrGWCBSPTFTPStatus OBJECT-TYPE
                SYNTAX      INTEGER {
                                        never(0),
                                        once(1),
                                        always(2)
                                    }
 
                ACCESS      read-write
                STATUS      mandatory
                DESCRIPTION
                        "TFTP download config type"
				--CONFIGURABLE
            ::= { usrGWCBSPIPEntry 8}
 

			usrGWCBSPCrashEnable OBJECT-TYPE
				SYNTAX      INTEGER {
										disable(0),
										enable(1)
									}
				ACCESS      read-write
				STATUS      mandatory
				DESCRIPTION
						"Says whether the crashupload option is Enabled or
						Disabled"
				--CONFIGURABLE
			::= { usrGWCBSP 15}


			usrGWCBSPDiag OBJECT-TYPE
				SYNTAX      INTEGER {
										disable(0),
										enable(1)
									}
				ACCESS      read-write
				STATUS      mandatory
				DESCRIPTION
						"To enable or disable Mfg Diagnostics"
				--CONFIGURABLE
			::= { usrGWCBSP 16}

			usrGWCBSPDipSwitches OBJECT-TYPE
				SYNTAX      OCTET STRING (SIZE(0..512))
				ACCESS      read-only
				STATUS      mandatory
				DESCRIPTION
						"The current DIP swicth settings"
			::= { usrGWCBSP 17}
	

			usrGWCBSPCrashDump OBJECT-TYPE
				SYNTAX      OCTET STRING (SIZE(0..1400))
				ACCESS      read-only
				STATUS      mandatory
				DESCRIPTION
						"Information about the previous crash"
				--CONFIGURABLE
			::= { usrGWCBSP 18}


			usrGWCBSPInterface OBJECT-TYPE
				SYNTAX      OCTET STRING (SIZE(0..16))
				ACCESS      read-write
				STATUS      mandatory
				DESCRIPTION
						"The boot interface of the product. The possible
						values are eth:1 or eth:2"
				--CONFIGURABLE
			::= { usrGWCBSP 19}

			usrGWCBSPCrashDumpReset OBJECT-TYPE
				SYNTAX      INTEGER {
										disable(0),
										enable(1)
									}
				ACCESS      read-write
				STATUS      mandatory
				DESCRIPTION
						"To Reset the Last Crash Dump"
			::= { usrGWCBSP 20}

			usrGWCBSPCommandLineParameters OBJECT-TYPE
				SYNTAX      OCTET STRING (SIZE(0..127))
				ACCESS      read-write
				STATUS      mandatory
				DESCRIPTION
					"Contains the command line parameters which are passed to the router at startup"
				--CONFIGURABLE
			::= { usrGWCBSP 21}

			 usrGWCBSPCFMStatusFlag OBJECT-TYPE
                SYNTAX      UsrConfigStatus
                ACCESS      read-write
                STATUS      mandatory
                DESCRIPTION
                    "This variable controls saving and loading of configuration
                     information for the bsp manager Module. The value can
                     be set to either save or load by a management station. The other
                     values indicate if any configuration operation and what type
                     is in progress."
                --CONFIGURABLE
            ::= { usrGWCBSP 22 }

			 usrGWCBSPKernelVersion OBJECT-TYPE
                SYNTAX      INTEGER
                ACCESS      read-only
                STATUS      mandatory
                DESCRIPTION
                        "The Kernel Version"     
            ::= { usrGWCBSP 23}

 

END

--
--	usr_atm_tc.mib - A MIB file for the Netserver gateway card 
--                       ATM Textual Conventions
--                        
--
--
-- Author:         Mike Redden
--
--
--  | Copyright (c) 1997 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--
               ATM-TC-MIB DEFINITIONS ::= BEGIN

               IMPORTS
--  OBJECT-IDENTITY,
                  MODULE-IDENTITY,
                  TimeTicks
                      FROM SNMPv2-SMI
		  mib-2
		      FROM RFC1213-MIB
                  TEXTUAL-CONVENTION
                      FROM SNMPv2-TC;

               atmTC OBJECT IDENTIFIER ::= { mib-2 37 }

               atmTCMIB MODULE-IDENTITY
                    LAST-UPDATED "9701080200Z"
                    ORGANIZATION "IETF AToMMIB Working Group"
                    CONTACT-INFO
                      "          Michael Noto
                        Postal:  Network Equipment Technologies
                                 800 Saginaw Drive RM 21.1.111
                                 Redwood City, CA 94063
                                 USA
                        Tel:     +1 415 569-7134
                        E-mail:  mike_noto@net.com

                                 Ethan Mickey Spiegel
                        Postal:  Cisco Systems
                                 170 W. Tasman Dr.
                                 San Jose, CA 95134
                                 USA
                        Tel:     +1 408 526 6408
                        E-mail:  mspiegel@cisco.com

                                 Kaj Tesink
                        Postal:  Bell Communications Research
                                 331 Newman Springs Road
                                 Red Bank, NJ 07701
                                 USA
                        Tel:     +1 908 758 5254
                        Fax:     +1 908 758 4177
                        E-mail:  kaj@cc.bellcore.com"
                    DESCRIPTION
                     "This MIB Module provides Textuanl Coventions
                     and OBJECT-IDENTITY Objects to be used by
                     ATM systems."
                    ::= { atmTC 3 } -- atmMIB 3
                                    -- See [14].


               -- The Textual Conventions defined below are organized
               -- alphabetically


               AtmAddr ::= TEXTUAL-CONVENTION
                       DISPLAY-HINT "1x"
                       STATUS  current
                       DESCRIPTION
                           "The ATM address used by the network entity.
                           The address types are: no address (0 octets),
                           E.164 (8 octets), and NSAP (20 octets).
                           Note: The E.164 address is encoded in BCD
                           format."
                      SYNTAX   OCTET STRING (SIZE(0|8|20))


              AtmConnCastType ::= TEXTUAL-CONVENTION
                      STATUS  current
                      DESCRIPTION
                        "The type of topology of a connection (point-
                        to-point, point-to-multipoint). In the case
                        of point-to-multipoint, the orientation of
                        this VPL or VCL in the connection.
                        On a host:
                        - p2mpRoot indicates that the host
                          is the root of the p2mp connection.
                        - p2mpLeaf indicates that the host
                          is a leaf of the p2mp connection.
                        On a switch:
                        - p2mpRoot indicates that cells received
                          by the switching fabric from the interface
                          are from the root of the p2mp connection.
                        - p2mpLeaf indicates that cells transmitted
                          to the interface from the switching fabric
                          are to the leaf of the p2mp connection."
                      SYNTAX   INTEGER {
                         p2p(1),
                         p2mpRoot(2),
                         p2mpLeaf(3)
                         }

              AtmConnKind ::= TEXTUAL-CONVENTION
                      STATUS  current
                      DESCRIPTION
                          "The use of call control. The use is as
                          follows:
                             pvc(1)
                                Virtual link of a PVC. Should not be
                                used in an PVC/SVC (i.e., SPVC)
                                crossconnect.
                             svcIncoming(2)
                                Virtual link established after a
                                received signaling request to setup
                                an SVC.
                             svcOutgoing(3)
                                Virtual link established after a
                                transmitted or forwarded signaling
                                request to setup an SVC.
                             spvcInitiator(4)
                                Virtual link at the PVC side of an
                                SVC/PVC crossconnect, where the
                                switch is the initiator of the SPVC
                                setup.
                             spvcTarget(5)
                                Virtual link at the PVC side of an
                                SVC/PVC crossconnect, where the
                                switch is the target of the SPVC
                                setup.

                          An spvcInitiator is always cross-connected to
                          an svcOutgoing, and an spvcTarget is always
                          cross-connected to an svcIncoming."
                     SYNTAX   INTEGER {
                        pvc(1),
                        svcIncoming(2),
                        svcOutgoing(3),
                        spvcInitiator(4),
                        spvcTarget(5)
                        }

                 AtmIlmiNetworkPrefix ::= TEXTUAL-CONVENTION
                     STATUS   current
                     DESCRIPTION
                         "A network prefix used for ILMI address
                         registration.  In the case of ATM endsystem
                         addresses (AESAs), the network prefix is the first
                         13 octets of the address which includes the AFI,
                         IDI, and HO-DSP fields.  In the case of native
                         E.164 addresses, the network prefix is the entire
                         E.164 address encoded in 8 octets, as if it were
                         an E.164 IDP in an ATM endsystem address
                         structure."
                     REFERENCE
                         "ATM Forum ILMI 4.0 Section 9,
                          ATM Forum UNI Signalling 4.0 Section 3"
                     SYNTAX   OCTET STRING (SIZE(8|13))

             AtmInterfaceType ::= TEXTUAL-CONVENTION
                     STATUS       current
                     DESCRIPTION
                         "The connection setup procedures used for the
                         identified interface.

                         Other: Connection setup procedures other than
                            those listed below.

                         Auto-configuration:
                            Indicates that the connection setup
                            procedures are to be determined dynamically,
                            or that determination has not yet been
                            completed. One such mechanism is via ATM
                            Forum ILMI auto-configuration procedures.

                         ITU-T DSS2:
                         -  ITU-T Recommendation Q.2931, Broadband
                            Integrated Service Digital Network (B-ISDN)
                            Digital Subscriber Signalling System No.2
                            (DSS2) User-Network Interface (UNI) Layer 3
                            Specification for Basic Call/Connection
                            Control (September 1994) [5]
                         -  ITU-T Draft Recommendation Q.2961,
                            B-ISDN DSS 2 Support of Additional Traffic
                            Parameters (May 1995) [8]

                         -  ITU-T Draft Recommendation Q.2971,
                            B-ISDN DSS 2 User Network Interface Layer 3
                            Specification for Point-to-multipoint
                            Call/connection Control (May 1995) [9]

                         ATM Forum UNI 3.0:
                            ATM Forum, ATM User-Network Interface,
                            Version 3.0 (UNI 3.0) Specification,
                            (1994) [3].

                         ATM Forum UNI 3.1:
                            ATM Forum, ATM User-Network Interface,
                            Version 3.1 (UNI 3.1) Specification,
                            (November 1994) [4].

                         ATM Forum UNI Signalling 4.0:
                            ATM Forum, ATM User-Network Interface (UNI)
                            Signalling Specification Version 4.0,
                            af-sig-0061.000 (June 1996) [7].

                         ATM Forum IISP (based on UNI 3.0 or UNI 3.1) :
                            Interim Inter-switch Signaling Protocol
                            (IISP) Specification, Version 1.0,
                            af-pnni-0026.000, (December 1994) [10].

                         ATM Forum PNNI 1.0 :
                            ATM Forum, Private Network-Network Interface
                            Specification, Version 1.0, af-pnni-0055.000,
                            (March 1996) [6].

                         ATM Forum B-ICI:
                            ATM Forum, B-ICI Specification, Version 2.0,
                            af-bici-0013.002, (November 1995) [11].

                         ATM Forum UNI PVC Only:
                            An ATM Forum compliant UNI with the
                            signalling disabled.

                         ATM Forum NNI PVC Only:
                            An ATM Forum compliant NNI with the
                            signalling disabled."
                    SYNTAX  INTEGER  {
                              other(1),
                              autoConfig(2),
                              ituDss2(3),
                              atmfUni3Dot0(4),
                              atmfUni3Dot1(5),
                              atmfUni4Dot0(6),
                              atmfIispUni3Dot0(7),
                              atmfIispUni3Dot1(8),
                              atmfIispUni4Dot0(9),
                              atmfPnni1Dot0(10),
                              atmfBici2Dot0(11),
                              atmfUniPvcOnly(12),
                              atmfNniPvcOnly(13)  }

            AtmServiceCategory ::= TEXTUAL-CONVENTION
                    STATUS  current
                    DESCRIPTION
                        "The service category for a connection."
                   REFERENCE
                       "ATM Forum Traffic Management 4.0."
                  SYNTAX   INTEGER {
                     other(1),   -- none of the following
                     cbr(2),     -- constant bit rate
                     rtVbr(3),   -- real-time variable bit rate
                     nrtVbr(4),  -- non real-time variable bit rate
                     abr(5),     -- available bit rate
                     ubr(6)      -- unspecified bit rate
                     }

          AtmSigDescrParamIndex ::= TEXTUAL-CONVENTION
                  STATUS  current
                  DESCRIPTION
                      "The value of this object identifies a row in the
                      atmSigDescrParamTable. The value 0 signifies that
                      none of the signalling parameters defined in the
                      atmSigDescrParamTable are applicable."
                  SYNTAX  INTEGER (0..2147483647)

          AtmTrafficDescrParamIndex ::= TEXTUAL-CONVENTION
                  STATUS  current
                  DESCRIPTION
                      "The value of this object identifies a row in the
                      atmTrafficDescrParamTable. The value 0 signifies
                      that no row has been identified."
                  SYNTAX  INTEGER (0..2147483647)

          AtmVcIdentifier ::= TEXTUAL-CONVENTION
                  STATUS  current
                  DESCRIPTION
                      "The VCI value for a VCL. The maximum VCI value
                      cannot exceed the value allowable by
                      atmInterfaceMaxVciBits defined in ATM-MIB."
                  SYNTAX   INTEGER (0..65535)

          AtmVpIdentifier ::= TEXTUAL-CONVENTION
                  STATUS  current
                  DESCRIPTION
                      "The VPI value for a VPL or VCL. The value VPI=0
                      is only allowed for a VCL. For ATM UNIs supporting
                      VPCs the VPI value ranges from 1 to 255. For ATM
                      UNIs supporting VCCs the VPI value ranges from 0
                      to 255.  For ATM NNIs the VPI value ranges from 0
                      to 4095.  The maximum VPI value cannot exceed the
                      value allowable by atmInterfaceMaxVpiBits defined
                      in ATM-MIB."
                  SYNTAX    INTEGER (0..4095)

          AtmVorXAdminStatus ::= TEXTUAL-CONVENTION
                  STATUS  current
                  DESCRIPTION
                      "The value determines the desired administrative
                      status of a virtual link or cross-connect. The up
                      and down states indicate that the traffic flow is
                      enabled or disabled respectively on the virtual
                      link or cross-connect."
                  SYNTAX   INTEGER {
                     up(1),
                     down(2)
                      }

          AtmVorXLastChange ::= TEXTUAL-CONVENTION
                  STATUS  current
                  DESCRIPTION
                      "The value of MIB II's sysUpTime at the time this
                      virtual link or cross-connect entered its current
                      operational state. If the current state was
                      entered prior to the last re-initialization of the
                      agent then this object contains a zero value."
                  SYNTAX   TimeTicks

          AtmVorXOperStatus ::= TEXTUAL-CONVENTION
                  STATUS  current
                  DESCRIPTION
                      "The value determines the operational status of a
                      virtual link or cross-connect. The up and down
                      states indicate that the traffic flow is enabled
                      or disabled respectively on the virtual link or
                      cross-connect. The unknown state indicates that
                      the state of it cannot be determined. The state
                      will be down or unknown if the supporting ATM
                      interface(s) is down or unknown respectively."
                  SYNTAX   INTEGER {
                     up(1),
                     down(2),
                     unknown(3)
                     }




          -- OBJECT-IDENTITIES:

          -- The following atmTrafficDescriptorTypes has been moved
          -- from [14].

--          atmTrafficDescriptorTypes OBJECT IDENTIFIER ::= {mib-2 37 1 1}
                                                      -- atmMIBObjects
                                                      -- See [14].

          -- All other and new OBJECT IDENTITIES go here:

              atmObjectIdentities OBJECT IDENTIFIER ::= {atmTCMIB 1}

          -- The following values are defined for use as
          -- possible values of the ATM traffic descriptor type.

--          atmNoTrafficDescriptor  OBJECT-IDENTITY
--              STATUS  obsolete
--              DESCRIPTION
--                  "This identifies the no ATM traffic
--                  descriptor type.  Parameters 1, 2, 3, 4,
--                  and 5 are not used.  This traffic descriptor
--                  type can be used for best effort traffic."
--              ::= {atmTrafficDescriptorTypes 1}
--
--          atmNoClpNoScr  OBJECT-IDENTITY
--              STATUS  current
--              DESCRIPTION
--                  "This traffic descriptor type is for no CLP
--                  and no Sustained Cell Rate.  The use of the
--                  parameter vector for this type:
--                  Parameter 1: peak cell rate in cells/second
--                               for CLP=0+1 traffic
--                  Parameter 2: CDVT in tenths of microseconds
--                  Parameter 3: not used
--                  Parameter 4: not used
--                  Parameter 5: not used.
--
--                  This traffic descriptor type is applicable to
--                  CBR connections following the UNI 3.0/3.1
--                  conformance definition for PCR CLP=0+1 [3,4].
--                  These CBR connections differ from CBR.1
--                  connections [13] in that the CLR objective
--                  applies only to the CLP=0 cell flow.
--
--                  This traffic descriptor type is also
--                  applicable to connections following the UBR.1
--                  conformance definition [13]."
--              ::= {atmTrafficDescriptorTypes 2}
--
--          atmClpNoTaggingNoScr  OBJECT-IDENTITY
--              STATUS  obsolete
--              DESCRIPTION
--                  "This traffic descriptor is for CLP without
--                  tagging and no Sustained Cell Rate.  The use
--                  of the parameter vector for this type:
--                  Parameter 1: peak cell rate in cells/second
--                               for CLP=0+1 traffic
--                  Parameter 2: peak cell rate in cells/second
--                               for CLP=0 traffic
--                  Parameter 3: not used
--                  Parameter 4: not used
--                  Parameter 5: not used."
--              ::= {atmTrafficDescriptorTypes 3}
--
--          atmClpTaggingNoScr  OBJECT-IDENTITY
--              STATUS  obsolete
--              DESCRIPTION
--                  "This traffic descriptor is for CLP with
--                  tagging and no Sustained Cell Rate.  The use
--                  of the parameter vector for this type:
--                  Parameter 1: peak cell rate in cells/second
--                               for CLP=0+1 traffic
--                  Parameter 2: peak cell rate in cells/second
--                               for CLP=0 traffic, excess
--                               tagged as CLP=1
--                  Parameter 3: not used
--                  Parameter 4: not used
--                  Parameter 5: not used."
--              ::= {atmTrafficDescriptorTypes 4}
--
--          atmNoClpScr  OBJECT-IDENTITY
--              STATUS  current
--              DESCRIPTION
--                  "This traffic descriptor type is for no CLP
--                  with Sustained Cell Rate.  The use of the
--                  parameter vector for this type:
--                  Parameter 1: peak cell rate in cells/second
--                               for CLP=0+1 traffic
--                  Parameter 2: sustainable cell rate in cells/second
--                               for CLP=0+1 traffic
--                  Parameter 3: maximum burst size in cells
--                  Parameter 4: CDVT in tenths of microseconds
--                  Parameter 5: not used.
--
--                  This traffic descriptor type is applicable
--                  to VBR connections following the UNI 3.0/3.1
--                  conformance definition for PCR CLP=0+1 and
--                  SCR CLP=0+1 [3,4].  These VBR connections
--                  differ from VBR.1 connections [13] in that
--                  the CLR objective applies only to the CLP=0
--                  cell flow."
--              ::= {atmTrafficDescriptorTypes 5}
--
--          atmClpNoTaggingScr  OBJECT-IDENTITY
--              STATUS  current
--              DESCRIPTION
--                  "This traffic descriptor type is for CLP with
--                  Sustained Cell Rate and no tagging.  The use
--                  of the parameter vector for this type:
--                  Parameter 1: peak cell rate in cells/second
--                               for CLP=0+1 traffic
--                  Parameter 2: sustainable cell rate in cells/second
--                               for CLP=0 traffic
--                  Parameter 3: maximum burst size in cells
--                  Parameter 4: CDVT in tenths of microseconds
--                  Parameter 5: not used.
--
--                  This traffic descriptor type is applicable to
--                  connections following the VBR.2 conformance
--                  definition [13]."
--              ::= {atmTrafficDescriptorTypes 6}
--
--          atmClpTaggingScr  OBJECT-IDENTITY
--              STATUS  current
--              DESCRIPTION
--                  "This traffic descriptor type is for CLP with
--                  tagging and Sustained Cell Rate.  The use of
--                  the parameter vector for this type:
--                  Parameter 1: peak cell rate in cells/second
--                               for CLP=0+1 traffic
--                  Parameter 2: sustainable cell rate in cells/second
--                               for CLP=0 traffic, excess tagged as
--                               CLP=1
--                  Parameter 3: maximum burst size in cells
--                  Parameter 4: CDVT in tenths of microseconds
--                  Parameter 5: not used.
--
--                  This traffic descriptor type is applicable to
--                  connections following the VBR.3 conformance
--                  definition [13]."
--              ::= {atmTrafficDescriptorTypes 7}
--
--          atmClpNoTaggingMcr  OBJECT-IDENTITY
--              STATUS  current
--              DESCRIPTION
--                  "This traffic descriptor type is for CLP with
--                  Minimum Cell Rate and no tagging.  The use of
--                  the parameter vector for this type:
--                  Parameter 1: peak cell rate in cells/second
--                               for CLP=0+1 traffic
--                  Parameter 2: CDVT in tenths of microseconds
--                  Parameter 3: minimum cell rate in cells/second
--                  Parameter 4: unused
--                  Parameter 5: unused.
--
--                  This traffic descriptor type is applicable to
--                  connections following the ABR conformance
--                  definition [13]."
--              ::= {atmTrafficDescriptorTypes 8}
--
--          atmClpTransparentNoScr  OBJECT-IDENTITY
--              STATUS  current
--              DESCRIPTION
--                  "This traffic descriptor type is for the CLP-
--                  transparent model [13] and no Sustained Cell Rate.
--                  The use of the parameter vector for this type:
--                  Parameter 1: peak cell rate in cells/second
--                               for CLP=0+1 traffic
--                  Parameter 2: CDVT in tenths of microseconds
--                  Parameter 3: not used
--                  Parameter 4: not used
--                  Parameter 5: not used.
--
--                  This traffic descriptor type is applicable to
--                  connections following the CBR.1 conformance
--                  definition [13].
--
--                  Connections specifying this traffic descriptor
--                  type will be rejected at UNI 3.0 or UNI 3.1
--                  interfaces.  For a similar traffic descriptor
--                  type that can be accepted at UNI 3.0 and
--                  UNI 3.1 interfaces, see atmNoClpNoScr."
--              ::= {atmTrafficDescriptorTypes 9}
--
--          atmClpTransparentScr  OBJECT-IDENTITY
--              STATUS  current
--              DESCRIPTION
--                  "This traffic descriptor type is for the CLP-
--                  transparent model [13] with Sustained Cell Rate.
--                  The use of the parameter vector for this type:
--                  Parameter 1: peak cell rate in cells/second
--                               for CLP=0+1 traffic
--                  Parameter 2: sustainable cell rate in cells/second
--                               for CLP=0+1 traffic
--                  Parameter 3: maximum burst size in cells
--                  Parameter 4: CDVT in tenths of microseconds
--                  Parameter 5: not used.
--
--                  This traffic descriptor type is applicable to
--                  connections following the VBR.1 conformance
--                  definition [13].
--
--                  Connections specifying this traffic descriptor
--                  type will be rejected at UNI 3.0 or UNI 3.1
--                  interfaces.  For a similar traffic descriptor
--                  type that can be accepted at UNI 3.0 and
--                  UNI 3.1 interfaces, see atmNoClpScr."
--              ::= {atmTrafficDescriptorTypes 10}
--
--          atmNoClpTaggingNoScr  OBJECT-IDENTITY
--              STATUS  current
--              DESCRIPTION
--                  "This traffic descriptor type is for no CLP
--                  with tagging and no Sustained Cell Rate.  The
--                  use of the parameter vector for this type:
--                  Parameter 1: peak cell rate in cells/second
--                               for CLP=0+1 traffic
--                  Parameter 2: CDVT in tenths of microseconds
--                  Parameter 3: not used
--                  Parameter 4: not used
--                  Parameter 5: not used.
--
--                  This traffic descriptor type is applicable to
--                  connections following the UBR.2 conformance
--                  definition [13]."
--              ::= {atmTrafficDescriptorTypes 11}
--
          END
--
-- For the revision history to work correctly, after a new MIB file has been
-- added to the CVS repository the first time the CVS Admin person needs to
-- set the correct comment string delimter for the file.
--
-- $Log: usr_atm_tc.mib,v $
-- Revision 1.2.4.1  1997/09/17 19:06:21  psd
-- Merged 2.0 to 3.0
--
--Revision 1.2.2.2  1997/09/05  13:17:20  psd
--MR 2630 fix.
--
--Revision 1.2.2.1  1997/09/05  13:15:55  psd
--MR 2630 fix.
--
--Revision 1.2  1997/08/13  15:19:36  eewanco
--Remove redundancies with RFC 1695
--
-- Revision 1.1  1997/05/29 10:59:27  mredden
-- creation
--
--
--
--
-- Local Variables:
-- tab-width:5
-- tab-stop-list:( 5 10 15 20 25 30 35 40 45 50 55 60 65 70 75 80)
-- End:
--



--
--	usr_ipoarp.mib - A MIB file for the portion of the
--                    Netserver gateway card IP over ATM 
--                    MIB implemented within atm_arp.
--
--
-- Author:         Mike Redden
--
--
--  | Copyright (c) 1997 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--
  USR-IPOA-ARP-MIB DEFINITIONS ::= BEGIN

  IMPORTS
      OBJECT-TYPE, NOTIFICATION-TYPE,
      Integer32, Counter32, IpAddress
          FROM SNMPv2-SMI
      TEXTUAL-CONVENTION, RowStatus
          FROM SNMPv2-TC
      AtmConnKind, AtmAddr
          FROM ATM-TC-MIB
      ipNetToMediaNetAddress, ipNetToMediaIfIndex,
	 ipAdEntAddr
          FROM RFC1213-MIB
      InterfaceIndex, usrIpoa, UsrConfigStatus, DisplayString, usrAtmArp, InterfaceIndexOrZero
          FROM USR-DEFINITIONS-MIB
      ;

  -- ***************************************************************
  -- Textual Conventions
  --***************************************************************

  IpoaEncapsType ::= TEXTUAL-CONVENTION
      STATUS      current
      DESCRIPTION
          "The encapsulation type used on a VC."
      SYNTAX      INTEGER {
                      llcSnap(1),
                      vcMuxed(2),
                      other(3)
                  }

  IpoaVpiInteger ::= TEXTUAL-CONVENTION
      STATUS     current
      DESCRIPTION
          "An integer large enough to hold a VPI."
      SYNTAX     Integer32 (0..255)

  IpoaVciInteger ::= TEXTUAL-CONVENTION
      STATUS     current
      DESCRIPTION
          "An integer large enough to hold a VCI."
      SYNTAX     Integer32 (0..65535)

  IpoaAtmAddr ::= TEXTUAL-CONVENTION
     DISPLAY-HINT "1x"
     STATUS  current
     DESCRIPTION
       "The ATM address used by the network entity.
        The address type can be determined by the
        OCTET STRING size. IpoaAtmAddr can be comprised
        of both an ATM Address and a subaddress. The
        ATM Address portion is required and must be
        first in the OCTET STRING.

        An implementation must use BCD encoding to
        represent a E.164 address as a MIB object."
     SYNTAX   OCTET STRING (SIZE(0..40))




  --
  -- Top-level structure of the MIB
  --

  usrIpoaObjects        OBJECT IDENTIFIER ::= { usrIpoa 1 }
  usrIpoaNotifications  OBJECT IDENTIFIER ::= { usrIpoa 2 }
  usrIpoaConformance    OBJECT IDENTIFIER ::= { usrIpoa 3 }

  -- ***************************************************************
  -- MIB Objects
  -- ***************************************************************


  -- The Logical IP Subnet Table

  usrIpoaLisTable OBJECT-TYPE
      SYNTAX      SEQUENCE OF IpoaLisEntry
      MAX-ACCESS  not-accessible
      STATUS      current
      DESCRIPTION
          "There is one entry in this table for every Logical IP
          Subnet (LIS) that this system is a member of."
      ::= { usrIpoaObjects 2 }

  usrIpoaLisEntry OBJECT-TYPE
      SYNTAX      IpoaLisEntry
      MAX-ACCESS  not-accessible
      STATUS      current
      DESCRIPTION
          "Information about a single LIS that this system is a
          member of.

          This table is indexed by an IP subnet address.

          Membership in a LIS is independent of the actual ATM
          physical interfaces being used. The usrIpoaLisTable defines
          all LISes that a system is a member of. The ipAddrTable
          and the usrIpoaClientTable provides the mapping from local
          IP address to ATM physical interface. The
          ipoaLisIfMappingTable provides the mappings between
          Logical IP Subnets and interfaces.

          The ipoaLisTable is indexed by ipoaLisSubnetAddr.
          An entry in the ipAddrTable should exist for each
          ipAddrEntry that is associated with an IP over ATM
          interface. Its ipAdEntAddr and ipAdEntNetMask when ANDed
          should map to a ipoaLisSubnetAddr."
      INDEX       { usrIpoaLisSubnetAddr }
      ::= { usrIpoaLisTable 1 }




-- Expires January 1998                                           [Page 15]





-- Greene et al.        IP and ARP over ATM (IPOA) MIB         11 July 1997


  IpoaLisEntry ::= SEQUENCE {
      usrIpoaLisSubnetAddr          IpAddress,
      usrIpoaLisDefaultMtu          Integer32,
      usrIpoaLisDefaultEncapsType   IpoaEncapsType,
      usrIpoaLisInactivityTimer     Integer32,
      usrIpoaLisMinHoldingTime      Integer32,
      usrIpoaLisQDepth              Integer32,
      usrIpoaLisMaxCalls            Integer32,
      usrIpoaLisCacheEntryAge       Integer32,
      usrIpoaLisRetries             Integer32,
      usrIpoaLisTimeout             Integer32,
      usrIpoaLisDefaultPeakCellRate Integer32,
      usrIpoaLisActiveVcs           Counter32,
      usrIpoaLisRowStatus           RowStatus }

  usrIpoaLisSubnetAddr OBJECT-TYPE
      SYNTAX      IpAddress
      MAX-ACCESS  read-only
      STATUS      current
      DESCRIPTION
          "The IP subnet address associated with this LIS."
      ::= { usrIpoaLisEntry 1 }

  usrIpoaLisDefaultMtu OBJECT-TYPE
      SYNTAX      Integer32 (0..65535)
      MAX-ACCESS  read-create
      STATUS      current
      DESCRIPTION
          "The default MTU used within this LIS. Note that the actual
          size used for a VC between two members of the LIS may be
          negotiated during connection setup and may be different than
          this value. The usrIpoaVcNegotiatedMtu object indicates the
          actual MTU in use for a particular VC."
      DEFVAL { 9180 }
      ::= { usrIpoaLisEntry 2 }

  usrIpoaLisDefaultEncapsType OBJECT-TYPE
      SYNTAX      IpoaEncapsType
      MAX-ACCESS  read-create
      STATUS      current
      DESCRIPTION
          "The default encapsulation to use on VCs created for this
          LIS. Note that the actual encapsulation type may be negotiated
          during connection setup and may be different than this
          value. The usrIpoaVcNegotiatedEncapsType object indicates the
          actual encapsulation in use for a particular VC."
      DEFVAL { llcSnap }
      ::= { usrIpoaLisEntry 3 }



-- Expires January 1998                                           [Page 16]





-- Greene et al.        IP and ARP over ATM (IPOA) MIB         11 July 1997


  usrIpoaLisInactivityTimer OBJECT-TYPE
      SYNTAX      Integer32
      UNITS       "seconds"
      MAX-ACCESS  read-create
      STATUS      current
      DESCRIPTION
          "The time, in seconds, before a call established for an
          ipNetToMediaEntry on a client will timeout due to no
          traffic being passed on the VC. A value of 0 implies
          no time out."
      REFERENCE
          "RFC1755, Sec. 3.4 VC Teardown"
      DEFVAL      { 300 }
      ::= { usrIpoaLisEntry 4 }

  usrIpoaLisMinHoldingTime OBJECT-TYPE
      SYNTAX      Integer32 (0..65535)
      UNITS       "seconds"
      MAX-ACCESS  read-create
      STATUS      current
      DESCRIPTION
          "The minimum amount of time, in seconds, that a call will
           remain open. If 0 then usrIpoaInactivityTimer will
           completely determine when a call is terminated."
      REFERENCE
          "RFC1755, Sec. 3.4 VC Teardown"
      DEFVAL      { 60 }
      ::= { usrIpoaLisEntry 5 }

  usrIpoaLisQDepth OBJECT-TYPE
      SYNTAX      Integer32 (1..65535)
      UNITS       "packets"
      MAX-ACCESS  read-create
      STATUS      current
      DESCRIPTION
          "The maximum number of outstanding requests that are
           allowed while waiting for ATMARP replies and
           In_ATMARP replies for this LIS."
      DEFVAL      { 1 }
      ::= { usrIpoaLisEntry 6 }

  usrIpoaLisMaxCalls OBJECT-TYPE
      SYNTAX      Integer32 (1..65535)
      MAX-ACCESS  read-create
      STATUS      current
      DESCRIPTION
          "The maximum number of SVCs that can be established
          simultaneously."



-- Expires January 1998                                           [Page 17]





-- Greene et al.        IP and ARP over ATM (IPOA) MIB         11 July 1997


      DEFVAL      { 500 }
      ::= { usrIpoaLisEntry 7 }

  usrIpoaLisCacheEntryAge OBJECT-TYPE
      SYNTAX      Integer32 (60..1200)
      UNITS       "seconds"
      MAX-ACCESS  read-create
      STATUS      current
      DESCRIPTION
          "The time, in seconds, before an ipNetToMediaEntry will age
          out of the table. Note that the default value will be
          different for a client and a server. A ATMARP server should
          use a default of 1200 and a client should use 900."
      DEFVAL      { 900 }
      ::= { usrIpoaLisEntry 8 }

  usrIpoaLisRetries OBJECT-TYPE
      SYNTAX      Integer32 (0..10)
      MAX-ACCESS  read-create
      STATUS      current
      DESCRIPTION
          "The number of times the ATMARP request will be retried when
          no response is received in the timeout interval indicated by
          usrIpoaLisTimeout."
      DEFVAL      { 2 }
      ::= { usrIpoaLisEntry 9 }

  usrIpoaLisTimeout OBJECT-TYPE
      SYNTAX      Integer32 (1..60)
      UNITS       "seconds"
      MAX-ACCESS  read-create
      STATUS      current
      DESCRIPTION
          "The time to wait, in seconds, before retransmission of an ARP
          PDU."
      DEFVAL      { 10 }
      ::= { usrIpoaLisEntry 10 }

  usrIpoaLisDefaultPeakCellRate OBJECT-TYPE
      SYNTAX Integer32
      MAX-ACCESS read-create
      STATUS current
      DESCRIPTION
          "This object is the signalling parameter that
           should be used when setting up all best effort
           VCCs. This parameter applies to the forward and
           backward direction on a per best effort VCC basis.
           A value of zero implies that no configured default
           exists and that local policy should be used to
           determine the actual default to used during
           call setup. ATM Signaling Support for IP over ATM
           (RFC 1755) recommends 1/10th of the ATM interface's
           speed."
      ::= { usrIpoaLisEntry 11 }

  usrIpoaLisActiveVcs OBJECT-TYPE
      SYNTAX      Counter32
      MAX-ACCESS  read-only
      STATUS      current
      DESCRIPTION
          "Number of active SVCs."
      ::= { usrIpoaLisEntry 12 }

  usrIpoaLisRowStatus OBJECT-TYPE
      SYNTAX      RowStatus
      MAX-ACCESS  read-create
      STATUS      current
      DESCRIPTION
          "This object allows entries to be created and deleted in the
          usrIpoaLisTable.

          When the usrIpoaLisRowStatus deleted (by setting this object to
          destroy(6)), this has the side-effect of removing all
          entries from the ipNetToMediaTable that are associated with
          this LIS (in other words, it flushes the entity's ATMARP
          cache). It also removes the usrIpoaVcTable entries that were
          associated with those ipNetToMediaTable entries. Destroying
          the row also removes the corresponding entries in the
          usrIpoaArpSrvrTable, usrIpoaArpClientTable,
          usrIpoaLisIfMappingTable and usrIpoaArpRemoteSrvrTable.

          Entries in both the ipNetToMediaTable and the usrIpoaVcTable
          that are associated with a usrIpoaConfigPvcEntry are not
          effected by changes to usrIpoaLisRowStatus."
      REFERENCE
          "RFC 1903, 'Textual Conventions for version 2 of the Simple
          Network Management Protocol (SNMPv2).'"
      ::= { usrIpoaLisEntry 13 }

  --
  -- The ATMARP Client Table
  --

  usrIpoaArpClientTable OBJECT-TYPE
      SYNTAX      SEQUENCE OF UsrIpoaArpClientEntry
      MAX-ACCESS  not-accessible
      STATUS      current
      DESCRIPTION
          "The ATMARP clients running on this system."
      ::= { usrIpoaObjects 4 }

  usrIpoaArpClientEntry OBJECT-TYPE
      SYNTAX      UsrIpoaArpClientEntry
      MAX-ACCESS  not-accessible
      STATUS      current
      DESCRIPTION
          "Information about a single ATMARP Client. Clients can be
          started and stopped by adding and removing entries from this
          table. Note that adding and removing entries from this table
          may have the same effect on the corresponding ipAddrTable
          entry. An entry in the usrIpoaArpClientTable has a corresponding
          entry in the ipAddrTable. Both are indexed by ipAdEntAddr.
          The ifIndex and subnet mask of a client entry are the
          ipAddrEntry's ipAdEntIfIndex and ipAdEntNetMask respectively.
          A remote creation of an object in this table requires
          that either the corresponding ipAddrTable entry exists or
          that ipAdEntIfIndex and ipAdEntNetMask be specified in the
          creation of a usrIpoaArpClientEntry at a minimum in order
          to create the corresponding ipAddrEntry. Specification
          of ipAdEntBcastAddr and ipAdEntReasmMaxSize to complete a
          ipAddrEntry is implementation dependent."
      INDEX       { ipAdEntAddr }
      ::= { usrIpoaArpClientTable 1 }

  UsrIpoaArpClientEntry ::= SEQUENCE {
      usrIpoaArpClientAtmAddr             IpoaAtmAddr,
      usrIpoaArpClientSrvrInUse           IpoaAtmAddr,
      usrIpoaArpClientInArpReqsIn         Counter32,
      usrIpoaArpClientInArpReqsOut        Counter32,
      usrIpoaArpClientInArpRepliesIn      Counter32,
      usrIpoaArpClientInArpRepliesOut     Counter32,
      usrIpoaArpClientInArpInvalidReqsIn  Counter32,
      usrIpoaArpClientInArpInvalidReqsOut Counter32,
      usrIpoaArpClientArpReqsIn           Counter32,
      usrIpoaArpClientArpReqsOut          Counter32,
      usrIpoaArpClientArpRepliesIn        Counter32,
      usrIpoaArpClientArpRepliesOut       Counter32,
      usrIpoaArpClientArpNaksIn           Counter32,
      usrIpoaArpClientArpNaksOut          Counter32,
      usrIpoaArpClientArpOpUnknown        Counter32,
      usrIpoaArpClientArpSrvrNoResp       Counter32,
      usrIpoaArpClientRowStatus           RowStatus }

  usrIpoaArpClientAtmAddr OBJECT-TYPE
      SYNTAX      IpoaAtmAddr
      MAX-ACCESS  read-create
      STATUS      current
      DESCRIPTION
          "The ATM address of the client."
	 --CONFIGURABLE
      ::= { usrIpoaArpClientEntry 1 }

  usrIpoaArpClientSrvrInUse OBJECT-TYPE
      SYNTAX      IpoaAtmAddr
      MAX-ACCESS  read-only
      STATUS      current
      DESCRIPTION
          "The ATM address of the ATMARP Server in use by this
           client. A value of 0 implies that communication with
           a ATMARP Server is not in effect."
      DEFVAL { ''H }
      ::= { usrIpoaArpClientEntry 2 }

  usrIpoaArpClientInArpReqsIn OBJECT-TYPE
      SYNTAX      Counter32
      MAX-ACCESS  read-only
      STATUS      current
      DESCRIPTION
          "The number of InATMARP requests received by this client."
      ::= { usrIpoaArpClientEntry 3 }

  usrIpoaArpClientInArpReqsOut OBJECT-TYPE
      SYNTAX      Counter32
      MAX-ACCESS  read-only
      STATUS      current
      DESCRIPTION
          "The number of InATMARP requests sent by this client."
      ::= { usrIpoaArpClientEntry 4 }

  usrIpoaArpClientInArpRepliesIn OBJECT-TYPE
      SYNTAX      Counter32
      MAX-ACCESS  read-only
      STATUS      current
      DESCRIPTION
          "The number of InATMARP replies received by this client."
      ::= { usrIpoaArpClientEntry 5 }

  usrIpoaArpClientInArpRepliesOut OBJECT-TYPE
      SYNTAX      Counter32
      MAX-ACCESS  read-only
      STATUS      current
      DESCRIPTION
          "Total number of InATMARP replies sent by this client."
      ::= { usrIpoaArpClientEntry 6 }

  usrIpoaArpClientInArpInvalidReqsIn OBJECT-TYPE
      SYNTAX      Counter32
      MAX-ACCESS  read-only
      STATUS      current
      DESCRIPTION
          "The number of times that this client detected an invalid
           InATMARP request."
      ::= { usrIpoaArpClientEntry 7 }

  usrIpoaArpClientInArpInvalidReqsOut OBJECT-TYPE
      SYNTAX      Counter32
      MAX-ACCESS  read-only
      STATUS      current
      DESCRIPTION
          "The number of times that this client did not receive
           a InATMARP reply."
      ::= { usrIpoaArpClientEntry 8 }

  usrIpoaArpClientArpReqsIn OBJECT-TYPE
      SYNTAX      Counter32
      MAX-ACCESS  read-only
      STATUS      current
      DESCRIPTION
          "Total number of ATMARP requests received by this client."
      ::= { usrIpoaArpClientEntry 9 }

  usrIpoaArpClientArpReqsOut OBJECT-TYPE
      SYNTAX      Counter32
      MAX-ACCESS  read-only
      STATUS      current
      DESCRIPTION
          "Total number of ATMARP requests sent by this client."
      ::= { usrIpoaArpClientEntry 10 }

  usrIpoaArpClientArpRepliesIn OBJECT-TYPE
      SYNTAX      Counter32
      MAX-ACCESS  read-only
      STATUS      current
      DESCRIPTION
          "Total number of ATMARP replies received by this client."
      ::= { usrIpoaArpClientEntry 11 }

  usrIpoaArpClientArpRepliesOut OBJECT-TYPE
      SYNTAX      Counter32
      MAX-ACCESS  read-only
      STATUS      current
      DESCRIPTION
          "Total number of ATMARP replies sent by this client."
      ::= { usrIpoaArpClientEntry 12 }

  usrIpoaArpClientArpNaksIn OBJECT-TYPE
      SYNTAX      Counter32
      MAX-ACCESS  read-only
      STATUS      current
      DESCRIPTION
          "Total number of negative ATMARP replies
           received by this client."
      ::= { usrIpoaArpClientEntry 13 }

  usrIpoaArpClientArpNaksOut OBJECT-TYPE
      SYNTAX      Counter32
      MAX-ACCESS  read-only
      STATUS      current
      DESCRIPTION
          "Total number of negative ATMARP replies
           send by this client."
      ::= { usrIpoaArpClientEntry 14 }

  usrIpoaArpClientArpOpUnknown OBJECT-TYPE
      SYNTAX      Counter32
      MAX-ACCESS  read-only
      STATUS      current
      DESCRIPTION
          "The number of times that this client received
           an ATMARP message with an operation code for which it
           is not coded to support."
      ::= { usrIpoaArpClientEntry 15 }

  usrIpoaArpClientArpSrvrNoResp OBJECT-TYPE
      SYNTAX      Counter32
      MAX-ACCESS  read-only
      STATUS      current
      DESCRIPTION
          "The number of times this client failed to receive
           a response from a ATMARP Server within the
           usrIpoaLisTimeout value for usrIpoaLisRetries times.
           This may imply that the client will re-elect a
           primary ATMARP server for this LIS from the
           usrIpoaArpRemoteSrvrTable."
      ::= { usrIpoaArpClientEntry 16 }

  usrIpoaArpClientRowStatus OBJECT-TYPE
      SYNTAX      RowStatus
      MAX-ACCESS  read-create
      STATUS      current
      DESCRIPTION
          "This object allows entries to be created and deleted from the
          usrIpoaArpClientTable."
      REFERENCE
          "RFC 1903, 'Textual Conventions for version 2 of the Simple
          Network Management Protocol (SNMPv2).'"
	 --CONFIGURABLE
      ::= { usrIpoaArpClientEntry 17 }

  -- The Remote ATMARP Server Table

  usrIpoaArpRemoteSrvrTable OBJECT-TYPE
      SYNTAX      SEQUENCE OF UsrIpoaArpRemoteSrvrEntry
      MAX-ACCESS  not-accessible
      STATUS      current
      DESCRIPTION
          "A table of non-local ATMARP servers associated with a LIS.
          An entry in this table has three indexes: first the
          usrIpoaLisSubnetAddr of the LIS that the corresponding
          ATMARP server provides ATMARP services for, then the
          usrIpoaArpRemoteSrvrAtmAddr, which is the ATM address of the
          remote ATMARP server and finally the ifIndex of the
          interface on which the VC to the ATMARP Remote Server
          will be opened. A ifIndex value of 0 should be used
          when a single VC is to be shared for ATMARP purposes
          by multiple interfaces."
      ::= { usrIpoaObjects 6 }

  usrIpoaArpRemoteSrvrEntry OBJECT-TYPE
      SYNTAX      UsrIpoaArpRemoteSrvrEntry
      MAX-ACCESS  not-accessible
      STATUS      current
      DESCRIPTION
          "Information about one non-local ATMARP server."
      INDEX  { usrIpoaLisSubnetAddr, usrIpoaArpRemoteSrvrAtmAddr,
               usrIpoaArpRemoteSrvrIfIndex }
      ::= { usrIpoaArpRemoteSrvrTable 1 }

  UsrIpoaArpRemoteSrvrEntry ::= SEQUENCE {
      usrIpoaArpRemoteSrvrAtmAddr   IpoaAtmAddr,
      usrIpoaArpRemoteSrvrRowStatus RowStatus,
      usrIpoaArpRemoteSrvrIfIndex   InterfaceIndexOrZero,
      usrIpoaArpRemoteSrvrIpAddr    IpAddress }

  usrIpoaArpRemoteSrvrAtmAddr OBJECT-TYPE
      SYNTAX      IpoaAtmAddr
      MAX-ACCESS  not-accessible
      STATUS      current
      DESCRIPTION
          "The ATM address of the remote ATMARP server."
      ::= { usrIpoaArpRemoteSrvrEntry 1 }

  usrIpoaArpRemoteSrvrRowStatus OBJECT-TYPE
      SYNTAX      RowStatus
      MAX-ACCESS  read-create
      STATUS      current
      DESCRIPTION
          "This object allows entries to be created and deleted from the
          usrIpoaArpRemoteSrvrTable as well as indicating the weather a
          VC exists to the Remote ATMARP Server.

          usrIpoaArpRemoteSrvrRowStatus states:
          active(1)       - VC exists to Remote ATMARP Server who's IP
                            Address is stored in
                            usrIpoaArpRemoteSrvrIpAddr.
                            This VC can be determined by searching the
                            usrIpoaVcTable using usrIpoaArpRemoteSrvrIfIndex
                            (if not 0 otherwise ignore
                            ipNetToMediaIfIndex
                            index) and usrIpoaArpRemoteSrvrIpAddr. A
                            usrIpoaArpClientEntry should exist were its
                            usrIpoaArpClientSrvrInUse object has the same
                            value as usrIpoaArpRemoteSrvrAtmAddr.
         notInService(2)  - Entry exists without an active VC to
                            the Remote ATMARP Server.
         notReady(3)      - usrIpoaArpRemoteSrvrEntry is incomplete.
         createAndGo(4)   - Value used to remotely create an entry
                            and then active it.
         createAndWait(5) - Value used to remotely create an entry and
                            leave entry inactive with either
                            notInService or notReady state.
         destroy(6)       - When usrIpoaArpRemoteSrvrRowStatus is set with
                            this value the corresponding table entry is
                            deleted."
      REFERENCE
          "RFC 1903, 'Textual Conventions for version 2 of the Simple
          Network Management Protocol (SNMPv2).'"
	 --CONFIGURABLE
      ::= { usrIpoaArpRemoteSrvrEntry 2 }

  usrIpoaArpRemoteSrvrIfIndex OBJECT-TYPE
      SYNTAX      InterfaceIndexOrZero
      MAX-ACCESS  not-accessible
      STATUS      current
      DESCRIPTION
          "The ifIndex of the interface that the VC to the
           Remote ATMARP Server is associated with."
      ::= { usrIpoaArpRemoteSrvrEntry 3 }

  usrIpoaArpRemoteSrvrIpAddr OBJECT-TYPE
      SYNTAX      IpAddress
      MAX-ACCESS  read-only
      STATUS      current
      DESCRIPTION
          "The IP Address of the Remote ATMARP Server. A value of
           0 implies that this address isn't known."
      DEFVAL { 0 }
      ::= { usrIpoaArpRemoteSrvrEntry 4 }

  --
  -- The VC Table
  --

  usrIpoaVcTable OBJECT-TYPE
      SYNTAX      SEQUENCE OF UsrIpoaVcEntry
      MAX-ACCESS  not-accessible
      STATUS      current
      DESCRIPTION
          "A system that support IP over ATM is an IP system and
          therefore must support all of the appropriate tables from
          RFC1213, MIB-II. This includes the ipNetToMediaTable (the ARP
          cache). This usrIpoaVcTable keeps a set of VCs for each entry in
          the ARP cache that was put there by this IP over ATM system
          acting as either a host or server."
      ::= { usrIpoaObjects 7 }

  usrIpoaVcEntry OBJECT-TYPE
      SYNTAX      UsrIpoaVcEntry
      MAX-ACCESS  not-accessible
      STATUS      current
      DESCRIPTION
          "A VC (permanent or switched) that this host or server has
          opened with another member of a LIS. Additional information
          can be determined about the VC from RFC1695, the AToM MIB.

          In an SVC environment, entries can not be created in
          this table by a management application. Entries are
          automatically
          added by the system as the result of ATMARP processing.

          In a PVC environment, an entry is automatically added to
          this table when an entry is created in the usrIpoaConfigPvcTable
          and the IP Address at the end of the PVC is discovered using
          In_ATMARP. An entry also is added to the ipNetToMediaTable."
      INDEX       { ipNetToMediaIfIndex,
                    ipNetToMediaNetAddress,
                    usrIpoaVcVpi,
                    usrIpoaVcVci
                  }
      ::= { usrIpoaVcTable 1 }


  UsrIpoaVcEntry ::= SEQUENCE {
      usrIpoaVcVpi                  IpoaVpiInteger,
      usrIpoaVcVci                  IpoaVciInteger,
      usrIpoaVcType                 AtmConnKind,
      usrIpoaVcNegotiatedMtu        Integer32,
      usrIpoaVcNegotiatedEncapsType IpoaEncapsType }

  usrIpoaVcVpi OBJECT-TYPE
      SYNTAX      IpoaVpiInteger
      MAX-ACCESS  read-only
      STATUS      current
      DESCRIPTION
          "The VPI value for the Virtual Circuit."
      ::= { usrIpoaVcEntry 1 }

  usrIpoaVcVci OBJECT-TYPE
      SYNTAX      IpoaVciInteger
      MAX-ACCESS  read-only
      STATUS      current
      DESCRIPTION
          "The VCI value for the Virtual Circuit."
      ::= { usrIpoaVcEntry 2 }

  usrIpoaVcType OBJECT-TYPE
      SYNTAX      AtmConnKind
      MAX-ACCESS  read-only
      STATUS      current
      DESCRIPTION
          "The type of the Virtual Circuit."
      ::= { usrIpoaVcEntry 3 }

  usrIpoaVcNegotiatedEncapsType OBJECT-TYPE
      SYNTAX      IpoaEncapsType
      MAX-ACCESS  read-only
      STATUS      current
      DESCRIPTION
          "The encapsulation type used when communicating over this
          circuit."
      ::= { usrIpoaVcEntry 4 }

  usrIpoaVcNegotiatedMtu OBJECT-TYPE
      SYNTAX      Integer32 (0..65535)
      MAX-ACCESS  read-only
      STATUS      current
      DESCRIPTION
          "The MTU used when communicating over this circuit."
      ::= { usrIpoaVcEntry 5 }

  usrIpoaConfigPvcTable OBJECT-TYPE
      SYNTAX      SEQUENCE OF UsrIpoaConfigPvcEntry
      MAX-ACCESS  not-accessible
      STATUS      current
      DESCRIPTION
          "This table must be supported when PVCs are intended to
          be supported in order to enable the setup of PVCs for use
          by IP."
      ::= { usrIpoaObjects 8 }

  usrIpoaConfigPvcEntry OBJECT-TYPE
      SYNTAX      UsrIpoaConfigPvcEntry
      MAX-ACCESS  not-accessible
      STATUS      current
      DESCRIPTION
          "Defines a single PVC that exists at this host for use by
          IP. "
      INDEX       { usrIpoaConfigPvcIfIndex,
                    usrIpoaConfigPvcVpi,
                    usrIpoaConfigPvcVci
                  }
      ::= { usrIpoaConfigPvcTable 1 }

  UsrIpoaConfigPvcEntry ::= SEQUENCE {
      usrIpoaConfigPvcIfIndex              InterfaceIndex,
      usrIpoaConfigPvcVpi                  IpoaVpiInteger,
      usrIpoaConfigPvcVci                  IpoaVciInteger,
      usrIpoaConfigPvcDefaultMtu           Integer32,
      usrIpoaConfigPvcRowStatus            RowStatus}

  usrIpoaConfigPvcIfIndex OBJECT-TYPE
      SYNTAX      InterfaceIndex
      MAX-ACCESS  not-accessible
      STATUS      current
      DESCRIPTION
          "The ifIndex of the ATM AAL Interface that this PVC
           is associated with."
	 --CONFIGURABLE
      ::= { usrIpoaConfigPvcEntry 1 }

  usrIpoaConfigPvcVpi OBJECT-TYPE
      SYNTAX      IpoaVpiInteger
      MAX-ACCESS  not-accessible
      STATUS      current
      DESCRIPTION
          "The VPI value for the Virtual Circuit."
	 --CONFIGURABLE
      ::= { usrIpoaConfigPvcEntry 2 }

  usrIpoaConfigPvcVci OBJECT-TYPE
      SYNTAX      IpoaVciInteger
      MAX-ACCESS  not-accessible
      STATUS      current
      DESCRIPTION
          "The VCI value for the Virtual Circuit."
      ::= { usrIpoaConfigPvcEntry 3 }

  usrIpoaConfigPvcDefaultMtu OBJECT-TYPE
      SYNTAX      Integer32 (0..65535)
      MAX-ACCESS  read-create
      STATUS      current
      DESCRIPTION
         "Classic2 allows use of other MTU values for PVCs
         but considers the how a value other than 9180 could
         be selected to be out of scope. usrIpoaConfigPvcDefaultMtu
         can be used to configure the MTU to be used for the PVC.
         Both ends must have the same value configured."
      DEFVAL { 9180 }
	 --CONFIGURABLE
      ::= { usrIpoaConfigPvcEntry 4 }

  usrIpoaConfigPvcRowStatus OBJECT-TYPE
      SYNTAX      RowStatus
      MAX-ACCESS  read-create
      STATUS      current
      DESCRIPTION
         "This object allows rows to be created and deleted in the
          usrIpoaConfigPvcTable. Creation of a entry in this table
          should eventually result in the creation of a
          ipNetToMediaEntry
          and a corresponding usrIpoaVcEntry after InATMARP has
          determined the destination address of system that the
          PVC is connected to. Setting this object to destroy(6)
          should remove the corresponding ipNetToMediaTable and
          usrIpoaVcTable entries.  In this implementation, setting
          this object to destroy also removes the corresponding 
          entry in the AtmArpPvcTable."
     REFERENCE
         "RFC 1903, 'Textual Conventions for version 2 of the Simple
         Network Management Protocol (SNMPv2).'"
	 --CONFIGURABLE
     ::= { usrIpoaConfigPvcEntry 5 }


  usrAtmArpPvcTable OBJECT-TYPE
      SYNTAX      SEQUENCE OF UsrAtmArpPvcEntry
      MAX-ACCESS  not-accessible
      STATUS      current
      DESCRIPTION
          "This table must be supported when PVCs are intended to
          be supported in order to enable the setup of PVCs for use
          by IP.  This table contains additional implementation
          specific information required for RFC 1577 PVCs. This table
          is mainly used to translate the IP Over ATM PVC name to the
          corresponding Ifindex, VPI and VCI values used to identify
          this PVC in the ConfigPvc table."

      ::= { usrAtmArp 1 }

  usrAtmArpPvcEntry OBJECT-TYPE
      SYNTAX      UsrAtmArpPvcEntry
      MAX-ACCESS  not-accessible
      STATUS      current
      DESCRIPTION
          "Defines a single PVC that exists at this host for use by
          IP. Entries in this table must be created at the same time
          entries are created in the IpoaConfigPvc table. "

      INDEX       { usrAtmArpPvcName }

      ::= { usrAtmArpPvcTable 1 }

  UsrAtmArpPvcEntry ::= SEQUENCE {
      usrAtmArpPvcName                     DisplayString,
      usrAtmArpPvcIfIndex                  InterfaceIndex,
      usrAtmArpPvcVpi                      IpoaVpiInteger,
      usrAtmArpPvcVci                      IpoaVciInteger,
	 usrAtmArpPvcNetworkName              DisplayString,
	 usrAtmArpPvcInterfaceName            DisplayString,
      usrAtmArpPvcNetIfIndex               InterfaceIndex,
	 usrAtmArpPvcEnabledFlag              INTEGER}

  usrAtmArpPvcName OBJECT-TYPE
      SYNTAX DisplayString (SIZE(0..32))
      MAX-ACCESS  not-accessible
      STATUS      current
      DESCRIPTION
         "A string containing the name of the RFC1577 PVC."
      ::= { usrAtmArpPvcEntry 1 }

  usrAtmArpPvcIfIndex OBJECT-TYPE
      SYNTAX      InterfaceIndex
      MAX-ACCESS  read-create
      STATUS      current
      DESCRIPTION
          "The ifIndex of the ATM AAL Interface that this PVC
           is associated with."
      --CONFIGURABLE
      ::= { usrAtmArpPvcEntry 2 }

  usrAtmArpPvcVpi OBJECT-TYPE
      SYNTAX      IpoaVpiInteger
      MAX-ACCESS  read-create
      STATUS      current
      DESCRIPTION
          "The VPI value for the Virtual Circuit."
      --CONFIGURABLE
      ::= { usrAtmArpPvcEntry 3 }

  usrAtmArpPvcVci OBJECT-TYPE
      SYNTAX      IpoaVciInteger
      MAX-ACCESS  read-create
      STATUS      current
      DESCRIPTION
          "The VCI value for the Virtual Circuit."
      --CONFIGURABLE
      ::= { usrAtmArpPvcEntry 4 }

  usrAtmArpPvcNetworkName OBJECT-TYPE
      SYNTAX DisplayString (SIZE(0..32))
      MAX-ACCESS  read-create
      STATUS      current
      DESCRIPTION
         "A string containing the name of the network of this RFC1577 PVC."
      --CONFIGURABLE
      ::= { usrAtmArpPvcEntry 5 }

  usrAtmArpPvcInterfaceName OBJECT-TYPE
      SYNTAX DisplayString (SIZE(0..32))
      MAX-ACCESS  read-only
      STATUS      current
      DESCRIPTION
         "A string containing the name of the ATMAAL interface where this RFC1577 PVC is established."
      ::= { usrAtmArpPvcEntry 6 }

  usrAtmArpPvcNetIfIndex OBJECT-TYPE
      SYNTAX      InterfaceIndex
      MAX-ACCESS  read-create
      STATUS      current
      DESCRIPTION
          "The ifIndex of the ATM Net Interface that this PVC
           is associated with."
      --CONFIGURABLE
      ::= { usrAtmArpPvcEntry 7 }

  usrAtmArpPvcEnabledFlag OBJECT-TYPE
      SYNTAX      INTEGER {
			enabled(1),
			disabled(2)
			}

      MAX-ACCESS  read-create
      STATUS      current
      DESCRIPTION
          "This flag indicates if this ATM 1577 PVC is enabled or disabled."
      ::= { usrAtmArpPvcEntry 8 }

	usrAtmArpConfigFileName OBJECT-TYPE
		SYNTAX      DisplayString
		MAX-ACCESS  read-write
          STATUS      current
		DESCRIPTION		
		  "The name of a ConfigFile to read/write permanent
		   database records. If the value of this object is an
             empty string, then ATM ARP uses the default
             name `@file://Atmarp.cfg'. "
     ::= { usrAtmArp 2 }

	usrAtmArpCFMStatusFlag  OBJECT-TYPE
	 	SYNTAX	  UsrConfigStatus
		MAX-ACCESS  read-write
	     STATUS      current
		DESCRIPTION
		  "Setting the value of this object to `save' causes the values
		   of the ATM ARP MIB objects to be written out to the
             current config file, which is stored in the 
             usrIpoaArpConfigFileName object. While the new
             ConfigFile is being written, ATM ARP
		   will set the value of this flag to `saving''. Any
		   attempts to set the value while it is not `normal'
		   (i.e. the file is currently being written to the
		   ConfigFile) while result in a badValue error being
		   returned. Setting the value to `normal' will result in no
		   action."
     ::= { usrAtmArp 3 }

  usrAtmArpServerNameTable OBJECT-TYPE
      SYNTAX      SEQUENCE OF UsrAtmArpServerNameEntry
      MAX-ACCESS  not-accessible
      STATUS      current
      DESCRIPTION
           "atm arp remote server name config table."
      ::= { usrAtmArp 4 }

  usrAtmArpServerNameEntry OBJECT-TYPE
      SYNTAX      UsrAtmArpServerNameEntry
      MAX-ACCESS  not-accessible
      STATUS      current
      DESCRIPTION
          "entry in the atm arp server name table"

      INDEX       { usrAtmArpServerName }
      ::= { usrAtmArpServerNameTable 1 }


  UsrAtmArpServerNameEntry ::= SEQUENCE {
      usrAtmArpServerName                  DisplayString,
      usrAtmArpLISSubnetAddress	           IpAddress, 
      usrAtmArpRemoteServerAtmAddr	   AtmAddr, 
      usrAtmArpRemoteServerIfIndex	   INTEGER, 
      usrAtmArpRemoteServerIfName	   DisplayString, 
      usrAtmArpServerRowStatus             INTEGER
  }

  usrAtmArpServerName OBJECT-TYPE
      SYNTAX DisplayString (SIZE(0..32))
      MAX-ACCESS  not-accessible
      STATUS      current
      DESCRIPTION
         "A string containing the name of the atm arp server."
      ::= { usrAtmArpServerNameEntry 1 }

  usrAtmArpLISSubnetAddress OBJECT-TYPE
      SYNTAX  IpAddress
      MAX-ACCESS  read-create
      STATUS      current
      DESCRIPTION
         "LIS subnet address."
	 --CONFIGURABLE
      ::= { usrAtmArpServerNameEntry 2}

  usrAtmArpRemoteServerAtmAddr OBJECT-TYPE
      SYNTAX  AtmAddr
      MAX-ACCESS  read-create
      STATUS      current
      DESCRIPTION
         "Remote arp server atm address."
	 --CONFIGURABLE
      ::= { usrAtmArpServerNameEntry 3 }

  usrAtmArpRemoteServerIfIndex OBJECT-TYPE
      SYNTAX INTEGER
      MAX-ACCESS  read-create
      STATUS      current
      DESCRIPTION
         "Interface index"
	 --CONFIGURABLE
      ::= { usrAtmArpServerNameEntry 4 }

  usrAtmArpServerRowStatus OBJECT-TYPE
      SYNTAX INTEGER
      MAX-ACCESS  read-only
      STATUS      current
      DESCRIPTION
         "server name index. dummy object, used to figure out
          server name in the list."
      ::= { usrAtmArpServerNameEntry 5 }

  usrAtmArpRemoteServerIfName OBJECT-TYPE
      SYNTAX DisplayString
      MAX-ACCESS  read-create
      STATUS      current
      DESCRIPTION
         "Interface index"
      ::= { usrAtmArpServerNameEntry 6 }

  -- ***************************************************************
  -- Notifications
  -- ***************************************************************

  usrIpoaMtuExceeded NOTIFICATION-TYPE
    OBJECTS {
          ipNetToMediaIfIndex,
          ipNetToMediaNetAddress,
          usrIpoaVcVpi,
          usrIpoaVcVci
     }
      STATUS  current
      DESCRIPTION
          "A frame was received that exceeds the negotiated MTU size."
      ::= { usrIpoaNotifications 1 }

  END
--
-- For the revision history to work correctly, after a new MIB file has been
-- added to the CVS repository the first time the CVS Admin person needs to
-- set the correct comment string delimter for the file.
--
-- $Log: usr_ipoa_arp.mib,v $
-- Revision 1.2.6.2  1997/12/19 13:20:28  psd
-- Another merge from 2.0
--
-- Revision 1.2.6.1  1997/09/17 19:06:33  psd
-- Merged 2.0 to 3.0
--
--Revision 1.2.4.2  1997/09/09  19:56:28  mredden
--Add client MIB
--
-- Revision 1.2.4.1  1997/08/29 02:49:08  mredden
-- Moved some new mib objects under atmarp
--
-- Revision 1.2  1997/05/30 21:15:12  mredden
-- Add PVC name object to 1483 MIB
--
-- Revision 1.1  1997/05/29 10:58:51  mredden
-- Creation
--
--
--
--
-- Local Variables:
-- tab-width:5
-- tab-stop-list:( 5 10 15 20 25 30 35 40 45 50 55 60 65 70 75 80)
-- End:
--
--
--	rfc1695-atmaal.mib - The ATMAAL specific portions of the AtoM MIB.
--                           The groups implemented within the ATMAAL
--                           driver are specified within this file.
--                           The groups specified are:
--
--                              ATM Interface configuration group
--                              ATM Interface DS3 PLCP group
--                              ATM Interface TC Sublayer group
--                              ATM Interface AAL5 VCC performance
--                                  statistics group
--
--                           The remaining groups are specified in the
--                           rfc1695-atmnet.mib file.
--
-- Author:         <Mike Redden>
--
--
--  | Copyright (c) 1997 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

               ATM-MIB-ATMAAL DEFINITIONS ::= BEGIN

               IMPORTS
                  MODULE-IDENTITY, OBJECT-TYPE, 
                  Counter32, Integer32, IpAddress
                      FROM SNMPv2-SMI
                  TEXTUAL-CONVENTION, DisplayString
                      FROM SNMPv2-TC
                  mib-2
                      FROM RFC1213-MIB
                  ifIndex
		      FROM IF-MIB;


               atmMIB MODULE-IDENTITY
                    LAST-UPDATED "9406072245Z"
                    ORGANIZATION "IETF AToM MIB Working Group"
                    CONTACT-INFO
                     "          Masuma Ahmed
                        Postal:  Bellcore
                                 331 Newman Springs Road
                                 Red Bank, NJ 07701
                                 US
                        Tel:     +1 908 758 2515
                        Fax:     +1 908 758 4131
                        E-mail:  mxa@mail.bellcore.com

                                 Kaj Tesink
                        Postal:  Bellcore
                                 331 Newman Springs Road
                                 Red Bank, NJ 07701
                                 US
                        Tel:     +1 908 758 5254
                        Fax:     +1 908 758 4196
                        E-mail:  kaj@cc.bellcore.com"
                    DESCRIPTION
                     "This is the MIB Module for ATM and AAL5-related
                      objects for managing ATM interfaces, ATM virtual
                      links, ATM cross-connects, AAL5 entities, and
                      and AAL5 connections."
                    ::= { mib-2 37 }

               atmMIBObjects  OBJECT IDENTIFIER ::= {atmMIB 1}

               -- This ATM MIB Module consists of the following groups:

               -- (1) ATM Interface configuration group
               -- (2) ATM Interface DS3 PLCP group
               -- (3) ATM Interface TC Sublayer group
               -- (4) ATM Interface AAL5 VCC performance statistics
               --     group


               IfIndex ::= TEXTUAL-CONVENTION
                    STATUS     current
                    DESCRIPTION
                      "The value of this object identifies the interface
                       for which the entry contains management
                       information. The value of this object for a
                       particular interface has the same value as the
                       ifIndex object, defined in RFC 1213, for the same
                       interface."
                    SYNTAX     Integer32

               --    ATM Interface Configuration Parameters Group

               -- This group contains ATM specific
               -- configuration information associated with
               -- an ATM interface beyond those
               -- supported using the ifTable.


               atmInterfaceConfTable    OBJECT-TYPE
                    SYNTAX      SEQUENCE OF AtmInterfaceConfEntry
                    MAX-ACCESS   not-accessible
                    STATUS       current
                    DESCRIPTION
                     "This table contains ATM local interface
                      configuration parameters, one entry per ATM
                      interface port."
                    ::= { atmMIBObjects 2 }

               atmInterfaceConfEntry    OBJECT-TYPE
                    SYNTAX         AtmInterfaceConfEntry
                    MAX-ACCESS     not-accessible
                    STATUS         current
                    DESCRIPTION
                     "This list contains ATM interface configuration
                      parameters and state variables."
                    INDEX { ifIndex }
                    ::= { atmInterfaceConfTable  1}

               AtmInterfaceConfEntry    ::= SEQUENCE  {
                    atmInterfaceMaxVpcs             INTEGER,
                    atmInterfaceMaxVccs             INTEGER,
                    atmInterfaceConfVpcs            INTEGER,
                    atmInterfaceConfVccs            INTEGER,
                    atmInterfaceMaxActiveVpiBits    INTEGER,
                    atmInterfaceMaxActiveVciBits    INTEGER,
                    atmInterfaceIlmiVpi             INTEGER,
                    atmInterfaceIlmiVci             INTEGER,
                    atmInterfaceAddressType         INTEGER,
                    atmInterfaceAdminAddress        OCTET STRING,
                    atmInterfaceMyNeighborIpAddress IpAddress,
                    atmInterfaceMyNeighborIfName    DisplayString
                         }

               atmInterfaceMaxVpcs    OBJECT-TYPE
                    SYNTAX       INTEGER  (0..4096)
                    MAX-ACCESS    read-write
                    STATUS         current
                    DESCRIPTION
                     "The maximum number of VPCs (PVCs and SVCs)
                      supported at this ATM interface.  At the ATM UNI,
                      the maximum number of VPCs (PVCs and SVCs)
                      ranges from 0 to 256 only."
                    ::= { atmInterfaceConfEntry 1}

               atmInterfaceMaxVccs    OBJECT-TYPE
                    SYNTAX       INTEGER  (0..65536)
                    MAX-ACCESS     read-write
                    STATUS         current
                    DESCRIPTION
                     "The maximum number of VCCs (PVCs and SVCs)
                      supported at this ATM interface."
                    ::= { atmInterfaceConfEntry 2}

               atmInterfaceConfVpcs    OBJECT-TYPE
                    SYNTAX       INTEGER  (0..4096)
                    MAX-ACCESS     read-only
                    STATUS         current
                    DESCRIPTION
                     "The number of VPCs (PVCs and SVCs)
                      configured for use at this ATM interface.
                      At the ATM UNI, the configured number of
                      VPCs (PVCs and SVCs) can range from
                      0 to 256 only."
                    ::= { atmInterfaceConfEntry 3}

               atmInterfaceConfVccs    OBJECT-TYPE
                    SYNTAX       INTEGER  (0..65536)
                    MAX-ACCESS    read-only
                    STATUS        current
                    DESCRIPTION
                     "The number of VCCs (PVCs and SVCs)
                      configured for use at the ATM interface."
                    ::= { atmInterfaceConfEntry 4}

               atmInterfaceMaxActiveVpiBits    OBJECT-TYPE
                    SYNTAX           INTEGER  (0..12)
                    MAX-ACCESS         read-write
                    STATUS             current
                    DESCRIPTION
                     "The  maximum number of active VPI bits
                      configured for use at the ATM interface.
                      At the ATM UNI, the maximum number of active
                      VPI bits configured for use ranges from
                      0 to 8 only."
                    ::= { atmInterfaceConfEntry 5}

               atmInterfaceMaxActiveVciBits    OBJECT-TYPE
                    SYNTAX             INTEGER  (0..16)
                    MAX-ACCESS         read-write
                    STATUS             current
                    DESCRIPTION
                     "The maximum number of active VCI bits
                      configured for use at this ATM interface."
                    ::= { atmInterfaceConfEntry 6}

               atmInterfaceIlmiVpi         OBJECT-TYPE
                    SYNTAX          INTEGER (0..255)
                    MAX-ACCESS       read-write
                    STATUS           current
                    DESCRIPTION
                     "The VPI value of the VCC supporting
                      the ILMI at this ATM interface.  If the values of
                      atmInterfaceIlmiVpi and atmInterfaceIlmiVci are
                      both equal to zero then the ILMI is not
                      supported at this ATM interface."
                    DEFVAL { 0 }
                    ::= { atmInterfaceConfEntry 7}

               atmInterfaceIlmiVci         OBJECT-TYPE
                    SYNTAX          INTEGER (0..65535)
                    MAX-ACCESS       read-write
                    STATUS           current
                    DESCRIPTION
                     "The VCI value of the VCC supporting
                      the ILMI at this ATM interface.  If the values of
                      atmInterfaceIlmiVpi and atmInterfaceIlmiVci are
                      both equal to zero then the ILMI is not
                      supported at this ATM interface."
                    DEFVAL { 16 }
                    ::= { atmInterfaceConfEntry 8}

               atmInterfaceAddressType    OBJECT-TYPE
                    SYNTAX      INTEGER {
                                         private(1),
                                         nsapE164(2),
                                         nativeE164(3),
                                         other(4)
                                        }
                    MAX-ACCESS    read-only
                    STATUS        current
                    DESCRIPTION
                     "The type of primary ATM address configured
                      for use at this ATM interface."
                    ::= { atmInterfaceConfEntry 9 }

               atmInterfaceAdminAddress    OBJECT-TYPE
                    SYNTAX      OCTET STRING (SIZE(0..255))
                    MAX-ACCESS    read-only
                    STATUS        current
                    DESCRIPTION
                     "An address assigned for administrative purposes,
                      for example, an address associated with the
                      service provider side of a public network UNI.
                      If this interface has no assigned administrative
                      address, or when the address used for
                      administrative  purposes is the same as that used
                      for ifPhysAddress, then this is an octet string of
                      zero length."
                    ::= { atmInterfaceConfEntry 10 }

               atmInterfaceMyNeighborIpAddress OBJECT-TYPE
                    SYNTAX       IpAddress
                    MAX-ACCESS   read-write
                    STATUS       current
                    DESCRIPTION
                     "The IP address of the neighbor system connected to
                      the  far end of this interface, to which a Network
                      Management Station can send SNMP messages, as IP
                      datagrams sent to UDP port 161, in order to access
                      network management information concerning the
                      operation of that system.  Note that the value
                      of this object may be obtained in different ways,
                      e.g., by manual configuration, or through ILMI
                      interaction with the neighbor system."
                    ::= { atmInterfaceConfEntry 11 }

               atmInterfaceMyNeighborIfName    OBJECT-TYPE
                    SYNTAX       DisplayString
                    MAX-ACCESS   read-write
                    STATUS       current
                    DESCRIPTION
                     "The textual name of the interface on the neighbor
                      system on the far end of this interface, and to
                      which this interface connects.  If the neighbor
                      system is manageable through SNMP and supports
                      the object ifName, the value of this object must
                      be identical with that of ifName for the ifEntry
                      of the lowest level physical interface
                      for this port.  If this interface does not have a
                      textual name, the value of this object is a zero
                      length string.  Note that the value of this object
                      may be obtained in different ways, e.g., by manual
                      configuration, or through ILMI interaction with
                      the neighbor system."
                    ::= { atmInterfaceConfEntry 12 }


               -- The ATM Interface DS3 PLCP Group

               -- This group contains the DS3 PLCP configuration and
               -- state parameters of those ATM interfaces
               -- which use DS3 PLCP for carrying ATM cells over DS3.

               atmInterfaceDs3PlcpTable    OBJECT-TYPE
                    SYNTAX      SEQUENCE OF AtmInterfaceDs3PlcpEntry
                    MAX-ACCESS   not-accessible
                    STATUS       current
                    DESCRIPTION
                     "This table contains ATM interface DS3 PLCP
                      parameters and state variables, one entry per
                      ATM interface port."
                    ::= { atmMIBObjects 3}

               atmInterfaceDs3PlcpEntry    OBJECT-TYPE
                    SYNTAX       AtmInterfaceDs3PlcpEntry
                    MAX-ACCESS   not-accessible
                    STATUS       current
                    DESCRIPTION
                     "This list contains DS3 PLCP parameters and
                      state variables at the ATM interface."
                    INDEX    {ifIndex }
                    ::= { atmInterfaceDs3PlcpTable 1}

               AtmInterfaceDs3PlcpEntry    ::= SEQUENCE  {
                    atmInterfaceDs3PlcpSEFSs         Counter32,
                    atmInterfaceDs3PlcpAlarmState    INTEGER,
                    atmInterfaceDs3PlcpUASs          Counter32
                      }


               atmInterfaceDs3PlcpSEFSs    OBJECT-TYPE
                    SYNTAX       Counter32
                    MAX-ACCESS   read-only
                    STATUS       current
                    DESCRIPTION
                     "The number of DS3 PLCP Severely Errored Framing
                      Second (SEFS).  Each SEFS represents a
                      one-second interval which contains
                      one or more SEF event."
                    ::= { atmInterfaceDs3PlcpEntry 1}

               atmInterfaceDs3PlcpAlarmState    OBJECT-TYPE
                    SYNTAX       INTEGER {
                                          noAlarm(1),
                                          receivedFarEndAlarm(2),
                                          incomingLOF(3)
                                                }
                    MAX-ACCESS     read-only
                    STATUS         current
                    DESCRIPTION
                     "This variable indicates if there is an
                      alarm present for the DS3 PLCP.  The value
                      receivedFarEndAlarm means that the DS3 PLCP
                      has received an incoming Yellow
                      Signal, the value incomingLOF means that
                      the DS3 PLCP has declared a loss of frame (LOF)
                      failure condition, and the value noAlarm
                      means that there are no alarms present.
                      Transition from the failure to the no alarm state
                      occurs when no defects (e.g., LOF) are received
                      for more than 10 seconds."
                    ::= { atmInterfaceDs3PlcpEntry 2}

               atmInterfaceDs3PlcpUASs    OBJECT-TYPE
                    SYNTAX       Counter32
                    MAX-ACCESS   read-only
                    STATUS       current
                    DESCRIPTION
                     "The counter associated with the number of
                      Unavailable Seconds encountered by the PLCP."
                    ::= { atmInterfaceDs3PlcpEntry 3}


               -- The ATM Interface TC Sublayer Group

               -- This group contains TC sublayer configuration and
               -- state parameters of those ATM interfaces
               -- which use TC sublayer for carrying ATM cells over
               -- SONET or DS3.


               atmInterfaceTCTable    OBJECT-TYPE
                    SYNTAX      SEQUENCE OF AtmInterfaceTCEntry
                    MAX-ACCESS   not-accessible
                    STATUS       current
                    DESCRIPTION
                     "This table contains ATM interface TC
                      Sublayer parameters and state variables,
                      one entry per ATM interface port."
                    ::= { atmMIBObjects 4}

               atmInterfaceTCEntry    OBJECT-TYPE
                    SYNTAX          AtmInterfaceTCEntry
                    MAX-ACCESS      not-accessible
                    STATUS          current
                    DESCRIPTION
                     "This list contains TC Sublayer parameters
                      and state variables at the ATM interface."
                    INDEX  {ifIndex }
                    ::= { atmInterfaceTCTable 1}

               AtmInterfaceTCEntry    ::= SEQUENCE  {
                    atmInterfaceOCDEvents      Counter32,
                    atmInterfaceTCAlarmState   INTEGER
                      }

               atmInterfaceOCDEvents    OBJECT-TYPE
                    SYNTAX        Counter32
                    MAX-ACCESS    read-only
                    STATUS        current
                    DESCRIPTION
                     "The number of times the Out of Cell
                      Delineation (OCD) events occur.  If seven
                      consecutive ATM cells have Header Error
                      Control (HEC) violations, an OCD event occurs.
                      A high number of OCD events may indicate a
                      problem with the TC Sublayer."
                    ::= { atmInterfaceTCEntry 1}

               atmInterfaceTCAlarmState    OBJECT-TYPE
                    SYNTAX        INTEGER {
                                           noAlarm(1),
                                           lcdFailure(2)
                                            }
                    MAX-ACCESS    read-only
                    STATUS        current
                    DESCRIPTION
                     "This variable indicates if there is an
                      alarm present for the TC Sublayer.  The value
                      lcdFailure indicates that a Loss of
                      Cell Delineation (LCD) failure state has been
                      declared for the TC Sublayer.  Transition from
                      failure to the no alarm state occurs
                      when 6 consecutive ATM cells
                      are received with valid HEC, followed by
                      about 10 seconds of acceptable working signal."
                     ::= { atmInterfaceTCEntry 2}



               -- AAL5 Virtual Channel Connection Performance Statistics
               -- Group

               -- This group contains the AAL5
               -- performance statistics of a VCC at the
               -- interface associated with an AAL5 entity in an ATM
               -- host or ATM switch.


               aal5VccTable    OBJECT-TYPE
                    SYNTAX      SEQUENCE OF Aal5VccEntry
                    MAX-ACCESS   not-accessible
                    STATUS       current
                    DESCRIPTION
                     "This table contains AAL5 VCC performance
                      parameters."
                    ::= { atmMIBObjects 12 }

               aal5VccEntry    OBJECT-TYPE
                    SYNTAX         Aal5VccEntry
                    MAX-ACCESS     not-accessible
                    STATUS         current
                    DESCRIPTION
                     "This list contains the AAL5 VCC
                      performance parameters."
                    INDEX { ifIndex, aal5VccVpi, aal5VccVci }
                    ::= { aal5VccTable 1 }

               Aal5VccEntry    ::= SEQUENCE  {
                    aal5VccVpi                        INTEGER,
                    aal5VccVci                        INTEGER,
                    aal5VccCrcErrors                  Counter32,
                    aal5VccSarTimeOuts                Counter32,
                    aal5VccOverSizedSDUs              Counter32
                         }


               aal5VccVpi               OBJECT-TYPE
                    SYNTAX       INTEGER  (0..4095)
                    MAX-ACCESS    not-accessible
                    STATUS         current
                    DESCRIPTION
                     "The VPI value of the AAL5 VCC at the
                      interface identified by the ifIndex."
                    ::= { aal5VccEntry 1 }

               aal5VccVci               OBJECT-TYPE
                    SYNTAX       INTEGER  (0..65535)
                    MAX-ACCESS    not-accessible
                    STATUS         current
                    DESCRIPTION
                     "The VCI value of the AAL5 VCC at the
                      interface identified by the ifIndex."
                    ::= { aal5VccEntry 2 }

               aal5VccCrcErrors    OBJECT-TYPE
                    SYNTAX  Counter32
                    MAX-ACCESS  read-only
                    STATUS           current
                    DESCRIPTION
                     "The number of AAL5 CPCS PDUs received with
                      CRC-32 errors on this AAL5 VCC at the
                      interface associated with an AAL5 entity."
                    ::= { aal5VccEntry 3 }

               aal5VccSarTimeOuts    OBJECT-TYPE
                    SYNTAX  Counter32
                    MAX-ACCESS  read-only
                    STATUS           current
                    DESCRIPTION
                     "The number of partially re-assembled AAL5
                      CPCS PDUs which were discarded
                      on this AAL5 VCC at the interface associated
                      with an AAL5 entity because they
                      were not fully re-assembled within the
                      required time period.  If the re-assembly
                      timer is not supported, then this object
                      contains a zero value."
                    ::= { aal5VccEntry 4 }

               aal5VccOverSizedSDUs    OBJECT-TYPE
                    SYNTAX  Counter32
                    MAX-ACCESS  read-only
                    STATUS           current
                    DESCRIPTION
                     "The number of AAL5 CPCS PDUs discarded
                      on this AAL5 VCC at the interface
                      associated with an AAL5 entity because the
                      AAL5 SDUs were too large."
                    ::= { aal5VccEntry 5 }

               END
--
--	rfc1695-atmnet.mib - The ATMNET specific portions of the AtoM MIB.
--                           The groups implemented within the ATMNET
--                           driver are specified within this file.
--                           The groups specified are:
--
--                              ATM Interface VPL configuration group
--                              ATM Interface VCL configuration group
--                              ATM VP Cross Connect group
--                              ATM VC Cross Connect group  
--
--                           The remaining groups are specified in the
--                           rfc1695-atmaal.mib file.
--
-- Author:         <Mike Redden>
--
--
--  | Copyright (c) 1997 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

               ATM-MIB-ATMNET DEFINITIONS ::= BEGIN

               IMPORTS
                  OBJECT-TYPE, OBJECT-IDENTITY,
                  Integer32
                      FROM SNMPv2-SMI
                  TEXTUAL-CONVENTION,
                  TimeStamp, RowStatus
                      FROM SNMPv2-TC
                  ifIndex
		      FROM IF-MIB
                  atmMIBObjects
                      FROM ATM-MIB-ATMAAL;

               -- This ATM MIB Module consists of the following groups:

               -- (1) ATM Interface VPL configuration group
               -- (2) ATM Interface VCL configuration group
               -- (3) ATM VP Cross Connect group
               -- (4) ATM VC Cross Connect group


               IfIndex ::= TEXTUAL-CONVENTION
                    STATUS     current
                    DESCRIPTION
                      "The value of this object identifies the interface
                       for which the entry contains management
                       information. The value of this object for a
                       particular interface has the same value as the
                       ifIndex object, defined in RFC 1213, for the same
                       interface."
                    SYNTAX     Integer32


               AtmTrafficDescrParamIndex ::= TEXTUAL-CONVENTION
                    STATUS     current
                    DESCRIPTION
                      "The value of this object identifies the row
                       in the atmTrafficDescrParamTable."
                    SYNTAX     Integer32

               atmTrafficDescriptorTypes  OBJECT IDENTIFIER ::=
                                                    {atmMIBObjects 1}

               -- The following values are defined for use as
               -- possible values of the ATM traffic descriptor type.
               -- ATM Forum specified seven types of ATM traffic
               -- descriptors.

               atmNoTrafficDescriptor  OBJECT-IDENTITY
                    STATUS     current
                    DESCRIPTION
                      "This identifies the no ATM traffic descriptor
                       type. Parameters 1, 2, 3, 4, and 5 are not used.
                       This traffic descriptor type can be used for
                       best effort traffic."
                    ::= { atmTrafficDescriptorTypes 1}

               atmNoClpNoScr  OBJECT-IDENTITY
                    STATUS     current
                    DESCRIPTION
                     "This traffic descriptor is for no CLP and
                      no Sustained Cell Rate.  The use of the
                      parameter vector for this type:
                      Parameter 1: CLP=0+1 peak cell rate in
                                   cells per second
                      Parameter 2: not used
                      Parameter 3: not used
                      Parameter 4: not used
                      Parameter 5: not used.
                      This traffic descriptor type can be used
                      for best effort traffic."
                  ::= { atmTrafficDescriptorTypes 2}

               atmClpNoTaggingNoScr OBJECT-IDENTITY
                    STATUS     current
                    DESCRIPTION
                     "This traffic descriptor is for no CLP without
                      tagging and no Sustained Cell Rate.  The use
                      of the parameter vector for this type:
                      Parameter 1: CLP=0+1 peak cell rate in
                                   cells per second
                      Parameter 2: CLP=0 peak cell rate in
                                   cells per second
                      Parameter 3: not used
                      Parameter 4: not used
                      Parameter 5: not used."
                    ::= { atmTrafficDescriptorTypes 3}

               atmClpTaggingNoScr OBJECT-IDENTITY
                   STATUS     current
                   DESCRIPTION
                     "This traffic descriptor is for CLP with
                      tagging and no Sustained Cell Rate.  The
                      use of the parameter vector for this type:
                      Parameter 1: CLP=0+1 peak cell rate in
                                   cells per second
                      Parameter 2: CLP=0 peak cell rate in
                                   cells per second with excess
                                   traffic tagged as CLP=1
                      Parameter 3: not used
                      Parameter 4: not used
                      Parameter 5: not used."
                   ::= { atmTrafficDescriptorTypes 4}

               atmNoClpScr OBJECT-IDENTITY
                    STATUS     current
                    DESCRIPTION
                     "This traffic descriptor is for no CLP
                      with Sustained Cell Rate.  The
                      use of the parameter vector for this type:
                      Parameter 1: CLP=0+1 peak cell rate in
                                   cells per second
                      Parameter 2: CLP=0+1 sustained cell rate in
                                   cells per second
                      Parameter 3: CLP=0+1 maximum burst size
                                   in cells
                      Parameter 4: not used
                      Parameter 5: not used."
                   ::= { atmTrafficDescriptorTypes 5}

               atmClpNoTaggingScr OBJECT-IDENTITY
                    STATUS     current
                    DESCRIPTION
                     "This traffic descriptor is for CLP
                      with Sustained Cell Rate and no tagging.
                      The use of the parameter vector for this type:
                      Parameter 1: CLP=0+1 peak cell rate in
                                   cells per second
                      Parameter 2: CLP=0 sustained cell rate in
                                   cells per second
                      Parameter 3: CLP=0 maximum burst size in cells
                      Parameter 4: not used
                      Parameter 5: not used."
                   ::= { atmTrafficDescriptorTypes 6}

               atmClpTaggingScr OBJECT-IDENTITY
                    STATUS     current
                    DESCRIPTION
                     "This traffic descriptor is for CLP
                      with tagging and Sustained Cell Rate.
                      The use of the parameter vector for this type:
                      Parameter 1: CLP=0+1 peak cell rate in
                                   cells per second
                      Parameter 2: CLP=0 sustained cell rate in
                                   cells per second with excess
                                   traffic tagged as CLP=1
                      Parameter 3: CLP=0 maximum burst size in cells
                      Parameter 4: not used
                      Parameter 5: not used."
                    ::= { atmTrafficDescriptorTypes 7}


               --  ATM Traffic Descriptor Parameter Group

               -- This group contains a set of self-consistent
               -- ATM traffic parameters including the
               -- ATM traffic QoS Class.

               -- The ATM virtual link tables (i.e., VPL and VCL tables)
               -- will use this ATM Traffic Descriptor table
               -- to assign traffic parameters and QoS Class
               -- to the receive and transmit directions of
               -- the ATM virtual links (i.e., VPLs and VCLs).
               -- The ATM VPL or VCL table will indicate a row
               -- in the atmTrafficDescrParamTable
               -- using its atmTrafficDescrParamIndex value.
               -- The management application can then compare a set of
               -- ATM traffic parameters with a single value.

               -- If no suitable row(s) in the atmTrafficDescrParamTable
               -- exists, the manager must create a new row(s) in this
               -- table. If such a row is created, agent checks the
               -- sanity of that set of ATM traffic parameter values.

               -- When creating a new row, the parameter values
               -- will be checked for self-consistency.
               -- Predefined/template rows may be supported.

               -- A row in the atmTrafficDescrParamTable is deleted
               -- by setting the atmTrafficDescrRowStatus to destroy(6).
               -- The agent will check whether this row is still in use
               -- by any entry of the atmVplTable or atmVclTable.
               -- The agent denies the request if the row is still in
               -- use.

               --  The ATM Traffic Descriptor Parameter Table


               atmTrafficDescrParamTable    OBJECT-TYPE
                    SYNTAX      SEQUENCE OF AtmTrafficDescrParamEntry
                    MAX-ACCESS   not-accessible
                    STATUS       current
                    DESCRIPTION
                     "This table contains information on ATM traffic
                      descriptor type and the associated parameters."
                    ::= { atmMIBObjects 5}

               atmTrafficDescrParamEntry    OBJECT-TYPE
                    SYNTAX           AtmTrafficDescrParamEntry
                    MAX-ACCESS       not-accessible
                    STATUS           current
                    DESCRIPTION
                     "This list contains ATM traffic descriptor
                      type and the associated parameters."
                    INDEX  {atmTrafficDescrParamIndex}
                    ::= { atmTrafficDescrParamTable  1}

               AtmTrafficDescrParamEntry    ::= SEQUENCE  {
                 atmTrafficDescrParamIndex   AtmTrafficDescrParamIndex,
                 atmTrafficDescrType         OBJECT IDENTIFIER,
                 atmTrafficDescrParam1       Integer32,
                 atmTrafficDescrParam2       Integer32,
                 atmTrafficDescrParam3       Integer32,
                 atmTrafficDescrParam4       Integer32,
                 atmTrafficDescrParam5       Integer32,
                 atmTrafficQoSClass          INTEGER,
                 atmTrafficDescrRowStatus    RowStatus
                              }

               atmTrafficDescrParamIndex    OBJECT-TYPE
                    SYNTAX           AtmTrafficDescrParamIndex
                    MAX-ACCESS       not-accessible
                    STATUS        current
                    DESCRIPTION
                     "This object is used by the virtual link
                      table (i.e., VPL or VCL table)
                      to identify the row of this table."
		    --CONFIGURABLE
                    ::= { atmTrafficDescrParamEntry  1}

               atmTrafficDescrType    OBJECT-TYPE
                    SYNTAX             OBJECT IDENTIFIER
                    MAX-ACCESS         read-create
                    STATUS             current
                    DESCRIPTION
                     "The value of this object identifies the type
                      of ATM traffic descriptor.
                      The type may indicate no traffic descriptor or
                      traffic descriptor with one or more parameters.
                      These parameters are specified as a parameter
                      vector, in the corresponding instances of the
                      objects:
                          atmTrafficDescrParam1
                          atmTrafficDescrParam2
                          atmTrafficDescrParam3
                          atmTrafficDescrParam4
                          atmTrafficDescrParam5."
                     DEFVAL  { atmNoTrafficDescriptor }
	             --CONFIGURABLE
                     ::= { atmTrafficDescrParamEntry 2}

               atmTrafficDescrParam1    OBJECT-TYPE
                    SYNTAX             Integer32
                    MAX-ACCESS          read-create
                    STATUS              current
                    DESCRIPTION
                     "The first parameter of the ATM traffic descriptor
                      used according to the value of
                      atmTrafficDescrType."
                    DEFVAL  { 0 }
                    --CONFIGURABLE
                    ::= { atmTrafficDescrParamEntry 3}

               atmTrafficDescrParam2    OBJECT-TYPE
                    SYNTAX             Integer32
                    MAX-ACCESS          read-create
                    STATUS              current
                    DESCRIPTION
                     "The second parameter of the ATM traffic descriptor
                      used according to the value of
                      atmTrafficDescrType."
                    DEFVAL  { 0 }
                    ::= { atmTrafficDescrParamEntry 4}

               atmTrafficDescrParam3    OBJECT-TYPE
                    SYNTAX             Integer32
                    MAX-ACCESS          read-create
                    STATUS              current
                    DESCRIPTION
                     "The third parameter of the ATM traffic descriptor
                      used according to the value of
                      atmTrafficDescrType."
                    DEFVAL  { 0 }
                    ::= { atmTrafficDescrParamEntry 5}

               atmTrafficDescrParam4    OBJECT-TYPE
                    SYNTAX             Integer32
                    MAX-ACCESS          read-create
                    STATUS              current
                    DESCRIPTION
                     "The fourth parameter of the ATM traffic descriptor
                      used according to the value of
                      atmTrafficDescrType."
                    DEFVAL  { 0 }
                    ::= { atmTrafficDescrParamEntry 6}

               atmTrafficDescrParam5    OBJECT-TYPE
                    SYNTAX             Integer32
                    MAX-ACCESS          read-create
                    STATUS              current
                    DESCRIPTION
                     "The fifth parameter of the ATM traffic descriptor
                      used according to the value of
                      atmTrafficDescrType."
                    DEFVAL  { 0 }
                    ::= { atmTrafficDescrParamEntry 7}

               atmTrafficQoSClass   OBJECT-TYPE
                    SYNTAX         INTEGER (0..255)
                    MAX-ACCESS      read-create
                    STATUS          current
                    DESCRIPTION
                     "The value of this object identifies the QoS Class.
                      Four Service classes have been
                      specified in the ATM Forum UNI Specification:
                      Service Class A: Constant bit rate video and
                                       Circuit emulation
                      Service Class B: Variable bit rate video/audio
                      Service Class C: Connection-oriented data
                      Service Class D: Connectionless data
                      Four QoS classes numbered 1, 2, 3, and 4 have
                      been specified with the aim to support service
                      classes A, B, C, and D respectively.
                      An unspecified QoS Class numbered `0' is used
                      for best effort traffic."
                    DEFVAL  { 0 }
                    --CONFIGURABLE
                    ::= { atmTrafficDescrParamEntry 8}


               atmTrafficDescrRowStatus       OBJECT-TYPE
                    SYNTAX    RowStatus
                    MAX-ACCESS   read-create
                    STATUS          current
                    DESCRIPTION
                     "This object is used to create
                      a new row or modify or delete an
                      existing row in this table."
                    DEFVAL  { active }
                    --CONFIGURABLE
                    ::= {atmTrafficDescrParamEntry 9}


               --  ATM Interface Virtual Path Link (VPL) Group

               -- This group contains configuration and state
               -- information of a bi-directional Virtual Path Link
               -- (VPL)

               -- This table can be used to create, delete or modify
               -- a VPL that is terminated in an ATM host or switch.
               -- This table can also be used to create, delete or
               -- modify a VPL which is cross-connected to another
               -- VPL.

               -- In the example below, the traffic flows on the receive
               -- and transmit directions of the VPLs are characterized
               -- by atmVplReceiveTrafficDescrIndex and
               -- atmVplTransmitTrafficDescrIndex respectively.
               -- The cross-connected VPLs are identified by
               -- atmVplCrossConnectIdentifier.



               --           ________________________________
               --           |                              |
               --  VPL      | ATM Host, Switch, or Network |   VPL
               -- receive   |                              |  receive
               -- ========> X                              X <=======
               -- <======== X                              X ========>
               -- transmit  |                              |  transmit
               --           |______________________________|



               --  The ATM Interface VPL Table


               atmVplTable    OBJECT-TYPE
                    SYNTAX      SEQUENCE OF AtmVplEntry
                    MAX-ACCESS   not-accessible
                    STATUS       current
                    DESCRIPTION
                     "The Virtual Path Link (VPL) table.  A
                      bi-directional VPL is modeled as one entry
                      in this table."
                    ::= { atmMIBObjects 6}

               atmVplEntry    OBJECT-TYPE
                    SYNTAX           AtmVplEntry
                    MAX-ACCESS       not-accessible
                    STATUS           current
                    DESCRIPTION
                     "An entry in the VPL table.  This entry is
                      used to model a bi-directional VPL.
                      To create a VPL at an ATM interface,
                      either of the following procedures are used:

                      Negotiated VPL establishment

                    (1) The management application creates
                        a VPL entry in the atmVplTable
                        by setting atmVplRowStatus to createAndWait(5).
                        This may fail for the following reasons:
                        - The selected VPI value is unavailable,
                        - The selected VPI value is in use.
                        Otherwise, the agent creates a row and
                        reserves the VPI value on that port.

                    (2) The manager selects an existing row(s) in the
                        atmTrafficDescrParamTable,
                        thereby, selecting a set of self-consistent
                        ATM traffic parameters and the QoS Class
                        for receive and transmit directions of the VPL.

                   (2a) If no suitable row(s) in the
                        atmTrafficDescrParamTable exists,
                        the manager must create a new row(s)
                        in that table.

                   (2b) The manager characterizes the VPL's traffic
                        parameters through setting the
                        atmVplReceiveTrafficDescrIndex and the
                        atmVplTransmitTrafficDescrIndex values
                        in the VPL table, which point to the rows
                        containing desired ATM traffic parameter values
                        in the atmTrafficDescrParamTable.  The agent
                        will check the availability of resources and
                        may refuse the request.

                    (3) The manager activates the VPL by setting the
                        the atmVplRowStatus to active(1).
                        If this set is successful, the agent has
                        reserved the resources to satisfy the requested
                        traffic parameter values and the QoS Class
                        for that VPL.
                    (4) If the VPL terminates a VPC in the ATM host
                        or switch, the manager turns on the
                        atmVplAdminStatus to up(1) to turn the VPL
                        traffic flow on.  Otherwise, the
                        atmVpCrossConnectTable  must be used
                        to cross-connect the VPL to another VPL(s)
                        in an ATM switch or network.

                      One-Shot VPL Establishment

                      A VPL may also be established in one step by a
                      set-request with all necessary VPL parameter
                      values and atmVplRowStatus set to createAndGo(4).

                      In contrast to the negotiated VPL establishment
                      which allows for detailed error checking
                      (i.e., set errors are explicitly linked to
                      particular resource acquisition failures),
                      the one-shot VPL establishment
                      performs the setup on one operation but
                      does not have the advantage of step-wise
                      error checking.

                      VPL Retirement

                      A VPL is released by setting atmVplRowStatus to
                      destroy(6), and the agent may release all
                      associated resources."
                    INDEX  {ifIndex, atmVplVpi }
                    ::= { atmVplTable  1}

               AtmVplEntry    ::= SEQUENCE  {
                    atmVplVpi                       INTEGER,
                    atmVplAdminStatus               INTEGER,
                    atmVplOperStatus                INTEGER,
                    atmVplLastChange                TimeStamp,
                    atmVplReceiveTrafficDescrIndex
                                    AtmTrafficDescrParamIndex,
                    atmVplTransmitTrafficDescrIndex
                                    AtmTrafficDescrParamIndex,
                    atmVplCrossConnectIdentifier    INTEGER,
                    atmVplRowStatus                 RowStatus
                       }


               atmVplVpi    OBJECT-TYPE
                    SYNTAX    INTEGER  (1..4095)
                    MAX-ACCESS     not-accessible
                    STATUS         current
                    DESCRIPTION
                     "The VPI value of the VPL.
                      Note that the VPI=0 is not used
                      for a VPL not associated with a VCL.
                      The maximum VPI value cannot
                      exceed the value allowable by the
                      atmInterfaceMaxVpiBits."
                    ::= { atmVplEntry 1}

               atmVplAdminStatus   OBJECT-TYPE
                    SYNTAX   INTEGER  {
                                       up(1),
                                       down(2)
                                           }
                    MAX-ACCESS   read-create
                    STATUS       current
                    DESCRIPTION
                     "This object is implemented only for a VPL which
                      terminates a VPC (i.e.,
                      one which is NOT cross-connected to other VPLs).
                      Its value specifies the desired administrative
                      state of the VPL.  The up and down states indicate
                      that the traffic flow is enabled and disabled
                      respectively for this VPL."
                    DEFVAL { down }
                    ::= { atmVplEntry 2}


               atmVplOperStatus   OBJECT-TYPE
                    SYNTAX   INTEGER  {
                                       up(1),
                                       down(2),
                                       unknown(3)
                                           }
                    MAX-ACCESS   read-only
                    STATUS       current
                    DESCRIPTION
                     "This object indicates the current operational
                      status of the VPL.  The up and down states
                      indicate that the VPL is currently
                      operational, or not operational, respectively.
                      The unknown state indicates that the status of
                      this VPL cannot be determined."
                    ::= { atmVplEntry 3}

               atmVplLastChange     OBJECT-TYPE
                    SYNTAX  TimeStamp
                    MAX-ACCESS  read-only
                    STATUS  current
                    DESCRIPTION
                     "The value of MIB II's sysUpTime object
                      at the time this VPL entered its current
                      operational state.  If the current state was
                      entered prior to the last re-initialization of the
                      agent, then this object contains a zero value."
                    ::= { atmVplEntry 4 }

               atmVplReceiveTrafficDescrIndex    OBJECT-TYPE
                    SYNTAX             AtmTrafficDescrParamIndex
                    MAX-ACCESS         read-create
                    STATUS             current
                    DESCRIPTION
                     "The value of this object identifies the row
                      in the atmTrafficDescrParamTable which
                      applies to the receive direction of the VPL."
                     ::= { atmVplEntry 5}

               atmVplTransmitTrafficDescrIndex    OBJECT-TYPE
                    SYNTAX             AtmTrafficDescrParamIndex
                    MAX-ACCESS         read-create
                    STATUS             current
                    DESCRIPTION
                     "The value of this object identifies the row
                      in the atmTrafficDescrParamTable which
                      applies to the transmit direction of the VPL."
                     ::= { atmVplEntry 6}

               atmVplCrossConnectIdentifier   OBJECT-TYPE
                    SYNTAX         INTEGER (0..2147483647)
                    MAX-ACCESS      read-only
                    STATUS          current
                    DESCRIPTION
                     "This object is implemented only for a VPL
                      which is cross-connected to other VPLs
                      that belong to the same VPC.  All such
                      associated VPLs have the same value of this
                      object, and all their cross-connections are
                      identified by entries in the
                      atmVpCrossConnectTable for which
                      atmVpCrossConnectIndex has the same value.
                      The value of this object is initialized by the
                      agent after the associated entries in the
                      atmVpCrossConnectTable have been created."
                    ::= {atmVplEntry 7}

               atmVplRowStatus       OBJECT-TYPE
                    SYNTAX    RowStatus
                    MAX-ACCESS   read-create
                    STATUS          current
                    DESCRIPTION
                     "This object is used to create, delete
                      or modify a row in this table.
                      To create a new VCL, this object is
                      initially set to 'createAndWait' or
                      'createAndGo'.  This object must not be
                      set to 'active' unless the following columnar
                      objects exist in this row:
                      atmVplReceiveTrafficDescrIndex and
                      atmVplTransmitTrafficDescrIndex."
                    DEFVAL { active }
                    ::= {atmVplEntry 8}


               --  ATM Interface Virtual Channel Link (VCL) Group

               -- This group contains configuration and state
               -- information of a bi-directional Virtual Channel
               -- Link (VCL) at an ATM interface.

               -- This table can be used to create, delete or modify
               -- a VCL that is terminated in an ATM host or switch.
               -- This table can also be
               -- used to create, delete or modify a VCL that is
               -- cross-connected to another VCL.


               --  The ATM Interface VCL Table


               atmVclTable    OBJECT-TYPE
                    SYNTAX      SEQUENCE OF AtmVclEntry
                    MAX-ACCESS   not-accessible
                    STATUS       current
                    DESCRIPTION
                     "The Virtual Channel Link (VCL) table.  A
                      bi-directional VCL is modeled as one entry
                      in this table."
                    ::= { atmMIBObjects 7}

               atmVclEntry    OBJECT-TYPE
                    SYNTAX           AtmVclEntry
                    MAX-ACCESS       not-accessible
                    STATUS           current
                    DESCRIPTION
                     "An entry in the VCL table.  This entry is
                      used to model a bi-directional VCL.
                      To create a VCL at an ATM interface,
                      either of the following procedures are used:

                      Negotiated VCL establishment

                    (1) The management application creates
                        a VCL entry in the atmVclTable
                        by setting atmVclRowStatus to createAndWait(5).
                        This may fail for the following reasons:
                        - The selected VPI/VCI values are unavailable,
                        - The selected VPI/VCI values are in use.
                        Otherwise, the agent creates a row and
                        reserves the VPI/VCI values on that port.

                    (2) The manager selects an existing row(s) in the
                        atmTrafficDescrParamTable,
                        thereby, selecting a set of self-consistent
                        ATM traffic parameters and the QoS Class
                        for receive and transmit directions of the VCL.

                   (2a) If no suitable row(s) in the
                        atmTrafficDescrParamTable exists,
                        the manager must create a new row(s)
                        in that table.

                   (2b) The manager characterizes the VCL's traffic
                        parameters through setting the
                        atmVclReceiveTrafficDescrIndex and the
                        atmVclTransmitTrafficDescrIndex values
                        in the VCL table, which point to the rows
                        containing desired ATM traffic parameter values
                        in the atmTrafficDescrParamTable.  The agent
                        will check the availability of resources and
                        may refuse the request.

                    (3) The manager activates the VCL by setting the
                        the atmVclRowStatus to active(1).
                        If this set is successful, the agent has
                        reserved the resources to satisfy the requested
                        traffic parameter values and the QoS Class
                        for that VCL.
                    (4) If the VCL terminates a VCC in the ATM host
                        or switch, the manager turns on the
                        atmVclAdminStatus to up(1) to turn the VCL
                        traffic flow on.  Otherwise, the
                        atmVcCrossConnectTable  must be used
                        to cross-connect the VCL to another VCL(s)
                        in an ATM switch or network.

                     One-Shot VCL Establishment

                     A VCL may also be established in one step by a
                     set-request with all necessary VCL parameter
                     values and atmVclRowStatus set to createAndGo(4).

                     In contrast to the negotiated VCL establishment
                     which allows for detailed error checking
                     (i.e., set errors are explicitly linked to
                     particular resource acquisition failures),
                     the one-shot VCL establishment
                     performs the setup on one operation but
                     does not have the advantage of step-wise
                     error checking.

                     VCL Retirement

                     A VCL is released by setting atmVclRowStatus to
                     destroy(6), and the agent may release all
                     associated resources."
                    INDEX  {ifIndex, atmVclVpi, atmVclVci }
                    ::= { atmVclTable  1}

               AtmVclEntry    ::= SEQUENCE  {
                    atmVclVpi                       INTEGER,
                    atmVclVci                       INTEGER,
                    atmVclAdminStatus               INTEGER,
                    atmVclOperStatus                INTEGER,
                    atmVclLastChange                TimeStamp,
                    atmVclReceiveTrafficDescrIndex
                                    AtmTrafficDescrParamIndex,
                    atmVclTransmitTrafficDescrIndex
                                    AtmTrafficDescrParamIndex,
                    atmVccAalType                   INTEGER,
                    atmVccAal5CpcsTransmitSduSize   INTEGER,
                    atmVccAal5CpcsReceiveSduSize    INTEGER,
                    atmVccAal5EncapsType            INTEGER,
                    atmVclCrossConnectIdentifier    INTEGER,
                    atmVclRowStatus                 RowStatus
                           }

               atmVclVpi    OBJECT-TYPE
                    SYNTAX    INTEGER  (0..4095)
                    MAX-ACCESS     not-accessible
                    STATUS         current
                    DESCRIPTION
                     "The VPI value of the VCL.
                      The maximum VPI value cannot
                      exceed the value allowable by the
                      atmInterfaceMaxVpiBits."
                    --CONFIGURABLE
                    ::= { atmVclEntry 1}

               atmVclVci    OBJECT-TYPE
                    SYNTAX    INTEGER  (0..65535)
                    MAX-ACCESS     not-accessible
                    STATUS         current
                    DESCRIPTION
                     "The VCI value of the VCL.
                      The maximum VCI value cannot
                      exceed the value allowable by the
                      atmInterfaceMaxVciBits."
                    --CONFIGURABLE
                    ::= { atmVclEntry 2}

               atmVclAdminStatus   OBJECT-TYPE
                    SYNTAX   INTEGER  {
                                       up(1),
                                       down(2)
                                           }
                    MAX-ACCESS   read-create
                    STATUS       current
                    DESCRIPTION
                     "This object is implemented only for a VCL which
                      terminates a VCC (i.e.,
                      one which is NOT cross-connected to other VCLs).
                      Its value specifies the desired administrative
                      state of the VCL.  The up and down states indicate
                      that the traffic flow is enabled and disabled
                      respectively for this VCL."
                    --CONFIGURABLE
                    ::= { atmVclEntry 3}

               atmVclOperStatus   OBJECT-TYPE
                    SYNTAX   INTEGER  {
                                       up(1),
                                       down(2),
                                       unknown(3)
                                           }
                    MAX-ACCESS   read-only
                    STATUS       current
                    DESCRIPTION
                     "This object indicates the current operational
                      status of the VCL.  The up and down states
                      indicate that the VCL is currently
                      operational, or not operational, respectively.
                      The unknown state indicates that the status of
                      this VCL cannot be determined."
                    --CONFIGURABLE
                    ::= { atmVclEntry 4}

               atmVclLastChange     OBJECT-TYPE
                    SYNTAX  TimeStamp
                    MAX-ACCESS  read-only
                    STATUS  current
                    DESCRIPTION
                     "The value of MIB II's sysUpTime object
                      at the time this VCL entered its current
                      operational state.  If the current state was
                      entered prior to the last re-initialization of the
                      agent, then this object contains a zero value."
                    ::= { atmVclEntry 5 }

               atmVclReceiveTrafficDescrIndex    OBJECT-TYPE
                    SYNTAX             AtmTrafficDescrParamIndex
                    MAX-ACCESS         read-create
                    STATUS             current
                    DESCRIPTION
                     "The value of this object identifies the row
                      in the ATM Traffic Descriptor Table which
                      applies to the receive direction of this VCL."
                    --CONFIGURABLE
                     ::= { atmVclEntry 6}

               atmVclTransmitTrafficDescrIndex    OBJECT-TYPE
                    SYNTAX             AtmTrafficDescrParamIndex
                    MAX-ACCESS         read-create
                    STATUS             current
                    DESCRIPTION
                     "The value of this object identifies the row
                      of the ATM Traffic Descriptor Table which applies
                      to the transmit direction of this VCL."
                    --CONFIGURABLE
                     ::= { atmVclEntry 7}

               atmVccAalType    OBJECT-TYPE
                    SYNTAX      INTEGER {
                                         aal1(1),
                                         aal34(2),
                                         aal5(3),
                                         other(4),
                                         unknown(5)
                                        }
                    MAX-ACCESS    read-create
                    STATUS        current
                    DESCRIPTION
                     "An instance of this object only exists when the
                      local VCL end-point is also the VCC end-point,
                      and AAL is in use.
                      The type of AAL used on this VCC.
                      The AAL type includes AAL1, AAL3/4,
                      and AAL5. The other(4) may be user-defined
                      AAL type.  The unknown type indicates that
                      the AAL type cannot be determined."
                    --CONFIGURABLE
                    ::= { atmVclEntry 8 }

               atmVccAal5CpcsTransmitSduSize OBJECT-TYPE
                    SYNTAX      INTEGER (1..65535)
                    MAX-ACCESS   read-create
                    STATUS       current
                    DESCRIPTION
                     "An instance of this object only exists when the
                      local VCL end-point is also the VCC end-point,
                      and AAL5 is in use.
                      The maximum AAL5 CPCS SDU size in octets that is
                      supported on the transmit direction of this VCC."
                    DEFVAL { 9188 }
                    --CONFIGURABLE
                          ::= { atmVclEntry 9 }

               atmVccAal5CpcsReceiveSduSize OBJECT-TYPE
                    SYNTAX      INTEGER (1..65535)
                    MAX-ACCESS   read-create
                    STATUS       current
                    DESCRIPTION
                     "An instance of this object only exists when the
                      local VCL end-point is also the VCC end-point,
                      and AAL5 is in use.
                      The maximum AAL5 CPCS SDU size in octets that is
                      supported on the receive direction of this VCC."
                    DEFVAL { 9188 }
                    --CONFIGURABLE
                          ::= { atmVclEntry 10 }

               atmVccAal5EncapsType  OBJECT-TYPE
                    SYNTAX   INTEGER {
                                   vcMultiplexRoutedProtocol(1),
                                   vcMultiplexBridgedProtocol8023(2),
                                   vcMultiplexBridgedProtocol8025(3),
                                   vcMultiplexBridgedProtocol8026(4),
                                   vcMultiplexLANemulation8023(5),
                                   vcMultiplexLANemulation8025(6),
                                   llcEncapsulation(7),
                                   multiprotocolFrameRelaySscs(8),
                                   other(9),
                                   unknown(10)
                                      }
                    MAX-ACCESS   read-create
                    STATUS        current
                    DESCRIPTION
                     "An instance of this object only exists when the
                      local VCL end-point is also the VCC end-point,
                      and AAL5 is in use.
                      The type of data encapsulation used over
                      the AAL5 SSCS layer. The definitions reference
                      RFC 1483 Multiprotocol Encapsulation
                      over ATM AAL5 and to the ATM Forum
                      LAN Emulation specification."
                    DEFVAL { llcEncapsulation }
                    --CONFIGURABLE
                          ::= { atmVclEntry 11 }

               atmVclCrossConnectIdentifier   OBJECT-TYPE
                    SYNTAX         INTEGER (0..2147483647)
                    MAX-ACCESS      read-only
                    STATUS          current
                    DESCRIPTION
                     "This object is implemented only for a VCL
                      which is cross-connected to other VCLs
                      that belong to the same VCC.  All such
                      associated VCLs have the same value of this
                      object, and all their cross-connections are
                      identified by entries in the
                      atmVcCrossConnectTable for which
                      atmVcCrossConnectIndex has the same value.
                      The value of this object is initialized by the
                      agent after the associated entries in the
                      atmVcCrossConnectTable have been created."
                    --CONFIGURABLE
                    ::= {atmVclEntry 12}

               atmVclRowStatus          OBJECT-TYPE
                    SYNTAX       RowStatus
                    MAX-ACCESS   read-create
                    STATUS       current
                    DESCRIPTION
                     "This object is used to create, delete or
                      modify a row in this table.  To create
                      a new VCL, this object is initially set
                      to 'createAndWait' or 'createAndGo'.
                      This object must not be set to 'active'
                      unless the following columnar objects exist
                      in this row:
                      atmVclReceiveTrafficDescrIndex,
                      atmVclTransmitTrafficDescrIndex.
                      In addition, if the local VCL end-point
                      is also the VCC end-point:
                      atmVccAalType.
                      In addition, for AAL5 connections only:
                      atmVccAal5CpcsTransmitSduSize,
                      atmVccAal5CpcsReceiveSduSize, and
                      atmVccAal5EncapsType."
                    DEFVAL { active }
                    --CONFIGURABLE
                          ::= {atmVclEntry 13}


               --     ATM Virtual Path (VP) Cross Connect Group

               -- This group contains configuration and state
               -- information of all point-to-point,
               -- point-to-multipoint, or multipoint-to-multipoint
               -- VP cross-connects.

               -- This table has read-create access and can be used
               -- to cross-connect the VPLs together in an ATM switch
               -- or network. The atmVpCrossConnectIndex
               -- is used to associate the related
               -- VPLs that are cross-connected together.

               -- The ATM VP Cross Connect Group
               -- models each bi-directional VPC
               -- cross-connect as a set of entries in
               -- the atmVpCrossConnectTable. A
               -- point-to-point VPC cross-connect is modeled
               -- as one entry; a point-to-multipoint (N leafs) VPC
               -- cross-connect as N entries in this table; and
               -- a multipoint-to-multipoint (N parties) VPC cross-
               -- connect as N(N-1)/2 entries in this table.
               -- In the latter cases, all the N (or N(N-1)/2) entries
               -- are associated with a single VPC cross-connect by
               -- having the same value of atmVpCrossConnectIndex.


               --      _________________________________________
               --      |                                       |
               --  Low |         ATM Switch or Network         | High
               --  port|                                       | port
               -- _____|>> from low to high VPC traffic flow >>|______
               --      |<< from high to low VPC traffic flow <<|
               --      |                                       |
               --      |_______________________________________|
               --

               -- The terms low and high are chosen to represent
               -- numerical ordering of the two interfaces associated
               -- with a VPC cross-connect. That is, the ATM interface
               -- with the lower value of ifIndex is termed 'low',
               -- while the other ATM interface associated with the
               -- VPC cross-connect is termed 'high'. This terminology
               -- is used to provide directional information; for
               -- example, the atmVpCrossConnectL2HOperStatus applies
               -- to the low->high direction, and
               -- atmVpCrossConnectH2LOperStatus applies to the
               -- high->low  direction, as illustrated above.

               atmVpCrossConnectIndexNext    OBJECT-TYPE
                    SYNTAX  INTEGER (0..2147483647)
                    MAX-ACCESS  read-only
                    STATUS  current
                    DESCRIPTION
                     "This object contains an appropriate value to
                      be used for atmVpCrossConnectIndex when creating
                      entries in the atmVpCrossConnectTable.  The value
                      0 indicates that no unassigned entries are
                      available. To obtain the atmVpCrossConnectIndex
                      value for a new entry, the manager issues a
                      management protocol retrieval operation to obtain
                      the current value of this object.  After each
                      retrieval, the agent should modify the value to
                      the next unassigned index."
                    ::= { atmMIBObjects 8 }


               --  The ATM VP Cross Connect Table


               atmVpCrossConnectTable OBJECT-TYPE
                    SYNTAX  SEQUENCE OF AtmVpCrossConnectEntry
                    MAX-ACCESS  not-accessible
                    STATUS  current
                    DESCRIPTION
                     "The ATM VP Cross Connect table.  A bi-
                      directional VP cross-connect which
                      cross-connects two VPLs is modeled
                      as one entry in this table."
                    ::= { atmMIBObjects 9 }


               atmVpCrossConnectEntry OBJECT-TYPE
                    SYNTAX  AtmVpCrossConnectEntry
                    MAX-ACCESS  not-accessible
                    STATUS  current
                    DESCRIPTION
                     "An entry in the ATM VP Cross Connect table.
                      This entry is used to model a bi-directional
                      ATM VP cross-connect which cross-connects
                      two VPLs.

                      Step-wise Procedures to set up a VP Cross-connect

                      Once the entries in the atmVplTable are created,
                      the following procedures are used
                      to cross-connect the VPLs together.

                     (1) The manager obtains a unique
                         atmVpCrossConnectIndex by reading the
                         atmVpCrossConnectIndexNext object.

                     (2) Next, the manager creates a set of one
                         or more rows in the ATM VP Cross Connect
                         Table, one for each cross-connection between
                         two VPLs.  Each row is indexed by the ATM
                         interface port numbers and VPI values of the
                         two ends of that cross-connection.
                         This set of rows specifies the topology of the
                         VPC cross-connect and is identified by a single
                         value of atmVpCrossConnectIndex.

                      Negotiated VP Cross-Connect Establishment

                    (2a) The manager creates a row in this table by
                         setting atmVpCrossConnectRowStatus to
                         createAndWait(5).  The agent checks the
                         requested topology and the mutual sanity of
                         the ATM traffic parameters and
                         QoS Classes, i.e., the row creation fails if:
                         - the requested topology is not supported
                           by the agent,
                         - the traffic/QoS parameter values
                           associated with the requested row are
                           incompatible with those of already existing
                           rows for this VP cross-connect.
                         [For example, for setting up
                         a point-to-point VP cross-connect, the
                         ATM traffic parameters in the receive direction
                         of a VPL at the low end of the cross-connect
                         must equal to the traffic parameters in the
                         transmit direction of the other VPL at the
                         high end of the cross-connect,
                         otherwise, the row creation fails.]
                         The agent also checks for internal errors
                         in building the cross-connect.

                         The atmVpCrossConnectIndex values in the
                         corresponding atmVplTable rows are filled
                         in by the agent at this point.

                    (2b) The manager promotes the row in the
                         atmVpCrossConnectTable by setting
                         atmVpCrossConnectRowStatus to active(1).  If
                         this set is successful, the agent has reserved
                         the resources specified by the ATM traffic
                         parameter and QoS Class values
                         for each direction of the VP cross-connect
                         in an ATM switch or network.

                     (3) The manager sets the
                         atmVpCrossConnectAdminStatus to up(1) in all
                         rows of this VP cross-connect to turn the
                         traffic flow on.


                      One-Shot VP Cross-Connect Establishment

                      A VP cross-connect may also be established in
                      one step by a set-request with all necessary
                      parameter values and atmVpCrossConnectRowStatus
                      set to createAndGo(4).

                      In contrast to the negotiated VP cross-connect
                      establishment which allows for detailed error
                      checking (i.e., set errors are explicitly linked
                      to particular resource acquisition failures),
                      the one-shot VP cross-connect establishment
                      performs the setup on one operation but does not
                      have the advantage of step-wise error checking.

                      VP Cross-Connect Retirement

                      A VP cross-connect identified by a particular
                      value of atmVpCrossConnectIndex is released by:

                     (1) Setting atmVpCrossConnectRowStatus of all
                         rows identified by this value of
                         atmVpCrossConnectIndex to destroy(6).
                         The agent may release all
                         associated resources, and the
                         atmVpCrossConnectIndex values in the
                         corresponding atmVplTable row are removed.
                         Note that a situation when only a subset of
                         the associated rows are deleted corresponds
                         to a VP topology change.

                     (2) After deletion of the appropriate
                         atmVpCrossConnectEntries, the manager may
                         set atmVplRowStatus to destroy(6) the
                         associated VPLs.  The agent releases
                         the resources and removes the associated
                         rows in the atmVplTable.

                      VP Cross-connect Reconfiguration

                      At the discretion of the agent, a VP
                      cross-connect may be reconfigured by
                      adding and/or deleting leafs to/from
                      the VP topology as per the VP cross-connect
                      establishment/retirement procedures.
                      Reconfiguration of traffic/QoS parameter
                      values requires release of the VP cross-connect
                      before those parameter values may by changed
                      for individual VPLs."
                    INDEX { atmVpCrossConnectIndex,
                          atmVpCrossConnectLowIfIndex,
                          atmVpCrossConnectLowVpi,
                          atmVpCrossConnectHighIfIndex,
                          atmVpCrossConnectHighVpi }
                    ::= { atmVpCrossConnectTable 1 }

               AtmVpCrossConnectEntry ::= SEQUENCE {
                    atmVpCrossConnectIndex          INTEGER,
                    atmVpCrossConnectLowIfIndex     IfIndex,
                    atmVpCrossConnectLowVpi         INTEGER,
                    atmVpCrossConnectHighIfIndex    IfIndex,
                    atmVpCrossConnectHighVpi        INTEGER,
                    atmVpCrossConnectAdminStatus    INTEGER,
                    atmVpCrossConnectL2HOperStatus  INTEGER,
                    atmVpCrossConnectH2LOperStatus  INTEGER,
                    atmVpCrossConnectL2HLastChange  TimeStamp,
                    atmVpCrossConnectH2LLastChange  TimeStamp,
                    atmVpCrossConnectRowStatus      RowStatus
                            }

               atmVpCrossConnectIndex OBJECT-TYPE
                    SYNTAX  INTEGER (1..2147483647)
                    MAX-ACCESS  not-accessible
                    STATUS  current
                    DESCRIPTION
                     "A unique value to identify this VP cross-connect."
                    ::= { atmVpCrossConnectEntry 1 }

               atmVpCrossConnectLowIfIndex OBJECT-TYPE
                    SYNTAX  IfIndex
                    MAX-ACCESS  not-accessible
                    STATUS  current
                    DESCRIPTION
                     "The value of this object is equal to MIB II's
                      ifIndex value of the ATM interface port for this
                      VP cross-connect.  The term low implies
                      that this ATM interface has the numerically lower
                      ifIndex value than the other ATM interface
                      identified in the same atmVpCrossConnectEntry."
                    ::= { atmVpCrossConnectEntry 2 }

               atmVpCrossConnectLowVpi OBJECT-TYPE
                    SYNTAX  INTEGER  (1..4095)
                    MAX-ACCESS  not-accessible
                    STATUS  current
                    DESCRIPTION
                     "The value of this object is equal to the VPI
                      value at the ATM interface
                      associated with the VP cross-connect that is
                      identified by atmVpCrossConnectLowIfIndex.
                      The VPI value cannot exceed the number
                      supported by the atmInterfaceMaxVpiBits
                      at the low ATM interface port."
                    ::= { atmVpCrossConnectEntry 3 }

               atmVpCrossConnectHighIfIndex OBJECT-TYPE
                    SYNTAX  IfIndex
                    MAX-ACCESS  not-accessible
                    STATUS  current
                    DESCRIPTION
                     "The value of this object is equal to MIB II's
                      ifIndex value of the ATM interface port for
                      this VP cross-connect.  The term high
                      implies that this ATM interface has the
                      numerically higher ifIndex value than the
                      other ATM interface identified in the same
                      atmVpCrossConnectEntry."
                    ::= { atmVpCrossConnectEntry 4 }

               atmVpCrossConnectHighVpi OBJECT-TYPE
                    SYNTAX  INTEGER   (1..4095)
                    MAX-ACCESS  not-accessible
                    STATUS  current
                    DESCRIPTION
                     "The value of this object is equal to the VPI
                      value at the ATM interface associated with
                      the VP cross-connect that is identified
                      by atmVpCrossConnectHighIfIndex.
                      The VPI value cannot exceed the number
                      supported by the atmInterfaceMaxVpiBits
                      at the high ATM interface port."
                    ::= { atmVpCrossConnectEntry 5 }

               atmVpCrossConnectAdminStatus OBJECT-TYPE
                    SYNTAX  INTEGER {
                                    up(1),
                                    down(2)
                            }
                    MAX-ACCESS  read-create
                    STATUS  current
                    DESCRIPTION
                     "The value of this object identifies the desired
                      administrative status of this bi-directional
                      VP cross-connect.  The up and down states
                      indicate that the traffic flow is enabled
                      and disabled respectively on this VP
                      cross-connect."
                    DEFVAL { down }
                    ::= { atmVpCrossConnectEntry 6 }

               atmVpCrossConnectL2HOperStatus OBJECT-TYPE
                    SYNTAX  INTEGER {
                              up(1),
                              down(2),
                              unknown(3)
                                }
                    MAX-ACCESS  read-only
                    STATUS  current
                    DESCRIPTION
                     "The value of this object identifies the current
                      operational status of the VP cross-connect
                      in one direction; (i.e., from the low to
                      high direction).  The up and down states indicate
                      that this ATM VP cross-connect from low
                      to high direction is operational or not
                      operational respectively.
                      The unknown state indicates that
                      the state of it cannot be determined."
                    ::= { atmVpCrossConnectEntry 7 }

               atmVpCrossConnectH2LOperStatus OBJECT-TYPE
                    SYNTAX  INTEGER {
                              up(1),
                              down(2),
                              unknown(3)
                                 }
                    MAX-ACCESS  read-only
                    STATUS  current
                    DESCRIPTION
                     "The value of this object identifies the current
                      operational status of the VP cross-connect
                      in one direction; (i.e., from the high to
                      low direction).  The up and down states indicate
                      that this ATM VP cross-connect from high
                      to low direction is operational or not
                      operational respectively.  The
                      unknown state indicates that the state
                      of it cannot be determined."
                    ::= { atmVpCrossConnectEntry 8 }

               atmVpCrossConnectL2HLastChange OBJECT-TYPE
                    SYNTAX  TimeStamp
                    MAX-ACCESS  read-only
                    STATUS  current
                    DESCRIPTION
                     "The value of MIB II's sysUpTime object
                      at the time this VP cross-connect entered
                      its current operational state in the low to
                      high direction.  If the current state was
                      entered prior to the last re-initialization of the
                      agent, then this object contains a zero value."
                    ::= { atmVpCrossConnectEntry 9 }

               atmVpCrossConnectH2LLastChange OBJECT-TYPE
                    SYNTAX  TimeStamp
                    MAX-ACCESS  read-only
                    STATUS  current
                    DESCRIPTION
                     "The value of MIB II's sysUpTime object at the
                      time this VP cross-connect entered its current
                      operational state in the high to low direction.
                      If the current state was entered prior to the
                      last re-initialization of the agent,
                      then this object contains a zero value."
                    ::= { atmVpCrossConnectEntry 10 }

               atmVpCrossConnectRowStatus OBJECT-TYPE
                    SYNTAX  RowStatus
                    MAX-ACCESS  read-create
                    STATUS  current
                    DESCRIPTION
                     "The status of this entry in the
                      atmVpCrossConnectTable.  This object is used to
                      create a cross-connect for cross-connecting
                      VPLs which are created using the atmVplTable
                      or to change or delete an existing cross-connect.
                      This object must be initially set
                      to `createAndWait' or 'createAndGo'.
                      This object cannot be set to `active'
                      unless the following columnar object exists
                      in this row: atmVpCrossConnectAdminStatus.
                      To turn on a VP cross-connect,
                      the atmVpCrossConnectAdminStatus
                      is set to `up'."
                    DEFVAL { active }
                    ::= { atmVpCrossConnectEntry 11 }


               --     ATM Virtual Channel (VC) Cross Connect Group

               -- This group contains configuration and state
               -- information of a bi-directional VC cross-connect.

               -- This group is used to model a bi-directional
               -- point-to-point, point-to-multipoint or
               -- multipoint-to-multipoint VC cross-connects.

               -- This table has read-create access and is used
               -- to cross-connect the VCLs together in an ATM switch
               -- or network that belong to a VC connection.
               -- The atmVcCrossConnectIndex is used to associate
               -- the related VCLs that are cross-connected together.


               -- The step-wise procedures described for setting
               -- up a VP cross-connect are also used for setting up
               -- a VC cross-connect.


               atmVcCrossConnectIndexNext    OBJECT-TYPE
                    SYNTAX  INTEGER (0..2147483647)
                    MAX-ACCESS  read-only
                    STATUS  current
                    DESCRIPTION
                     "This object contains an appropriate value to
                      be used for atmVcCrossConnectIndex when creating
                      entries in the atmVcCrossConnectTable.  The value
                      0 indicates that no unassigned entries are
                      available. To obtain the atmVpCrossConnectIndex
                      value for a new entry, the manager issues a
                      management protocol retrieval operation to obtain
                      the current value of this object.  After each
                      retrieval, the agent should modify the value to
                      the next unassigned index."
                    ::= { atmMIBObjects 10 }


               --  The ATM VC Cross Connect Table

               atmVcCrossConnectTable OBJECT-TYPE
                    SYNTAX  SEQUENCE OF AtmVcCrossConnectEntry
                    MAX-ACCESS  not-accessible
                    STATUS  current
                    DESCRIPTION
                     "The ATM VC Cross Connect table.  A bi-
                      directional VC cross-connect which
                      cross-connects two end points (i.e., VCLs)
                      is modeled as one entry in this table."
                    ::= { atmMIBObjects 11 }


               atmVcCrossConnectEntry OBJECT-TYPE
                    SYNTAX  AtmVcCrossConnectEntry
                    MAX-ACCESS  not-accessible
                    STATUS  current
                    DESCRIPTION
                     "An entry in the ATM VC Cross Connect table.
                      This entry is used to model a bi-directional ATM
                      VC cross-connect cross-connecting two end points.

                      Step-wise Procedures to set up a VC Cross-connect

                      Once the entries in the atmVclTable are created,
                      the following procedures are used
                      to cross-connect the VCLs together to
                      form a VCC segment.

                     (1) The manager obtains a unique
                         atmVcCrossConnectIndex by reading the
                         atmVcCrossConnectIndexNext object.

                     (2) Next, the manager creates a set of one
                         or more rows in the ATM VC Cross Connect
                         Table, one for each cross-connection between
                         two VCLs.  Each row is indexed by the ATM
                         interface port numbers and VPI/VCI values of
                         the two ends of that cross-connection.
                         This set of rows specifies the topology of the
                         VCC cross-connect and is identified by a single
                         value of atmVcCrossConnectIndex.

                      Negotiated VC Cross-Connect Establishment

                    (2a) The manager creates a row in this table by
                         setting atmVcCrossConnectRowStatus to
                         createAndWait(5).  The agent checks the
                         requested topology and the mutual sanity of
                         the ATM traffic parameters and
                         QoS Classes, i.e., the row creation fails if:
                         - the requested topology is not supported
                           by the agent,
                         - the traffic/QoS parameter values
                           associated with the requested row are
                           incompatible with those of already existing
                           rows for this VC cross-connect.
                         [For example, for setting up
                         a point-to-point VC cross-connect, the
                         ATM traffic parameters in the receive direction
                         of a VCL at the low end of the cross-connect
                         must equal to the traffic parameters in the
                         transmit direction of the other VCL at the
                         high end of the cross-connect,
                         otherwise, the row creation fails.]
                         The agent also checks for internal errors
                         in building the cross-connect.

                         The atmVcCrossConnectIndex values in the
                         corresponding atmVclTable rows are filled
                         in by the agent at this point.

                    (2b) The manager promotes the row in the
                         atmVcCrossConnectTable by setting
                         atmVcCrossConnectRowStatus to active(1).  If
                         this set is successful, the agent has reserved
                         the resources specified by the ATM traffic
                         parameter and QoS Class values
                         for each direction of the VC cross-connect
                         in an ATM switch or network.

                     (3) The manager sets the
                         atmVcCrossConnectAdminStatus to up(1)
                         in all rows of this VC cross-connect to
                         turn the traffic flow on.


                      One-Shot VC Cross-Connect Establishment

                      A VC cross-connect may also be established in
                      one step by a set-request with all necessary
                      parameter values and atmVcCrossConnectRowStatus
                      set to createAndGo(4).

                      In contrast to the negotiated VC cross-connect
                      establishment which allows for detailed error
                      checking i.e., set errors are explicitly linked to
                      particular resource acquisition failures), the
                      one-shot VC cross-connect establishment
                      performs the setup on one operation but does
                      not have the advantage of step-wise error
                      checking.

                      VC Cross-Connect Retirement

                      A VC cross-connect identified by a particular
                      value of atmVcCrossConnectIndex is released by:

                     (1) Setting atmVcCrossConnectRowStatus of all rows
                         identified by this value of
                         atmVcCrossConnectIndex to destroy(6).
                         The agent may release all
                         associated resources, and the
                         atmVcCrossConnectIndex values in the
                         corresponding atmVclTable row are removed.
                         Note that a situation when only a subset of
                         the associated rows are deleted corresponds
                         to a VC topology change.

                     (2) After deletion of the appropriate
                         atmVcCrossConnectEntries, the manager may
                         set atmVclRowStatus to destroy(6) the
                         associated VCLs.  The agent releases
                         the resources and removes the associated
                         rows in the atmVclTable.

                      VC Cross-Connect Reconfiguration

                      At the discretion of the agent, a VC
                      cross-connect may be reconfigured by
                      adding and/or deleting leafs to/from
                      the VC topology as per the VC cross-connect
                      establishment/retirement procedures.
                      Reconfiguration of traffic/QoS parameter
                      values requires release of the VC cross-connect
                      before those parameter values may by changed
                      for individual VCLs."
                    INDEX { atmVcCrossConnectIndex,
                          atmVcCrossConnectLowIfIndex,
                          atmVcCrossConnectLowVpi,
                          atmVcCrossConnectLowVci,
                          atmVcCrossConnectHighIfIndex,
                          atmVcCrossConnectHighVpi,
                          atmVcCrossConnectHighVci }
                    ::= { atmVcCrossConnectTable 1 }

               AtmVcCrossConnectEntry ::= SEQUENCE {
                    atmVcCrossConnectIndex          INTEGER,
                    atmVcCrossConnectLowIfIndex     IfIndex,
                    atmVcCrossConnectLowVpi         INTEGER,
                    atmVcCrossConnectLowVci         INTEGER,
                    atmVcCrossConnectHighIfIndex    IfIndex,
                    atmVcCrossConnectHighVpi        INTEGER,
                    atmVcCrossConnectHighVci        INTEGER,
                    atmVcCrossConnectAdminStatus    INTEGER,
                    atmVcCrossConnectL2HOperStatus  INTEGER,
                    atmVcCrossConnectH2LOperStatus  INTEGER,
                    atmVcCrossConnectL2HLastChange  TimeStamp,
                    atmVcCrossConnectH2LLastChange  TimeStamp,
                    atmVcCrossConnectRowStatus      RowStatus
                            }

               atmVcCrossConnectIndex OBJECT-TYPE
                    SYNTAX  INTEGER (1..2147483647)
                    MAX-ACCESS  not-accessible
                    STATUS  current
                    DESCRIPTION
                     "A unique value to identify this VC cross-connect."
                    --CONFIGURABLE
                    ::= { atmVcCrossConnectEntry 1 }

               atmVcCrossConnectLowIfIndex OBJECT-TYPE
                    SYNTAX  IfIndex
                    MAX-ACCESS  not-accessible
                    STATUS  current
                    DESCRIPTION
                     "The value of this object is equal to MIB II's
                      ifIndex value of the ATM interface port for this
                      VC cross-connect.  The term low implies
                      that this ATM interface has the numerically lower
                      ifIndex value than the other ATM interface
                      identified in the same atmVcCrossConnectEntry."
                    --CONFIGURABLE
                    ::= { atmVcCrossConnectEntry 2 }

               atmVcCrossConnectLowVpi OBJECT-TYPE
                    SYNTAX  INTEGER  (0..4095)
                    MAX-ACCESS  not-accessible
                    STATUS  current
                    DESCRIPTION
                     "The value of this object is equal to the VPI
                      value at the ATM interface
                      associated with the VC cross-connect that is
                      identified by atmVcCrossConnectLowIfIndex.
                      The VPI value cannot exceed the number
                      supported by the atmInterfaceMaxVpiBits
                      at the low ATM interface port."
                    --CONFIGURABLE
                    ::= { atmVcCrossConnectEntry 3 }

               atmVcCrossConnectLowVci OBJECT-TYPE
                    SYNTAX  INTEGER  (0..65535)
                    MAX-ACCESS  not-accessible
                    STATUS  current
                    DESCRIPTION
                     "The value of this object is equal to the VCI
                      value at the ATM interface
                      associated with this VC cross-connect that is
                      identified by atmVcCrossConnectLowIfIndex.
                      The VCI value cannot exceed the number
                      supported by the atmInterfaceMaxVciBits
                      at the low ATM interface port."
                    --CONFIGURABLE
                    ::= { atmVcCrossConnectEntry 4 }

               atmVcCrossConnectHighIfIndex OBJECT-TYPE
                    SYNTAX  IfIndex
                    MAX-ACCESS  not-accessible
                    STATUS  current
                    DESCRIPTION
                     "The value of this object is equal to MIB II's
                      ifIndex value for the ATM interface port for
                      this VC cross-connect.  The term high
                      implies that this VC cross-connect
                      that this ATM interface has the numerically higher
                      ifIndex value than the other ATM interface
                      identified in the same atmVcCrossConnectEntry."
                    --CONFIGURABLE
                    ::= { atmVcCrossConnectEntry 5 }

               atmVcCrossConnectHighVpi OBJECT-TYPE
                    SYNTAX  INTEGER   (0..4095)
                    MAX-ACCESS  not-accessible
                    STATUS  current
                    DESCRIPTION
                     "The value of this object is equal to the VPI
                      value at the ATM interface
                      associated with the VC cross-connect that is
                      identified by atmVcCrossConnectHighIfIndex.
                      The VPI value cannot exceed
                      the number supported by the atmInterfaceMaxVpiBits
                      at the high ATM interface port."
                    --CONFIGURABLE
                    ::= { atmVcCrossConnectEntry 6 }

               atmVcCrossConnectHighVci OBJECT-TYPE
                    SYNTAX  INTEGER   (0..65535)
                    MAX-ACCESS  not-accessible
                    STATUS  current
                    DESCRIPTION
                     "The value of this object is equal to the VCI
                      value at the ATM interface
                      associated with the VC cross-connect that is
                      identified by atmVcCrossConnectHighIfIndex.
                      The VCI value cannot exceed
                      the number supported by the atmInterfaceMaxVciBits
                      at the high ATM interface port."
                    --CONFIGURABLE
                    ::= { atmVcCrossConnectEntry 7 }

               atmVcCrossConnectAdminStatus OBJECT-TYPE
                    SYNTAX  INTEGER {
                              up(1),
                              down(2)
                              }
                    MAX-ACCESS  read-create
                    STATUS  current
                    DESCRIPTION
                     "The value of this object identifies the desired
                      administrative status of this bi-directional
                      VC cross-connect. The up and down states
                      indicate that the traffic flow is enabled or
                      disabled respectively on this VC cross-connect."
                    DEFVAL { down }
                    --CONFIGURABLE
                    ::= { atmVcCrossConnectEntry 8 }

               atmVcCrossConnectL2HOperStatus OBJECT-TYPE
                    SYNTAX  INTEGER {
                              up(1),
                              down(2),
                              unknown(3)
                            }
                    MAX-ACCESS  read-only
                    STATUS  current
                    DESCRIPTION
                     "The value of this object identifies the current
                      operational status of the VC cross-connect
                      in one direction; (i.e., from the low to
                      high direction).  The up and down states indicate
                      that this ATM VC cross-connect from low
                      to high direction is operational or not
                      operational respectively.  The unknown state
                      indicates that the state of it cannot be
                      determined."
                    ::= { atmVcCrossConnectEntry 9 }

               atmVcCrossConnectH2LOperStatus OBJECT-TYPE
                    SYNTAX  INTEGER {
                              up(1),
                              down(2),
                              unknown(3)
                            }
                    MAX-ACCESS  read-only
                    STATUS  current
                    DESCRIPTION
                     "The value of this object identifies the current
                      operational status of the VC cross-connect
                      in one direction; (i.e., from the high to
                      low direction).  The up and down states indicate
                      that this ATM VC cross-connect from high
                      to low direction is operational or not
                      operational respectively.  The unknown state
                      indicates that the state of it cannot be
                      determined."
                    ::= { atmVcCrossConnectEntry 10 }

               atmVcCrossConnectL2HLastChange OBJECT-TYPE
                    SYNTAX  TimeStamp
                    MAX-ACCESS  read-only
                    STATUS  current
                    DESCRIPTION
                     "The value of MIB II's sysUpTime object
                      at the time this VC cross-connect entered
                      its current operational state in low to high
                      direction.  If the current state was
                      entered prior to the last re-initialization of the
                      agent, then this object contains a zero value."
                    ::= { atmVcCrossConnectEntry 11 }

               atmVcCrossConnectH2LLastChange OBJECT-TYPE
                    SYNTAX  TimeStamp
                    MAX-ACCESS  read-only
                    STATUS  current
                    DESCRIPTION
                     "The value of MIB II's sysUpTime object
                      at the time this VC cross-connect entered
                      its current operational state in high to low
                      direction.  If the current state was
                      entered prior to the last re-initialization of the
                      agent, then this object contains a zero value."
                    ::= { atmVcCrossConnectEntry 12 }

               atmVcCrossConnectRowStatus OBJECT-TYPE
                    SYNTAX  RowStatus
                    MAX-ACCESS  read-create
                    STATUS  current
                    DESCRIPTION
                     "The status of this entry in the
                      atmVcCrossConnectTable.  This object is used to
                      create a new cross-connect for cross-connecting
                      VCLs which are created using the atmVclTable
                      or to change or delete existing cross-connect.
                      This object must be initially set to
                      `createAndWait' or 'createAndGo'.  This object
                      cannot be set to `active' unless the following
                      columnar object exists in this row:
                      atmVcCrossConnectAdminStatus.
                      To turn on a VC cross-connect,
                      the atmVcCrossConnectAdminStatus
                      is set to `up'."
                    --CONFIGURABLE
                    ::= { atmVcCrossConnectEntry 13 }

               END
--
--	usr_atm_cc.mib - MIB defined for supporting CLI commands for
--                       VC Corss Connect. In addition to rfc1695-atmnet.mib
--
-- Author:         
--
--
--  | Copyright (c) 1997 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

               USR-ATM-CROSS-CONNECT-MIB DEFINITIONS ::= BEGIN

               IMPORTS
                  OBJECT-TYPE
                      FROM SNMPv2-SMI
                  RowStatus
                      FROM SNMPv2-TC
                  DisplayString
                      FROM RFC1213-MIB
                  IfIndex
		      FROM ATM-MIB-ATMNET
		  usrAtmCrossConnect
		      FROM USR-DEFINITIONS-MIB
                  ;    

               --  The ATM VC Cross Connect for cli commands

               usrAtmVcCrossConnectTable OBJECT-TYPE
                    SYNTAX  SEQUENCE OF UsrAtmVcCrossConnectEntry
                    MAX-ACCESS  not-accessible
                    STATUS  current
                    DESCRIPTION
                     "This usrAtmVcCrossConnectTable keeps cross connect name
                      and corresponding cross connect index
                      pcr is used to obtain traffic descriptor Index."
                    ::= { usrAtmCrossConnect 1 }


               usrAtmVcCrossConnectEntry OBJECT-TYPE
                    SYNTAX  UsrAtmVcCrossConnectEntry
                    MAX-ACCESS  not-accessible
                    STATUS  current
                    DESCRIPTION " "
                    INDEX { usrAtmVcCrossConnectName}
                    ::= { usrAtmVcCrossConnectTable 1 }

               UsrAtmVcCrossConnectEntry ::= SEQUENCE {
                    usrAtmVcCrossConnectName           DisplayString,
                    usrAtmVcCrossConnectIndex          INTEGER,
                    usrAtmVcCrossConnectLowIfIndex     IfIndex,
                    usrAtmVcCrossConnectLowVpi         INTEGER,
                    usrAtmVcCrossConnectLowVci         INTEGER,
                    usrAtmVcCrossConnectHighIfIndex    IfIndex,
                    usrAtmVcCrossConnectHighVpi        INTEGER,
                    usrAtmVcCrossConnectHighVci        INTEGER,
                    usrAtmVcCrossConnectLowPort        INTEGER,
                    usrAtmVcCrossConnectHighPort       INTEGER,
                    usrAtmVcCrossConnectPcr            INTEGER,
                    usrAtmVcCrossConnectRowStatus      RowStatus
               }

               usrAtmVcCrossConnectName OBJECT-TYPE
                    SYNTAX  DisplayString
                    MAX-ACCESS  not-accessible
                    STATUS  current
                    DESCRIPTION "VC Cross connect name used as index"
                    --CONFIGURABLE
                    ::= { usrAtmVcCrossConnectEntry 1 }

               usrAtmVcCrossConnectIndex OBJECT-TYPE
                    SYNTAX  INTEGER
                    MAX-ACCESS  read-create
                    STATUS  current
                    DESCRIPTION  "cross connect index for the entry  "
                    --CONFIGURABLE
                    ::= { usrAtmVcCrossConnectEntry 2 }

               usrAtmVcCrossConnectLowIfIndex OBJECT-TYPE
                    SYNTAX  IfIndex
                    MAX-ACCESS  read-create
                    STATUS  current
                    DESCRIPTION  "ifindex of the vc with low val "
                    --CONFIGURABLE
                    ::= { usrAtmVcCrossConnectEntry 3 }


               usrAtmVcCrossConnectLowVpi OBJECT-TYPE
                    SYNTAX  INTEGER
                    MAX-ACCESS  read-create
                    STATUS  current
                    DESCRIPTION  "vpi value of the vc with low ifindex"
                    --CONFIGURABLE
                    ::= { usrAtmVcCrossConnectEntry 4 }

               usrAtmVcCrossConnectLowVci OBJECT-TYPE
                    SYNTAX  INTEGER
                    MAX-ACCESS  read-create
                    STATUS  current
                    DESCRIPTION  "vci of the vc with low ifindex val"
                    --CONFIGURABLE
                    ::= { usrAtmVcCrossConnectEntry 5 }

               usrAtmVcCrossConnectHighIfIndex OBJECT-TYPE
                    SYNTAX  IfIndex
                    MAX-ACCESS  read-create
                    STATUS  current
                    DESCRIPTION  "vc associated with high ifindex param"
                    --CONFIGURABLE
                    ::= { usrAtmVcCrossConnectEntry 6 }


               usrAtmVcCrossConnectHighVpi OBJECT-TYPE
                    SYNTAX  INTEGER
                    MAX-ACCESS  read-create
                    STATUS  current
                    DESCRIPTION  "vpi of the vc with high ifindex param"
                    --CONFIGURABLE
                    ::= { usrAtmVcCrossConnectEntry 7 }

               usrAtmVcCrossConnectHighVci OBJECT-TYPE
                    SYNTAX  INTEGER
                    MAX-ACCESS  read-create
                    STATUS  current
                    DESCRIPTION  "vci of the vc eith high ifindex val"
                    --CONFIGURABLE
                    ::= { usrAtmVcCrossConnectEntry 8 }

               usrAtmVcCrossConnectLowPort OBJECT-TYPE
                    SYNTAX  INTEGER
                    MAX-ACCESS  read-create
                    STATUS  current
                    DESCRIPTION  "low end port number"
                    ::= { usrAtmVcCrossConnectEntry 9 }

               usrAtmVcCrossConnectHighPort OBJECT-TYPE
                    SYNTAX  INTEGER
                    MAX-ACCESS  read-create
                    STATUS  current
                    DESCRIPTION  "high end port number"
                    ::= { usrAtmVcCrossConnectEntry 10 }

               usrAtmVcCrossConnectPcr OBJECT-TYPE
                    SYNTAX  INTEGER
                    MAX-ACCESS  read-create
                    STATUS  current
                    DESCRIPTION  "peak cell rate -as traffic descr index created"
                    ::= { usrAtmVcCrossConnectEntry 11 }

               usrAtmVcCrossConnectRowStatus OBJECT-TYPE
                    SYNTAX  RowStatus
                    MAX-ACCESS   read-only
                    STATUS  current
                    DESCRIPTION  "cross connect row status"
                    ::= { usrAtmVcCrossConnectEntry 12 }
               END
--
--	usr_dsx3.mib - A MIB file for the Netserver gateway card
--                    Dsx3 MIB
--
--
-- Author:         Jay D. Miller
--
--
--  | Copyright (c) 1997 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-DSX3-MIB DEFINITIONS ::= BEGIN

	IMPORTS
        OBJECT-TYPE
            FROM SNMPv2-SMI
        DisplayString, usrDsx3, UsrConfigStatus
            FROM USR-DEFINITIONS-MIB;

	usrDsx3ConfigFileName OBJECT-TYPE
		SYNTAX      DisplayString
		MAX-ACCESS      read-write
		STATUS      current
		DESCRIPTION		
		  "The name of a ConfigFile to read/write permanent
		   database records. If the value of this object is an
                   empty string, then the NMBA process uses the
                   default name `@file://Dsx3.cfg'. "
	::= { usrDsx3 1 }

	usrDsx3CFMStatusFlag  OBJECT-TYPE
	 	SYNTAX	  UsrConfigStatus
		MAX-ACCESS      read-write
		STATUS      current
		DESCRIPTION
		  "Setting the value of this object to `save' causes the values
		   of the Dsx3SlotTable to be written out to the
                   current config file, which is stored in the 
                   usrDsx3ConfigFileName object. While the new
                   ConfigFile is being written, the NMBA process
		   will set the value of this flag to `saving''. Any
		   attempts to set the value while it is not `normal'
		   (i.e. the file is currently being written to the
		   ConfigFile) while result in a badValue error being
		   returned. Setting the value to `normal' will result in no
		   action."
	::= { usrDsx3 2 }

    usrDsx3ConfigTable OBJECT-TYPE
        SYNTAX  SEQUENCE OF UsrDsx3ConfigEntry
        MAX-ACCESS  not-accessible
        STATUS  current
        DESCRIPTION
                "USR Specific variable Config table."
        ::= { usrDsx3 3 }

    usrDsx3ConfigEntry OBJECT-TYPE
        SYNTAX  UsrDsx3ConfigEntry
        MAX-ACCESS  not-accessible
        STATUS  current
        DESCRIPTION
                "An entry in the DSX3/E3 Configuration table."
        INDEX   { usrDsx3LineIndex }
        ::= { usrDsx3ConfigTable 1 }

    UsrDsx3ConfigEntry ::=
        SEQUENCE {
            usrDsx3LineIndex
                INTEGER,
            usrDsx3CableLength
                INTEGER,
            usrDsx3FrameType
                INTEGER,
            usrDsx3PayloadScrambling
                INTEGER,
            usrDsx3TransmitCells
                INTEGER,
            usrDsx3RecieveCells
                INTEGER
        }

    usrDsx3LineIndex OBJECT-TYPE
        SYNTAX  INTEGER (1..65535)
        MAX-ACCESS  read-only
        STATUS  current
        DESCRIPTION
        "This object is the identifier of a DSX3/E3
        Interface on a managed device.  If there is an
        ifEntry that is directly associated with this
        and only this DSX3/E3 interface, it should have
        the same value as ifIndex.  Otherwise, number
        the dsx3LineIndices with an unique identifier
        following the rules of choosing a number that
        is greater than ifNumber and numbering the
        inside interfaces (e.g., equipment side) with
        even numbers and outside interfaces (e.g,
        network side) with odd numbers."
	::= { usrDsx3ConfigEntry 1 }

	usrDsx3CableLength  OBJECT-TYPE
		SYNTAX   INTEGER {
         usrDsx3ShortHaul(1),
         usrDsx3LongHaul(2)
			}
		MAX-ACCESS  read-write
		STATUS      current
		DESCRIPTION
                  "This variable indicates which compensation 
                  measures are to be used with varying cable
                  lengths.

                  usrDsx3ShortHaul refers to cable lengths
                  shorter than xx meters. atmDsx3LongHaul handles
                  cable lengths longer than that."

	        --CONFIGURABLE
	::= { usrDsx3ConfigEntry 2 }

	usrDsx3FrameType  OBJECT-TYPE
		SYNTAX   INTEGER {
         usrDsx3Adm(1),
         usrDsx3Plcp(2)
			}
		MAX-ACCESS  read-write
		STATUS      current
		DESCRIPTION
                "This variable indicates which frame type
                 to use in transmission.

                 usrDsx3Adm sets the Phy to use Direct Mapping
                 on transmit , and usrDsx3Plcp uses the PLCP
                 framing format."
                 
	        --CONFIGURABLE
	::= { usrDsx3ConfigEntry 3 }

	usrDsx3PayloadScrambling OBJECT-TYPE
		SYNTAX   INTEGER {
			enabled(1),
			disabled(2)
			}
      MAX-ACCESS      read-write
      STATUS      current
      DESCRIPTION
            "An indicator that tells if this interface is using
             Payload Scrambling.  Setting the variable to enabled
             sets the Phy interface allow scrambling."
	        --CONFIGURABLE
   ::= { usrDsx3ConfigEntry 4 }

    usrDsx3TransmitCells OBJECT-TYPE
        SYNTAX  INTEGER (1..65535)
        MAX-ACCESS  read-only
        STATUS  current
        DESCRIPTION
        "This object contains the number of cells
        transmitted in the current valid interval. At
        the end of each interval the count is reset."
	::= { usrDsx3ConfigEntry 5 }

    usrDsx3RecieveCells OBJECT-TYPE
        SYNTAX  INTEGER (1..65535)
        MAX-ACCESS  read-only
        STATUS  current
        DESCRIPTION
        "This object contains the number of cells
        recieved in the current valid interval. At
        the end of each interval the count is reset."
	::= { usrDsx3ConfigEntry 6 }
END         -- End usrDsx3 MIB definitions







--
--	usr_atm_1483_pvc.mib - A MIB file for the Netserver ATM
--                             RFC1483 PVC MIB. 
--
--
-- Author:         Mike Redden
--
--
--  | Copyright (c) 1997 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--
  USR-ATM-1483-PVC-MIB DEFINITIONS ::= BEGIN

  IMPORTS
      OBJECT-TYPE, IpAddress
          FROM SNMPv2-SMI
      RowStatus
          FROM SNMPv2-TC
      usrAtm1483Pvc, UsrConfigStatus, DisplayString
          FROM USR-DEFINITIONS-MIB
      AtmVpIdentifier, AtmVcIdentifier
	  FROM ATM-TC-MIB
      ;

  usrAtm1483PvcConfigFileName OBJECT-TYPE
      SYNTAX      DisplayString
      MAX-ACCESS  read-write
      STATUS      current
      DESCRIPTION		
	 "The name of a ConfigFile to read/write permanent
	  database records. If the value of this object is an
          empty string, then ATM 1483 uses the default
          name `@file://Atm1483.cfg'. "
     ::= { usrAtm1483Pvc 1 }

  usrAtm1483PvcCFMStatusFlag  OBJECT-TYPE
      SYNTAX	  UsrConfigStatus
      MAX-ACCESS  read-write
      STATUS      current
      DESCRIPTION
	  "Setting the value of this object to `save' causes the values
	   of the ATM ARP MIB objects to be written out to the
           current config file, which is stored in the 
           usrIpoaArpConfigFileName object. While the new
           ConfigFile is being written, ATM ARP
	   will set the value of this flag to `saving''. Any
	   attempts to set the value while it is not `normal'
	   (i.e. the file is currently being written to the
	   ConfigFile) while result in a badValue error being
	   returned. Setting the value to `normal' will result in no
	   action."
     ::= { usrAtm1483Pvc 2 }
  --
  -- The ATM 1483 PVC Table
  --

  usrAtm1483PvcTable OBJECT-TYPE
      SYNTAX      SEQUENCE OF UsrAtm1483PvcEntry
      MAX-ACCESS  not-accessible
      STATUS      current
      DESCRIPTION
          "This usrAtm1483PvcTable keeps a set of PVCs and
           creates a corresponding entry in the appropriate
           protocol ARP cache or equivalent."
      ::= { usrAtm1483Pvc 3 }

  usrAtm1483PvcEntry OBJECT-TYPE
      SYNTAX      UsrAtm1483PvcEntry
      MAX-ACCESS  not-accessible
      STATUS      current
      DESCRIPTION
          "A PVC that this host has opened with another host for
          data transer of datagrams using the encapsulation
          specified in RFC1483. Additional information
          can be determined about the VC from RFC1695, the AToM MIB.

	  When an entry is added to this table, if the corresponding
          network protocol is IP, an entry is added to the 
          ipNetToMediaTable (ARP Cache) to allow the translation of 
          an IP address to the RFC1483 PVC created in this table, 
          and the PVC created in the RFC1695 AToM MIB."

      INDEX       { usrAtm1483PvcName
                  }
      ::= { usrAtm1483PvcTable 1 }


  UsrAtm1483PvcEntry ::= SEQUENCE {
      usrAtm1483PvcName                 DisplayString,
      usrAtm1483PvcVpi                  AtmVpIdentifier,
      usrAtm1483PvcVci                  AtmVcIdentifier,
      usrAtm1483PvcPort			INTEGER,
      usrAtm1483PvcPcr			INTEGER,
      usrAtm1483PvcNetworkName          DisplayString,
      usrAtm1483PvcNetworkAddr          IpAddress,
      usrAtm1483PvcProtocol             INTEGER,
      usrAtm1483PvcRowStatus            RowStatus }

  usrAtm1483PvcName OBJECT-TYPE
      SYNTAX DisplayString (SIZE(0..32))
      MAX-ACCESS  not-accessible
      STATUS      current
      DESCRIPTION
         "A string containing the name of the RFC1483 PVC."
      --CONFIGURABLE
      ::= { usrAtm1483PvcEntry 1 }

  usrAtm1483PvcVpi OBJECT-TYPE
      SYNTAX      AtmVpIdentifier
      MAX-ACCESS  read-create
      STATUS      current
      DESCRIPTION
          "The VPI value for the RFC1483 PVC."
	 --CONFIGURABLE
      ::= { usrAtm1483PvcEntry 2 }

  usrAtm1483PvcVci OBJECT-TYPE
      SYNTAX      AtmVcIdentifier
      MAX-ACCESS  read-create
      STATUS      current
      DESCRIPTION
          "The VCI value for the RFC1483 PVC."
	 --CONFIGURABLE
      ::= { usrAtm1483PvcEntry 3 }


  usrAtm1483PvcPort OBJECT-TYPE
      SYNTAX INTEGER(1..2)
      MAX-ACCESS  read-create
      STATUS      current
      DESCRIPTION
         "The port number for the RFC1483 PVC."
      --CONFIGURABLE
      ::= { usrAtm1483PvcEntry 4 }

  usrAtm1483PvcPcr OBJECT-TYPE
      SYNTAX INTEGER(1000..100000)
      MAX-ACCESS  read-create
      STATUS      current
      DESCRIPTION
         "The peak cell rate value to use when creating this PVC."
      --CONFIGURABLE
      ::= { usrAtm1483PvcEntry 5 }

  usrAtm1483PvcNetworkName OBJECT-TYPE
      SYNTAX DisplayString (SIZE(0..32))
      MAX-ACCESS  read-create
      STATUS      current
      DESCRIPTION
         "A string containing the name of the network of this RFC1483 PVC."
      --CONFIGURABLE
      ::= { usrAtm1483PvcEntry 6 }

  usrAtm1483PvcNetworkAddr OBJECT-TYPE
      SYNTAX IpAddress
      MAX-ACCESS  read-create
      STATUS      current
      DESCRIPTION
         "The network layer address of the end station that this
          RFC1483 PVC connects to.  This value is placed in the 
          ARP cache as a static entry so that the IP forwarder
          may map traffic destined for this network address to 
          this RFC1483 PVC."

      --CONFIGURABLE
      ::= { usrAtm1483PvcEntry 7 }

  usrAtm1483PvcProtocol OBJECT-TYPE
      SYNTAX INTEGER {
		     ip(1),
		     ipx(2),
		     at(3)
		     }
      MAX-ACCESS  read-only
      STATUS      current
      DESCRIPTION
         "The Level 3 protocol running over this RFC1483 PVC."
      --CONFIGURABLE
      ::= { usrAtm1483PvcEntry 8 }

  usrAtm1483PvcRowStatus OBJECT-TYPE
      SYNTAX      RowStatus
      MAX-ACCESS  read-create
      STATUS      current
      DESCRIPTION
         "This object allows rows to be created and deleted in the
          usrAtm1483PvcTable. For a PVC on an IP network, an entry 
          in this table will have a corresponding ipNetToMediaEntry 
          to allow the translation of an IP address to this PVC. Setting 
          this object to destroy(6) removes the corresponding 
          ipNetToMediaTable entry, if any."

     REFERENCE
         "RFC 1903, 'Textual Conventions for version 2 of the Simple
         Network Management Protocol (SNMPv2).'"
	 --CONFIGURABLE
     ::= { usrAtm1483PvcEntry 9 }

  usrAtm1483PvcDefaultPcr OBJECT-TYPE
      SYNTAX INTEGER
      MAX-ACCESS  read-only
      STATUS      current
      DESCRIPTION
         "An integer containing the default peak cell rate to use
	  when establishing VCs.  This value is one tenth the speed
          of the physical interface expressed as a cell rate."
      ::= { usrAtm1483Pvc 4 }

  END



--
--	usr_atm_1577_pvc.mib - MIB defined for supporting CLI commands for
--                             1577 PVCs.
--
-- Author:         
--
--
--  | Copyright (c) 1997 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

               USR-ATM-1577-PVC-MIB DEFINITIONS ::= BEGIN

               IMPORTS
                  OBJECT-TYPE
                      FROM SNMPv2-SMI
                  DisplayString
                      FROM RFC1213-MIB
		  RowStatus
	              FROM SNMPv2-TC
                  IfIndex
		      FROM ATM-MIB-ATMNET
	          usrAtm1577Pvc
	              FROM USR-DEFINITIONS-MIB
                  ;    

               --  The ATM 1577 PVCs for cli commands

               usrAtm1577PvcTable OBJECT-TYPE
                    SYNTAX  SEQUENCE OF UsrAtm1577PvcEntry
                    MAX-ACCESS  not-accessible
                    STATUS  current
                    DESCRIPTION
                     "This usrAtm1577PvcTable keeps PVC name
                      and corresponding index values for the
                      VCL table row. It also contains mib objects
   		      that may be used in retrieving values for
 	              display of 1577 PVCs."
                    ::= { usrAtm1577Pvc 1 }

               usrAtm1577PvcEntry OBJECT-TYPE
                    SYNTAX  UsrAtm1577PvcEntry
                    MAX-ACCESS  not-accessible
                    STATUS  current
                    DESCRIPTION "This is the name of the RFC1577 PVC."
                    INDEX { usrAtm1577PvcName}
                    ::= { usrAtm1577PvcTable 1 }

               UsrAtm1577PvcEntry ::= SEQUENCE {
                    usrAtm1577PvcName	        DisplayString,
                    usrAtm1577PvcIfIndex        IfIndex,
                    usrAtm1577PvcVpi		INTEGER,
		    usrAtm1577PvcVci		INTEGER,
		    usrAtm1577PvcNetworkName    DisplayString,
		    usrAtm1577PvcPort           INTEGER,
		    usrAtm1577PvcPcr            INTEGER,
	 	    usrAtm1577PvcRowStatus      RowStatus
               }

               usrAtm1577PvcName OBJECT-TYPE
                    SYNTAX  DisplayString
                    MAX-ACCESS  not-accessible
                    STATUS  current
                    DESCRIPTION "ATM 1577 PVC name used as an index"
                    ::= { usrAtm1577PvcEntry 1 }

               usrAtm1577PvcIfIndex OBJECT-TYPE
                    SYNTAX  IfIndex
                    MAX-ACCESS  read-create
                    STATUS  current
                    DESCRIPTION  "IfIndex of the ATMNET interface for this entry"
		    --CONFIGURABLE
                    ::= { usrAtm1577PvcEntry 2 }

               usrAtm1577PvcVpi OBJECT-TYPE
                    SYNTAX  INTEGER (0..4095)
                    MAX-ACCESS  read-create
                    STATUS  current
                    DESCRIPTION  "VPI value of this ATM 1577 PVC "
                    --CONFIGURABLE
                    ::= { usrAtm1577PvcEntry 3 }

               usrAtm1577PvcVci OBJECT-TYPE
                    SYNTAX  INTEGER (0..65535)
                    MAX-ACCESS  read-create
                    STATUS  current
                    DESCRIPTION  "VCI value of this ATM 1577 PVC "
                    --CONFIGURABLE
                    ::= { usrAtm1577PvcEntry 4 }

               usrAtm1577PvcPort OBJECT-TYPE
		    SYNTAX INTEGER(1..2)
                    MAX-ACCESS  read-only
                    STATUS      current
                    DESCRIPTION
                    "The port number for the RFC1577 PVC."
                    ::= { usrAtm1577PvcEntry 5 }

               usrAtm1577PvcPcr OBJECT-TYPE
                    SYNTAX INTEGER(1000..100000)
                    MAX-ACCESS  read-only
                    STATUS      current
                    DESCRIPTION
                    "The peak cell rate configured for this PVC."
                    ::= { usrAtm1577PvcEntry 6 }

               usrAtm1577PvcNetworkName OBJECT-TYPE
                    SYNTAX DisplayString (SIZE(0..32))
                    MAX-ACCESS  read-only
                    STATUS      current
                    DESCRIPTION
                    "A string containing the name of the network of this RFC1577 PVC."
                    ::= { usrAtm1577PvcEntry 7 }

               usrAtm1577PvcRowStatus OBJECT-TYPE
                    SYNTAX  RowStatus
                    MAX-ACCESS  read-only
                    STATUS  current
                    DESCRIPTION  "1577 PVC VCL row status"
                    ::= { usrAtm1577PvcEntry 8 }
               END






--
--	usr_atmcfg.mib - A MIB file for ATM configuration for the
--                   Netserver gateway card
--                   AtmCfg MIB
--
--
-- Author:         Mike Clarke
--
--
--  | Copyright (c) 1997 U.S. Robotics Access Corp., Skokie, IL 60076      |
--  |                                                                      |
--  | The information in this software is subject to change without notice |
--  | and should not be construed as a commitment by U.S. Robotics Access  |
--  | Corp.                                                                |
--  |                                                                      |
--  | U.S. Robotics Access Corp. assumes no responsibility for the use or  |
--  | reliability of its software on equipment which is not supplied by    |
--  | U.S. Robotics Access Corp.                                           |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in U.S. Robotics Access Corp.                           |
--

USR-ATMCFG-MIB DEFINITIONS ::= BEGIN

	IMPORTS
        OBJECT-TYPE
            FROM SNMPv2-SMI
        DisplayString, usrAtmCfg
            FROM USR-DEFINITIONS-MIB;

    usrAtmCfgTable OBJECT-TYPE
        SYNTAX  SEQUENCE OF UsrAtmCfgEntry
        MAX-ACCESS  not-accessible
        STATUS  current
        DESCRIPTION
            "USR Specific ATM Config table."
    ::= { usrAtmCfg 1 }
    
    usrAtmCfgEntry OBJECT-TYPE
        SYNTAX     UsrAtmCfgEntry
        MAX-ACCESS not-accessible
        STATUS     current
        DESCRIPTION
            "An entry in the Atm Configuration table."
        INDEX   { usrAtmIfName }
    ::= { usrAtmCfgTable 1 }
    
    UsrAtmCfgEntry ::=
        SEQUENCE {
           usrAtmIfName         DisplayString,
           usrSigAdminStatus    INTEGER,
           usrSigOperStatus     INTEGER,
           usrIlmiAdminStatus   INTEGER,
           usrIlmiOperStatus    INTEGER
        }

    usrAtmIfName OBJECT-TYPE
        SYNTAX      DisplayString
        MAX-ACCESS  not-accessible
        STATUS      current
        DESCRIPTION
        "This object is the identifier of a ATM (AAL)
        Interface on a managed device."
	::= { usrAtmCfgEntry 1 }

    usrSigAdminStatus OBJECT-TYPE
        SYNTAX  INTEGER {
            enable(1),
            disable(2)
        }
        MAX-ACCESS  read-write
        STATUS      current
        DESCRIPTION
            "The desired state of Signalling on a desired interface.
             The interface name, specified by usrAtmIfName represents
             the AAL interface to enable or disable signalling on. If
             the state is 'enable' then signalling messages will flow
             on the interface. If the state is changed to disable,
             then all signalling messages will stop on the interface."

    --CONFIGURABLE
	::= { usrAtmCfgEntry 2 }

    usrSigOperStatus OBJECT-TYPE
        SYNTAX  INTEGER {
            enabled(1),
            disabled(2)
        }
        MAX-ACCESS  read-only
        STATUS      current
        DESCRIPTION
            "The actual state of Signalling on a desired interface.
             This state should follow the state set by
             usrSigAdminStatus."
	::= { usrAtmCfgEntry 3 }

    usrIlmiAdminStatus OBJECT-TYPE
        SYNTAX  INTEGER {
            enable(1),
            disable(2)
        }
        MAX-ACCESS  read-write
        STATUS      current
        DESCRIPTION
            "The desired state of ILMI on a desired interface.  The
             interface name, specified by usrAtmIfName represents the
             AAL interface to enable or disable ILMI on. If the state
             is 'enable' then ILMI messages will flow on the
             interface. If the state is changed to disable, then all
             ILMI messages will stop on the interface."

    --CONFIGURABLE
	::= { usrAtmCfgEntry 4 }

    usrIlmiOperStatus OBJECT-TYPE
        SYNTAX  INTEGER {
            enabled(1),
            disabled(2)
        }
        MAX-ACCESS  read-only
        STATUS      current
        DESCRIPTION
            "The actual state of ILMI on a desired interface.  This
             state should follow the state set by usrSigAdminStatus."
	::= { usrAtmCfgEntry 5 }

END         -- End usrAtmCfg MIB definitions
